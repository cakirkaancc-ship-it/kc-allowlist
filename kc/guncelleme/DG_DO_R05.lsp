(setq *DEG_CODEMAP*
  '(
    (A1  LAYER   "E_AYDINLATMA_KNX_HATTI")
    (A2  LAYER   "E_AYDINLATMA_LINYE")
    (A3  LAYER   "E_AYDINLATMA_LINYE_KOMBINE")
    (A4  LAYER   "E_LIGHTING_LINE")
    (A5  LAYER   "E_LIGHTING_MULTI_LINE")
    (A6  BLOCK   "E_ARMATÜR")
    (A7  LAYER   "E_AYDINLATMA_BUTON_HATTI")

    (B1  LAYER   "E_PRIZ_LINYE")
    (B2  LAYER   "E_PRIZ_LINYE_KOMBINE")
    (B3  LAYER   "E_SOCKET_LINE")
    (B4  LAYER   "E_SOCKET_LINE_COMBINE")

    (C1  LAYER   "E_DATA_HATTI")
    (C2  LAYER   "E_DATA_LINE")
    (C3  LAYER   "E_DATA_MULTI_LINE")
    (C4  LAYER   "E_DATA_KOMBINE_HATTI")
    (C5  LAYER   "E_FIBER_OPTIK_KABLO")
    (C6  LAYER   "E_FIBER_OPTIC_LINE")
    (C7  LAYER   "E_FIBER_OPTIC_MULTI_LINE")
    (C8  LAYER   "E_FIBER_OPTIK_KOMBINE_HATTI")
    (C9  PATTERN "*DATA*")
    (C10 KEYWORD "DATA")

    (D1  LAYER   "E_CCTV_HAT")
    (D2  LAYER   "E_CCTV_LINE")
    (D3  LAYER   "E_CCTV_MULTI_LINE")
    (D4  LAYER   "E_CCTV_KOMBINE")
    (D5  PATTERN "*CCTV*")
    (D6  KEYWORD "CCTV")

    (E1  LAYER   "E_TELEFON_HATTI")
    (E2  LAYER   "E_TELEPHONE_LINE")
    (E3  LAYER   "E_TELEPHONE_MULTI_LINE")
    (E5  LAYER   "E_TELEFON_KOMBINE_HATTI")
    (E4  PATTERN "*TELEFON*")

    (F1  LAYER   "E_TV_HATTI")
    (F2  LAYER   "E_TV_KOMBINE_HATTI")
    (F3  LAYER   "E_TV_LINE")
    (F4  LAYER   "E_TV_MULTI_LINE")
    (F5  PATTERN "*TV*")

    (G1  LAYER   "E_UPS_LINYE")
    (G2  LAYER   "E_UPS_LINYE_KOMBINE")
    (G3  LAYER   "E_UPS_LINE")
    (G4  LAYER   "E_UPS_MULTI_LINE")

    (H1  LAYER   "E_KARTLI_GEÇIÞ_HAT")
    (H2  LAYER   "E_KARTLI_GEÇIÞ_KOMBINE")
    (H3  LAYER   "E_KARTLI_LINE")
    (H4  LAYER   "E_KARTLI_MULTI_LINE")
    (H5  PATTERN "*KARTLI*")

    (I1  BLOCK   "E_BUAT")
    (I2  BLOCK   "E_BUAT_100")
    (I3  PATTERN "*BUAT*")
    (I4  PATTERN "E_BUAT_*")

    (J1  BLOCK   "E_DAGITIM_PANOSU_100")
    (J2  BLOCK   "E_DAÐITIM_PANOSU_100")
    (J3  BLOCK   "E_DAÐýTýM_PANOSU_100")
    (J4  PATTERN "*PANO*")

    (K1  LAYER   "E_FLAÞÖR")
    (K2  BLOCK   "E_INDIKATR_100")
    (K3  BLOCK   "E_FIRE_ALARM_PANEL_100")
    (K4  BLOCK   "E_YANGIN_IHBAR_PANELI_100")
    (K5  BLOCK   "E_GÜÇ_KAYNAÐI_100")
    (K6  BLOCK   "E_CO_PANEL_100")
    (K7  BLOCK   "E_CO_DEDEKTÖR_100")
    (K8  PATTERN "*E_KARBONMONOKSIT_HAT*")
    (K9  PATTERN "*FIRE*")
    (K10 PATTERN "*YANG*")
    (K11 PATTERN "*YANGIN*")
    (K12 PATTERN "*FLAÞÖR*")
    (K13 PATTERN "*FLAÞ*")
    (K14 PATTERN "*FLASH*")
    (K15 PATTERN "*STROBE*")
    (K16 KEYWORD "FLASOR")
    (K17 KEYWORD "FLAÞÖR")
    (K18 BLOCK   "E_POWER_SUPPLY")
    (K19 BLOCK   "E_SIREN_KONTROL_MODÜL_100")

    (L1  KEYWORD "KLEMENS")
    (L2  KEYWORD "TERMINAL")

    (M1  BLOCK   "E_DOSEMEYE_INIS")
    (M2  PATTERN "*INIS*")
    (M3  PATTERN "*E_DOSEMEYE_INIS*")
    (M4  PATTERN "*E*DOSEMEYE*INIS*")

    (N1  BLOCK   "E_ILGILI_NOT_NO")
    (N2  PATTERN "*E_OK_*,*E_ARROW*")

    (O1  LAYER   "E_KOLON_NUMARASI")
    (O2  LAYER   "E_KOLON_SEMBOL")

    (P1  BLOCK   "E_LINYE")
    (P2  BLOCK   "E_MAHAL")

    (R1  KEYWORD "DEG_DONE")
    (R2  KEYWORD "DEG_SORTI")
  )
)

(setq *DEG_TOL_CODES*
  '(
    (Q1 LAYER "DEG_TOL_7")
    (Q2 LAYER "DEG_TOL_30")
  )
)

(setq *DEG_CODE_OVERRIDES* nil)
(setq *DEG_CFG_DEFAULTS*
  '(
    (DD_OFFSET . "10.0")
    (DD_AGIZ_ARAMA . "20.0")
    (DD_BLOK_YAKINLIK . "100.0")
    (DD_DIRSEK_DIST . "200.0")
    (DD_DIRSEK_KACIS . "50.0")
    (DF_OFFSET . "10.0")
    (DF_AGIZ_ARAMA . "20.0")
    (DF_BLOK_YAKINLIK . "100.0")
    (DF_DIRSEK_DIST . "200.0")
    (DF_DIRSEK_KACIS . "50.0")
    (DZ_OFFSET . "10.0")
    (DZ_AGIZ_ARAMA . "20.0")
    (DZ_BLOK_YAKINLIK . "100.0")
    (DZ_DIRSEK_DIST . "200.0")
    (DZ_DIRSEK_KACIS . "50.0")
    (DZ_COCUK_HAT_MESAFE . "750.0")
    (DC_DOWN_LEN . "200.0")
    (DC_FILLET_R . "10.0")
    (DC_SIDE_LEN . "700.0")
    (DD_DZ_ORTHO . "0")
    (DG_EXTRA_LIGHTING_LAYERS . "")
    (DG_KIT_LAYER . "E_ACIL_AYDINLATMA_KIT_SINYAL_HATTI")
    (DG_ANAHTAR_LAYER . "E_ANAHTAR_HATTI")
    (DK_TOUCH_TOL . "5.0")
    (DK_COPY_SPACING . "100.0")
    (DK_NORMAL_AREA_LAYERS . "E_YANGIN_HAT,E_YANGIN_HATTI,E_FIRE_LINE,E_FIRE_ALARM_LINE,E_FLAÞÖR,E_FLASOR,E_FLASHER,E_STROBE,E_STROBE_LINE,E_SES_HAT,E_ANNOUNCEMENT_LINE")
    (DK_COMBINED_RISER_LAYERS . "E_YANGIN_KOMBINE,E_FIRE_MULTI_LINE,E_ANNOUNCEMENT_MULTI_LINE,E_SES_KOMBINE")
    (DK_NORMAL_GROUP_SPACING . "0.0")
    (DK_NORMAL_FLOOR_SPACING . "700.0")
    (DK_UNDER_X1 . "10.0")
    (DK_UNDER_X2 . "10.0")
    (DK_UNDER_W . "70.0")
    (DK_UNDER_H . "60.0")
    (DK_TEXT_OFFSET_Y . "90.0")
    (DK_TEXT_HEIGHT . "25.0")
    (DK_UNDER_Y_OFFSET . "0.0")
    (DK_LOOP_TEXT_HEIGHT . "13.0")
    (DK_LOOP_TEXT_X_OFFSET . "15.0")
    (DK_LOOP_TEXT_Y_MARGIN . "5.0")
    (DK_LOOP_LINE_SHIFT_X . "30.0")
    (DK_LOOP_LINE_RISE . "50.0")
    (DK_LOOP_LINE_RUN . "300.0")
    (DK_LOOP_MARK_LENGTH . "10.0")
    (DKX_TOUCH_TOL . "7.0")
    (DKX_COPY_SPACING . "140.0")
    (DKX_FIRSTSTART_X . "110.0")
    (DKX_FIRSTSTART_Y . "100.0")
    (DKX_LASTBOTTOM_X . "10.0")
    (DKX_LASTBOTTOM_Y . "100.0")
    (DKX_TEXT_OFFSET_Y . "70.0")
    (DKX_TEXT_HEIGHT . "25.0")
    (DKX_MULTI_DX . "10.0")
    (DKX_MULTI_DROP_Y . "10.0")
    (DKX_VLEN_MAIN . "100.0")
    (DKX_VLEN_SECONDARY . "90.0")
    (DKX_HLEN_DEFAULT . "150.0")
    (DKX_HLEN_LAST2 . "20.0")
    (DKX_HLEN_LAST3_LEFT . "10.0")
    (DKX_HLEN_LAST3_RIGHT . "20.0")
    (DKX_DATA_SHIFT_Y . "5.25")
    (DKX_DATA_SHIFT_BLOCKS . "KLEMENS,TERMINAL")
    (PLAN_UNIT . "mm")
    (DO_KAYIT_PATH . "")
    (DP_E_LINE_VALUES . "")
    (DP_LIGHTING_LINE_LAYERS . "E_AYDINLATMA_LINYE,E_LIGHTING_LINE,E_AYDINLATMA_KNX_HATTI,E_AYDINLATMA_BUTON_HATTI,E_ANAHTAR_HATTI,E_ACIL_AYDINLATMA_KIT_SINYAL_HATTI")
    (DP_LIGHTING_COMB_LAYERS . "E_AYDINLATMA_LINYE_KOMBINE,E_LIGHTING_MULTI_LINE")
    (DP_DATA_LINE_LAYERS . "E_DATA_HATTI,E_DATA_LINE")
    (DP_DATA_COMB_LAYERS . "E_DATA_MULTI_LINE,E_DATA_KOMBINE_HATTI")
    (DP_E_BLOCK_VALUES . "")
    (DS_ROW_SPACING . "110.0")
    (DS_SYMBOL_DX . "110.0")
    (DS_COUNT_DX . "120.0")
    (DS_TABLE_BLOCK_W . "110.0")
    (DS_TABLE_SYMBOL_W . "120.0")
    (DS_TABLE_COUNT_W . "120.0")
    (DS_TEXT_HEIGHT . "25.0")
    (DS_EXCLUDE_BLOCKS . "E_OK,E_ARROW,E_DÖÞEME,E_DÖSEME,E_DOSEME")
    (CMD_DG . "DG")
    (CMD_DGT . "DGT")
    (CMD_DN . "DN")
    (CMD_DK . "DK")
    (CMD_DKK . "DKK")
    (CMD_DP . "DP")
    (CMD_DZ . "DZ")
    (CMD_DD . "DD")
    (CMD_DF . "DF")
    (CMD_DR . "DR")
    (CMD_DW . "DW")
    (CMD_DM . "DM")
    (CMD_DS . "DS")
    (CMD_DT . "DT")
    (CMD_DTM . "DTM")
    (CMD_DTT . "DTT")
    (DTT_OUTSIDE_GAP . "15.0")
    (DTT_RECT_WIDTH . "70.0")
    (DTT_RECT_HEIGHT . "40.0")
    (DTT_ATT_TEXT_HEIGHT . "8.0")
    (DTT_ATT_TEXT_STYLE . "Standard")
    (CMD_DO . "DO")
    (CMD_UCS . "UCS")
    (DG_KNX_START_TOL . "50.0")
    (DG_KNX_BLOCK_TOL . "30.0")
    (DG_KNX_END_TOL . "30.0")
    (DG_REF_TOL . "50.0")
    (DG_CHAIN_TOL . "7.0")
    (DG_REPORT_TOL . "7.0")
    (DG_REF_DAL_TOL . "7.0")
    (DG_DAL_SINGLE_TOL . "5.0")
    (DG_P1_TOL . "3.0")
    (DN_CHAIN_TOL . "5.0")
    (DN_BLOCK_TOL . "1.0")
    (DN_DOSEME_TOL . "10.0")
    (DN_MODL_TOL . "5.0")
    (DW_TOUCH_TOL . "0.000001")
    (DR_TREE_TOL . "0.1")
    (DGT_CHAIN_COLOR . "1")
    (DGT_TOL_SMALL_COLOR . "2")
    (DGT_TOL_BIG_COLOR . "3")
    (DGT_SORTI_COLOR . "4")
    (DGT_REF_COLOR . "7")
    (DT_KA_COLOR . "7")
    (DT_ZA_COLOR . "7")
    (DT_TYPE1_CODE . "KA")
    (DT_TYPE1_LAYER . "e_KA_tava")
    (DT_TYPE1_COLOR . "7")
    (DT_TYPE1_HATCH_PATTERN . "SOLID")
    (DT_TYPE1_HATCH_COLOR . "8")
    (DT_TYPE1_HATCH_SCALE . "10")
    (DT_TYPE2_CODE . "ZA")
    (DT_TYPE2_LAYER . "e_ZA_tava")
    (DT_TYPE2_COLOR . "7")
    (DT_TYPE2_HATCH_PATTERN . "SOLID")
    (DT_TYPE2_HATCH_COLOR . "8")
    (DT_TYPE2_HATCH_SCALE . "10")
    (DT_TYPE3_CODE . "")
    (DT_TYPE3_LAYER . "")
    (DT_TYPE3_COLOR . "7")
    (DT_TYPE3_HATCH_PATTERN . "SOLID")
    (DT_TYPE3_HATCH_COLOR . "8")
    (DT_TYPE3_HATCH_SCALE . "10")
    (DT_TYPE4_CODE . "")
    (DT_TYPE4_LAYER . "")
    (DT_TYPE4_COLOR . "7")
    (DT_TYPE4_HATCH_PATTERN . "SOLID")
    (DT_TYPE4_HATCH_COLOR . "8")
    (DT_TYPE4_HATCH_SCALE . "10")
    (DT_TYPE5_CODE . "")
    (DT_TYPE5_LAYER . "")
    (DT_TYPE5_COLOR . "7")
    (DT_TYPE5_HATCH_PATTERN . "SOLID")
    (DT_TYPE5_HATCH_COLOR . "8")
    (DT_TYPE5_HATCH_SCALE . "10")
    (DT_TYPE6_CODE . "")
    (DT_TYPE6_LAYER . "")
    (DT_TYPE6_COLOR . "7")
    (DT_TYPE6_HATCH_PATTERN . "SOLID")
    (DT_TYPE6_HATCH_COLOR . "8")
    (DT_TYPE6_HATCH_SCALE . "10")
    (DT_TYPE7_CODE . "")
    (DT_TYPE7_LAYER . "")
    (DT_TYPE7_COLOR . "7")
    (DT_TYPE7_HATCH_PATTERN . "SOLID")
    (DT_TYPE7_HATCH_COLOR . "8")
    (DT_TYPE7_HATCH_SCALE . "10")
  )
)
(setq *DEG_CFG_OVERRIDES* nil)
(setq *DEG_SETTINGS_FILE* nil)
(setq *DEG_SELF_FILE*
  (cond
    ((and (boundp '*load-truename*) *load-truename* (findfile *load-truename*)) (findfile *load-truename*))
    ((and (boundp '*load-truename*) *load-truename*) *load-truename*)
    ((and (boundp '*load-filename*) *load-filename* (findfile *load-filename*)) (findfile *load-filename*))
    ((and (boundp '*load-filename*) *load-filename*) *load-filename*)
    (T *DEG_SELF_FILE*)
  )
)

;; DEG_DO_PERSIST_BEGIN
(setq *DEG_PERSIST_CODE_OVERRIDES* nil)
(setq *DEG_PERSIST_CFG_OVERRIDES* nil)
;; DEG_DO_PERSIST_END
(setq *DEG_SETTINGS_FILE* nil)
(setq *DEG_DATA_DIR_CHECKED* nil)
(setq *DEG_DATA_DIR* nil)

(defun DEG:LEGACY-SETTINGS-FILE ()
  (strcat (getenv "TEMP") "\\DEG_DO_SETTINGS.lsp")
)

(defun DEG:PROGRAM-DATA-ROOT (/ base)
  (setq base (getenv "ProgramData"))
  (if (or (null base) (= (vl-string-trim " \t\r\n" base) ""))
    (setq base "C:\\ProgramData"))
  base
)

(defun DEG:USER-DATA-ROOT (/ base)
  (setq base (getenv "LOCALAPPDATA"))
  (if (or (null base) (= (vl-string-trim " \t\r\n" base) ""))
    (setq base (getenv "APPDATA")))
  (if (or (null base) (= (vl-string-trim " \t\r\n" base) ""))
    (setq base (getenv "TEMP")))
  base
)

(defun DEG:TRY-DATA-DIR (dir / made probe file)
  (if dir
    (progn
      (if (vl-file-directory-p dir)
        (setq made T)
        (setq made
          (not (vl-catch-all-error-p
                 (vl-catch-all-apply 'vl-mkdir (list dir))))))
      (if (and made (vl-file-directory-p dir))
        (progn
          (setq probe (strcat dir "\\write_test_" (itoa (getvar "MILLISECS")) ".tmp")
                file (open probe "w"))
          (if file
            (progn
              (write-line "DEG" file)
              (close file)
              (vl-catch-all-apply 'vl-file-delete (list probe))
              dir))))))
)

(defun DEG:DATA-DIR (/ dir)
  (if (not *DEG_DATA_DIR_CHECKED*)
    (progn
      (setq *DEG_DATA_DIR_CHECKED* T
            *DEG_DATA_DIR* nil)
      ;; DO ayarlari bilgisayardaki diger Windows kullanicilariyla karismasin.
      (setq dir (DEG:USER-DATA-ROOT))
      (if dir (setq *DEG_DATA_DIR* (DEG:TRY-DATA-DIR (strcat dir "\\DEG"))))
      ;; Kullanici profili yazilamazsa eski ortak konum yedek olarak kalir.
      (if (not *DEG_DATA_DIR*)
        (setq *DEG_DATA_DIR*
          (DEG:TRY-DATA-DIR (strcat (DEG:PROGRAM-DATA-ROOT) "\\DEG"))))))
  *DEG_DATA_DIR*
)

(defun DEG:RUNTIME-FILE (name / dir base)
  (setq dir (DEG:DATA-DIR))
  (if dir
    (strcat dir "\\" name)
    (progn
      (setq base
        (cond
          ((getenv "TEMP"))
          ((getenv "LOCALAPPDATA"))
          ((getenv "APPDATA"))
          (T "C:\\Windows\\Temp")))
      (strcat base "\\" name)))
)

(defun DEG:OLD-SETTINGS-FILES (/ bases out base oldFile directFile)
  (setq out
    (list (strcat (DEG:PROGRAM-DATA-ROOT) "\\DEG\\DEG_DO_SETTINGS.lsp")))
  (setq bases (list (getenv "LOCALAPPDATA") (getenv "APPDATA") (getenv "TEMP")))
  (foreach base bases
    (if (and base (/= base ""))
      (progn
        (setq oldFile (strcat base "\\DEG\\DEG_DO_SETTINGS.lsp")
              directFile (strcat base "\\DEG_DO_SETTINGS.lsp"))
        (if (not (member oldFile out)) (setq out (append out (list oldFile))))
        (if (not (member directFile out)) (setq out (append out (list directFile)))))))
  out
)

(defun DEG:SETTINGS-FILE ()
  (if (not *DEG_SETTINGS_FILE*)
    (setq *DEG_SETTINGS_FILE* (DEG:RUNTIME-FILE "DEG_DO_SETTINGS.lsp")))
  *DEG_SETTINGS_FILE*
)

(defun DEG:SAFE-ALIST (al / out p)
  (setq out nil)
  (if (listp al)
    (foreach p al
      (if (vl-consp p)
        (setq out (cons (cons (car p) (cdr p)) out))
      )
    )
  )
  (reverse out)
)

(defun DEG:SANITIZE-SETTINGS ()
  (setq *DEG_CODE_OVERRIDES* (DEG:SAFE-ALIST *DEG_CODE_OVERRIDES*))
  (setq *DEG_CFG_OVERRIDES*  (DEG:SAFE-ALIST *DEG_CFG_OVERRIDES*))
  T
)

(defun DEG:ALIST-PUT (al k v / a)
  (if (setq a (assoc k al))
    (subst (cons k v) a al)
    (cons (cons k v) al)
  )
)

(defun DEG:ALIST-DEL (al k / out p)
  (setq out nil)
  (foreach p al
    (if (/= (car p) k)
      (setq out (cons p out))
    )
  )
  (reverse out)
)

(defun DEG:EXPAND-ENV-PATH (text / out first second name value guard)
  (setq out text
        guard 0)
  (while (and out
              (< guard 10)
              (setq first (vl-string-search "%" out))
              (setq second (vl-string-search "%" out (1+ first))))
    (setq name  (substr out (+ first 2) (- second first 1))
          value (getenv name))
    (if (and value (/= value ""))
      (setq out
        (strcat
          (if (> first 0) (substr out 1 first) "")
          value
          (substr out (+ second 2))))
      (setq guard 10))
    (setq guard (1+ guard)))
  out
)

(defun DEG:DESKTOP-PATH (/ reg user one candidates path)
  (setq reg
    (vl-catch-all-apply
      'vl-registry-read
      (list
        "HKEY_CURRENT_USER\\Software\\Microsoft\\Windows\\CurrentVersion\\Explorer\\User Shell Folders"
        "Desktop")))
  (if (vl-catch-all-error-p reg) (setq reg nil))
  (if (and reg (= (type reg) 'STR))
    (setq reg (DEG:EXPAND-ENV-PATH reg)))
  (setq user (getenv "USERPROFILE")
        one  (getenv "OneDrive")
        candidates
          (list
            reg
            (if one (strcat one "\\Desktop"))
            (if one (strcat one "\\Masaüstü"))
            (if user (strcat user "\\Desktop"))
            (if user (strcat user "\\Masaüstü"))))
  (while (and candidates (not path))
    (if (and (car candidates)
             (/= (vl-string-trim " \t\r\n" (car candidates)) "")
             (vl-file-directory-p (car candidates)))
      (setq path (car candidates)))
    (setq candidates (cdr candidates)))
  (cond
    (path path)
    (reg reg)
    (user (strcat user "\\Desktop"))
    (T "C:\\Users\\Public\\Desktop"))
)

(defun DEG:CFG-DEFAULT (key / a)
  (cond
    ((= key 'DO_KAYIT_PATH) (DEG:DESKTOP-PATH))
    ((setq a (assoc key *DEG_CFG_DEFAULTS*)) (cdr a))
    (T ""))
)

(defun DEG:VAL (code / o a)
  (cond
    ((setq o (assoc code *DEG_CODE_OVERRIDES*)) (cdr o))
    ((setq a (assoc code *DEG_CODEMAP*)) (caddr a))
  )
)

(defun DEG:SET (code val)
  (if (or (null val) (= (vl-string-trim " \t\r\n" val) ""))
    (setq *DEG_CODE_OVERRIDES* (DEG:ALIST-DEL *DEG_CODE_OVERRIDES* code))
    (setq *DEG_CODE_OVERRIDES* (DEG:ALIST-PUT *DEG_CODE_OVERRIDES* code val))
  )
  (DEG:VAL code)
)

(defun DEG:CFG-GET (key / a value)
  (cond
    ((setq a (assoc key *DEG_CFG_OVERRIDES*))
      (setq value (cdr a))
      (if (and (= key 'DO_KAYIT_PATH)
               (= (vl-string-trim " \t\r\n" value) ""))
        (DEG:CFG-DEFAULT key)
        value))
    (T (DEG:CFG-DEFAULT key))
  )
)

(defun DEG:CFG-SET (key val)
  (if (or (null val) (= (vl-string-trim " \t\r\n" val) ""))
    (setq *DEG_CFG_OVERRIDES* (DEG:ALIST-DEL *DEG_CFG_OVERRIDES* key))
    (setq *DEG_CFG_OVERRIDES* (DEG:ALIST-PUT *DEG_CFG_OVERRIDES* key val))
  )
)

(defun DEG:CFG-GETNUM (key / s)
  (setq s (DEG:CFG-GET key))
  (if (or (null s) (= (vl-string-trim " " s) ""))
    0.0
    (atof s)
  )
)

(defun DEG:CFG-BOOL (key / s)
  (setq s (strcase (vl-string-trim " \t\r\n" (DEG:CFG-GET key))))
  (not (member s '("" "0" "NIL" "FALSE" "HAYIR" "NO")))
)

(defun DEG:CFG-NUM-OR (key def / v)
  (setq v (DEG:CFG-GETNUM key))
  (if (> v 0.0) v def)
)


(defun DEG:PLAN-UNIT-SCALE (/ u)
  (setq u (strcase (vl-string-trim " \t\r\n" (DEG:CFG-GET 'PLAN_UNIT))))
  (cond
    ((= u "CM") 1.0)
    ;; Ayar tabani santimetredir: 1 cm = 10 mm = 0.01 m.
    ((or (= u "METRE") (= u "M")) 0.01)
    (T 10.0)
  )
)

(defun DEG:INSUNITS-PLAN-UNIT (/ units)
  (setq units (getvar "INSUNITS"))
  (cond
    ((= units 4) "mm")
    ((= units 5) "cm")
    ((= units 6) "metre")
    ;; Birimsiz veya desteklenmeyen birimde yanlis tahmin yapma.
    (T nil))
)

(defun DEG:AUTO-UNIT-FLOOR (value / integer)
  (setq integer (fix value))
  (if (> integer value) (1- integer) integer)
)

(defun DEG:AUTO-UNIT-INSUNITS-DECADE (units)
  (cond
    ((= units 4) -3)  ;; millimetre
    ((= units 5) -2)  ;; santimetre
    ((= units 6) 0)   ;; metre
    (T nil))
)

(defun DEG:AUTO-UNIT-SCALE-CLASS (units scale / sourceDecade scaleDecade planDecade)
  ;; INSERT olceginin onluk dilimini, INSUNITS'in metre karsiligiyla
  ;; birlestirir. Ornek (INSUNITS=mm): 2,5 -> mm; 0,378 -> cm.
  (setq sourceDecade (DEG:AUTO-UNIT-INSUNITS-DECADE units))
  (if (and (numberp sourceDecade)
           (numberp scale)
           (> scale 1e-12))
    (progn
      (setq scaleDecade
              (DEG:AUTO-UNIT-FLOOR
                (+ (/ (log scale) (log 10.0)) 1e-9))
            planDecade (- sourceDecade scaleDecade))
      (cond
        ((= planDecade -3) "mm")
        ((= planDecade -2) "cm")
        ((= planDecade 0) "metre")
        (T nil)))
    nil)
)

(defun DEG:AUTO-UNIT-XREF-BLOCK-P (blockName / record flags)
  (setq record (if blockName (tblsearch "BLOCK" blockName) nil)
        flags  (if record (cdr (assoc 70 record)) 0))
  (and (numberp flags) (/= 0 (logand flags 12)))
)

(defun DEG:AUTO-UNIT-VOTE-WINNER (votes / counts unit rec best bestCount tied)
  (setq counts '(("mm" . 0) ("cm" . 0) ("metre" . 0)))
  (foreach unit votes
    (if (setq rec (assoc unit counts))
      (setq counts
        (subst (cons unit (1+ (cdr rec))) rec counts))))
  (setq best nil
        bestCount 0
        tied nil)
  (foreach rec counts
    (cond
      ((> (cdr rec) bestCount)
        (setq best (car rec)
              bestCount (cdr rec)
              tied nil))
      ((and (> (cdr rec) 0) (= (cdr rec) bestCount))
        (setq tied T))))
  (if (and best (> bestCount 0) (not tied)) best nil)
)

(defun DEG:AUTO-PLAN-UNIT-FROM-BLOCK-SCALES
  (units / ss index ent data layout rawName rawKey nameRec effectiveName obj result
           sx sy scale unit sampleRec typeSamples typeRec typeUnit typeVotes nameCache)
  ;; Her benzersiz etkin block adi yalniz bir oy verir. Ayni turden en fazla
  ;; dokuz INSERT ornegi, tek aykiri kopyanin sonucu bozmasini engeller.
  (if (DEG:AUTO-UNIT-INSUNITS-DECADE units)
    (progn
      (setq ss (ssget "_X" '((0 . "INSERT")))
            index 0
            typeSamples nil
            nameCache nil)
      (if ss
        (while (< index (sslength ss))
          (setq ent     (ssname ss index)
                data    (if ent (entget ent) nil)
                layout  (if data (cdr (assoc 410 data)) nil)
                rawName (if data (cdr (assoc 2 data)) nil)
                rawKey  (if rawName (strcase rawName) nil))
          (if (and rawName
                   (or (null layout) (= (strcase layout) "MODEL"))
                   (not (DEG:AUTO-UNIT-XREF-BLOCK-P rawName)))
            (progn
              (setq nameRec (assoc rawKey nameCache))
              (if nameRec
                (setq effectiveName (cdr nameRec))
                (progn
                  (setq obj
                    (vl-catch-all-apply
                      'vlax-ename->vla-object (list ent)))
                  (setq result
                    (if (vl-catch-all-error-p obj)
                      nil
                      (vl-catch-all-apply 'deg-block-name (list obj))))
                  (setq effectiveName
                    (if (or (null result) (vl-catch-all-error-p result))
                      rawKey
                      (strcase result)))
                  (setq nameCache
                    (cons (cons rawKey effectiveName) nameCache))))
              (setq sampleRec (assoc effectiveName typeSamples))
              (if (or (null sampleRec) (< (length (cdr sampleRec)) 9))
                (progn
                  (setq sx (cdr (assoc 41 data))
                        sy (cdr (assoc 42 data)))
                  (if (not (numberp sx)) (setq sx 1.0))
                  (if (not (numberp sy)) (setq sy sx))
                  (setq sx (abs sx)
                        sy (abs sy)
                        scale (if (and (> sx 1e-12) (> sy 1e-12))
                                (sqrt (* sx sy))
                                nil)
                        unit (DEG:AUTO-UNIT-SCALE-CLASS units scale))
                  (if unit
                    (if sampleRec
                      (setq typeSamples
                        (subst
                          (cons effectiveName (cons unit (cdr sampleRec)))
                          sampleRec
                          typeSamples))
                      (setq typeSamples
                        (cons (list effectiveName unit) typeSamples)))))))
          )
          (setq index (1+ index))))
      (foreach typeRec typeSamples
        (setq typeUnit (DEG:AUTO-UNIT-VOTE-WINNER (cdr typeRec)))
        (if typeUnit (setq typeVotes (cons typeUnit typeVotes))))
      (DEG:AUTO-UNIT-VOTE-WINNER typeVotes))
    nil)
)

(setq *DEG_AUTO_PLAN_UNIT_DRAWING_KEY* nil)

(defun DEG:AUTO-PLAN-UNIT-DRAWING-KEY (/ prefix name units)
  (setq prefix (getvar "DWGPREFIX")
        name   (getvar "DWGNAME")
        units  (getvar "INSUNITS"))
  (strcase
    (strcat
      "BLOCK-SCALE-V2|"
      (if prefix prefix "")
      (if name name "")
      "|"
      (itoa units)))
)

(defun DEG:AUTO-PLAN-UNIT-FROM-INSUNITS (/ drawingKey units planUnit)
  (setq drawingKey (DEG:AUTO-PLAN-UNIT-DRAWING-KEY))
  (if (or (not (boundp '*DEG_AUTO_PLAN_UNIT_DRAWING_KEY*))
          (/= *DEG_AUTO_PLAN_UNIT_DRAWING_KEY* drawingKey))
    (progn
      (setq *DEG_AUTO_PLAN_UNIT_DRAWING_KEY* drawingKey
            units (getvar "INSUNITS")
            planUnit (DEG:AUTO-PLAN-UNIT-FROM-BLOCK-SCALES units))
      (if (null planUnit)
        (setq planUnit (DEG:INSUNITS-PLAN-UNIT)))
      (if planUnit
        (progn
          ;; Yalniz aktif DWG oturumunu guncelle; kullanici ayar dosyasina
          ;; yazma. DO acilirsa secili deger burada otomatik gorunur.
          (DEG:CFG-SET 'PLAN_UNIT planUnit)
          (DEG:TOL-REFRESH-DN-GLOBALS)))))
  (DEG:CFG-GET 'PLAN_UNIT)
)

(defun DEG:NUM->STR (n / s)
  (setq s (rtos n 2 8))
  (if (vl-string-search "." s)
    (progn
      (while (and (> (strlen s) 1) (= (substr s (strlen s) 1) "0"))
        (setq s (substr s 1 (1- (strlen s))))
      )
      (if (= (substr s (strlen s) 1) ".")
        (setq s (substr s 1 (1- (strlen s))))
      )
    )
  )
  s
)

(defun DEG:CFG-DK-NUM-OR (key def / v)
  (* (DEG:CFG-NUM-OR key def) (DEG:PLAN-UNIT-SCALE))
)


(defun DEG:CFG-DK-SIGNED-NUM-OR (key def / s)
  (setq s (DEG:CFG-GET key))
  (if (or (null s) (= (vl-string-trim " \t\r\n" s) ""))
    def
    (* (atof s) (DEG:PLAN-UNIT-SCALE))
  )
)

(defun DEGDO--dk-display (key / s v)
  (setq s (DEG:CFG-GET key))
  (if (or (null s) (= (vl-string-trim " \t\r\n" s) ""))
    ""
    (progn
      (setq v (atof s))
      (DEG:NUM->STR (* v (DEG:PLAN-UNIT-SCALE)))
    )
  )
)

(defun DEGDO--dk-store (tile / s sc)
  (setq s (DEGDO--trim (get_tile tile)))
  (if (= s "")
    ""
    (progn
      (setq sc (DEG:PLAN-UNIT-SCALE))
      (if (<= sc 0.0) (setq sc 1.0))
      (DEG:NUM->STR (/ (atof s) sc))
    )
  )
)

(defun DEG:CFG-TOL-NUM-OR (key def / v)
  (* (DEG:CFG-NUM-OR key def) (DEG:PLAN-UNIT-SCALE))
)

(defun DEGDO--tol-display (key)
  (DEGDO--dk-display key)
)

(defun DEGDO--tol-store (tile)
  (DEGDO--dk-store tile)
)

(defun DEG:TOL-REFRESH-DN-GLOBALS ()
  (setq DEGN-DEGA--TOL        (DEG:CFG-TOL-NUM-OR 'DN_CHAIN_TOL 5.0))
  (setq DEGN-DEGA--TOLBLOCK   (DEG:CFG-TOL-NUM-OR 'DN_BLOCK_TOL 1.0))
  (setq DEGN-DEGA--TOL_DOSEME (DEG:CFG-TOL-NUM-OR 'DN_DOSEME_TOL 10.0))
  T
)

(defun DEG:CFG-DDDZ-NUM-OR (key def / v)
  (* (DEG:CFG-NUM-OR key def) (DEG:PLAN-UNIT-SCALE))
)

(defun DEGDO--dddz-display (key)
  (DEGDO--dk-display key)
)

(defun DEGDO--dddz-display-or (key def)
  (if (= (vl-string-trim " \t\r\n" (DEG:CFG-GET key)) "")
    (DEG:NUM->STR (* def (DEG:PLAN-UNIT-SCALE)))
    (DEGDO--dddz-display key)
  )
)

(defun DEGDO--dddz-store (tile)
  (DEGDO--dk-store tile)
)

(defun DEG:CFG-DTT-NUM-OR (key def)
  (* (DEG:CFG-NUM-OR key def) (DEG:PLAN-UNIT-SCALE))
)

(defun DEGDO--dtt-display (key)
  (DEGDO--dk-display key)
)

(defun DEGDO--dtt-store (tile)
  (DEGDO--dk-store tile)
)

(defun DEG:CFG-ACI-OR (key def / v)
  (setq v (fix (DEG:CFG-GETNUM key)))
  (if (and (>= v 1) (<= v 255)) v def)
)

(defun DEG:CFG-LIST-GET (key / s out itm)
  (setq s (DEG:CFG-GET key))
  (setq out '())
  (foreach itm (degk--split-commas s)
    (setq itm (vl-string-trim " \t\r\n" itm))
    (if (/= itm "")
      (setq out (append out (list (norm-layer itm))))
    )
  )
  out
)

(defun DEG:DG-EXTRA-LAYERS ()
  (DEG:CFG-LIST-GET 'DG_EXTRA_LIGHTING_LAYERS)
)

(defun DEG:SELF-FILE ()
  (cond
    ((and (boundp '*DEG_SELF_FILE*) *DEG_SELF_FILE* (findfile *DEG_SELF_FILE*)) (findfile *DEG_SELF_FILE*))
    ((and (boundp '*DEG_SELF_FILE*) *DEG_SELF_FILE*) *DEG_SELF_FILE*)
    ((and (boundp '*load-truename*) *load-truename* (findfile *load-truename*)) (findfile *load-truename*))
    ((and (boundp '*load-truename*) *load-truename*) *load-truename*)
    ((and (boundp '*load-filename*) *load-filename* (findfile *load-filename*)) (findfile *load-filename*))
    ((and (boundp '*load-filename*) *load-filename*) *load-filename*)
    (T nil)
  )
)

(defun DEG:READ-ALL-LINES (fn / f line out)
  (if (and fn (setq f (open fn "r")))
    (progn
      (while (setq line (read-line f))
        (setq out (append out (list line)))
      )
      (close f)
      out
    )
  )
)

(defun DEG:WRITE-ALL-LINES (fn lines / f ok)
  (if (and fn (setq f (open fn "w")))
    (progn
      (foreach line lines
        (write-line line f)
      )
      (close f)
      (setq ok T)
    )
  )
  ok
)

(defun DEG:FILE-MATCHES-LINES-P (fn lines / current)
  (and fn
       (findfile fn)
       (setq current (DEG:READ-ALL-LINES fn))
       (equal current lines))
)

(defun DEG:SAFE-DELETE-FILE (fn / result)
  (if (and fn (findfile fn))
    (progn
      (setq result (vl-catch-all-apply 'vl-file-delete (list fn)))
      (and (not (vl-catch-all-error-p result)) (not (findfile fn))))
    T)
)

(defun DEG:WRITE-SETTINGS-FILE (fn lines / tmp bak hadOriginal backupReady result ok)
  (setq tmp (strcat fn ".tmp." (itoa (getvar "MILLISECS")))
        bak (strcat fn ".bak")
        hadOriginal (if (findfile fn) T nil))
  (DEG:SAFE-DELETE-FILE tmp)
  (if (DEG:WRITE-ALL-LINES tmp lines)
    (progn
      (DEG:SAFE-DELETE-FILE bak)
      (if hadOriginal
        (progn
          (setq result (vl-catch-all-apply 'vl-file-copy (list fn bak)))
          (setq backupReady
            (and (not (vl-catch-all-error-p result)) (findfile bak))))
        (setq backupReady T))
      ;; AutoCAD ve GstarCAD vl-file-rename icin farkli donus degerleri
      ;; verebildiginden basariyi dosyanin gercek icerigiyle dogrula.
      (if (or (not hadOriginal) backupReady)
        (progn
          (DEG:SAFE-DELETE-FILE fn)
          (setq result (vl-catch-all-apply 'vl-file-rename (list tmp fn)))
          (setq ok (DEG:FILE-MATCHES-LINES-P fn lines))))
      (if (not ok)
        (progn
          (DEG:SAFE-DELETE-FILE fn)
          (setq result (vl-catch-all-apply 'vl-file-copy (list tmp fn)))
          (setq ok (DEG:FILE-MATCHES-LINES-P fn lines))))
      (if (not ok)
        (progn
          (setq result (vl-catch-all-apply 'DEG:WRITE-ALL-LINES (list fn lines)))
          (setq ok (and (not (vl-catch-all-error-p result))
                        (DEG:FILE-MATCHES-LINES-P fn lines)))))
      (if (and (not ok) backupReady (findfile bak))
        (progn
          (DEG:SAFE-DELETE-FILE fn)
          (vl-catch-all-apply 'vl-file-copy (list bak fn))))
      (DEG:SAFE-DELETE-FILE tmp)))
  ok
)

(defun DEG:WRITE-PERSISTED-SETTINGS (/ fn lines ok)
  (setq fn (DEG:SETTINGS-FILE)
        lines
          (list
            ";; DEG DO settings - generated automatically."
            (strcat "(setq *DEG_PERSIST_CODE_OVERRIDES* "
                    (vl-prin1-to-string *DEG_CODE_OVERRIDES*) ")")
            (strcat "(setq *DEG_PERSIST_CFG_OVERRIDES* "
                    (vl-prin1-to-string *DEG_CFG_OVERRIDES*) ")")))
  (if fn (setq ok (DEG:WRITE-SETTINGS-FILE fn lines)))
  ok
)

(defun DEG:UPDATE-SELF-SETTINGS (/ fn tmp lines out line skip found ok)
  (setq fn (DEG:SELF-FILE))
  (setq lines (DEG:READ-ALL-LINES fn))
  (if lines
    (progn
      (foreach line lines
        (cond
          ((wcmatch line "*DEG_DO_PERSIST_BEGIN*")
           (setq skip T found T)
           (setq out
             (append out
               (list
                 line
                 (strcat "(setq *DEG_PERSIST_CODE_OVERRIDES* " (vl-prin1-to-string *DEG_CODE_OVERRIDES*) ")")
                 (strcat "(setq *DEG_PERSIST_CFG_OVERRIDES* " (vl-prin1-to-string *DEG_CFG_OVERRIDES*) ")")
               )
             )
           )
          )
          ((and skip (wcmatch line "*DEG_DO_PERSIST_END*"))
           (setq skip nil)
           (setq out (append out (list line)))
          )
          ((not skip)
           (setq out (append out (list line)))
          )
        )
      )
      (if (not found)
        (setq out
          (append out
            (list
              ";; DEG_DO_PERSIST_BEGIN"
              (strcat "(setq *DEG_PERSIST_CODE_OVERRIDES* " (vl-prin1-to-string *DEG_CODE_OVERRIDES*) ")")
              (strcat "(setq *DEG_PERSIST_CFG_OVERRIDES* " (vl-prin1-to-string *DEG_CFG_OVERRIDES*) ")")
              ";; DEG_DO_PERSIST_END"
            )
          )
        )
      )
      (setq tmp (strcat fn ".tmp"))
      (if (and tmp (DEG:WRITE-ALL-LINES tmp out))
        (progn
          (if (findfile fn) (vl-file-delete fn))
          (setq ok (vl-file-copy tmp fn))
          (if (findfile tmp) (vl-file-delete tmp))
          ok
        )
      )
    )
  )
)

(defun DEG:SAVE-SETTINGS (/ ok codeText cfgText codeResult cfgResult envOk)
  (DEG:SANITIZE-SETTINGS)
  (setq ok       (DEG:WRITE-PERSISTED-SETTINGS)
        codeText (vl-prin1-to-string *DEG_CODE_OVERRIDES*)
        cfgText  (vl-prin1-to-string *DEG_CFG_OVERRIDES*)
        codeResult (vl-catch-all-apply 'setenv (list "DEG_DO_CODE_OVERRIDES" codeText))
        cfgResult  (vl-catch-all-apply 'setenv (list "DEG_DO_CFG_OVERRIDES" cfgText))
        envOk
          (and (not (vl-catch-all-error-p codeResult))
               (not (vl-catch-all-error-p cfgResult))
               (= (if (getenv "DEG_DO_CODE_OVERRIDES") (getenv "DEG_DO_CODE_OVERRIDES") "") codeText)
               (= (if (getenv "DEG_DO_CFG_OVERRIDES") (getenv "DEG_DO_CFG_OVERRIDES") "") cfgText)))
  (vl-catch-all-apply 'setenv
    (list "DEG_DO_SETTINGS_FALLBACK" (if ok "0" "1")))
  (or ok envOk)
)

(defun DEG:SAFE-READ-SETTING (s env / r)
  (if (and s (/= s ""))
    (progn
      (setq r (vl-catch-all-apply 'read (list s)))
      (if (vl-catch-all-error-p r)
        (progn
          (if env (setenv env ""))
          nil
        )
        r
      )
    )
  )
)

(defun DEG:FILE-SYSTIME-SAFE (fn / result)
  (setq result (vl-catch-all-apply 'vl-file-systime (list fn)))
  (if (vl-catch-all-error-p result) nil result)
)

(defun DEG:SYSTIME-NEWER-P (a b / newer done)
  (while (and a b (not done))
    (cond
      ((> (car a) (car b)) (setq newer T done T))
      ((< (car a) (car b)) (setq newer nil done T))
      (T (setq a (cdr a) b (cdr b)))))
  newer
)

(defun DEG:NEWEST-SETTINGS-FILE (files / best bestTime fn tm)
  (foreach fn files
    (if (and fn (findfile fn))
      (progn
        (setq tm (DEG:FILE-SYSTIME-SAFE fn))
        (if (or (not best)
                (and tm (or (not bestTime) (DEG:SYSTIME-NEWER-P tm bestTime))))
          (setq best fn bestTime tm)))))
  best
)

(defun DEG:LOAD-SETTINGS (/ s fn loaded result candidates candidate envApplied)
  (setq fn (DEG:SETTINGS-FILE)
        candidates (cons fn (DEG:OLD-SETTINGS-FILES))
        candidate (DEG:NEWEST-SETTINGS-FILE candidates))
  ;; Eski ortak ProgramData kaydi ile kullanici profilindeki kayittan en yenisini al.
  (if candidate
    (progn
      (setq result (vl-catch-all-apply 'load (list candidate nil)))
      (if (not (vl-catch-all-error-p result)) (setq loaded T))))
  (if (boundp '*DEG_PERSIST_CODE_OVERRIDES*)
    (setq *DEG_CODE_OVERRIDES* *DEG_PERSIST_CODE_OVERRIDES*))
  (if (boundp '*DEG_PERSIST_CFG_OVERRIDES*)
    (setq *DEG_CFG_OVERRIDES* *DEG_PERSIST_CFG_OVERRIDES*))
  ;; setenv kaydi Windows/CAD kullanicisina ozeldir ve son basarili Kaydet'i tasir.
  ;; Ortak ya da eski bir dosyanin yeni sekmede bu degerleri ezmesine izin verme.
  (if (and (setq s (getenv "DEG_DO_CODE_OVERRIDES")) (/= s ""))
    (progn
      (setq *DEG_CODE_OVERRIDES* (DEG:SAFE-READ-SETTING s "DEG_DO_CODE_OVERRIDES")
            envApplied T)))
  (if (and (setq s (getenv "DEG_DO_CFG_OVERRIDES")) (/= s ""))
    (progn
      (setq *DEG_CFG_OVERRIDES* (DEG:SAFE-READ-SETTING s "DEG_DO_CFG_OVERRIDES")
            envApplied T)))
  (DEG:SANITIZE-SETTINGS)
  ;; Ilk acilista en yeni/eski kaydi yeni kullanici konumuna tasiyip iyilestir.
  (if (or envApplied
          (and loaded candidate fn (/= (strcase candidate) (strcase fn))))
    (DEG:WRITE-PERSISTED-SETTINGS))
)

(DEG:LOAD-SETTINGS)
(DEG:SANITIZE-SETTINGS)

;; DN Block eski 7 cm varsayilanini yeni 1 cm varsayilanina bir kez tasi.
;; Daha sonra kullanicinin elle girdigi 7 cm degeri aynen korunur.
(if (/= (DEG:CFG-GET 'MIG_DN_BLOCK_TOL_CM1) "1")
  (progn
    (if (and (assoc 'DN_BLOCK_TOL *DEG_CFG_OVERRIDES*)
             (equal
               (atof (cdr (assoc 'DN_BLOCK_TOL *DEG_CFG_OVERRIDES*)))
               7.0
               0.000001))
      (setq *DEG_CFG_OVERRIDES*
        (DEG:ALIST-DEL *DEG_CFG_OVERRIDES* 'DN_BLOCK_TOL))
    )
    (DEG:CFG-SET 'MIG_DN_BLOCK_TOL_CM1 "1")
  )
)

;; DK Yazi Y Ofset eski 70 cm varsayilanini yeni 90 cm varsayilanina tasi.
;; Farkli bir kullanici degeri kayitliysa aynen korunur.
(if (and (assoc 'DK_TEXT_OFFSET_Y *DEG_CFG_OVERRIDES*)
         (equal
           (atof (cdr (assoc 'DK_TEXT_OFFSET_Y *DEG_CFG_OVERRIDES*)))
           70.0
           0.000001))
  (setq *DEG_CFG_OVERRIDES*
    (DEG:ALIST-DEL *DEG_CFG_OVERRIDES* 'DK_TEXT_OFFSET_Y))
)

;; Ayni kat loop araliginin eski 500 cm varsayilanini yeni 0 cm
;; varsayilanina tasi. Farkli kullanici degerleri aynen korunur.
(if (and (assoc 'DK_NORMAL_GROUP_SPACING *DEG_CFG_OVERRIDES*)
         (equal
           (atof (cdr (assoc 'DK_NORMAL_GROUP_SPACING *DEG_CFG_OVERRIDES*)))
           500.0
           0.000001))
  (setq *DEG_CFG_OVERRIDES*
    (DEG:ALIST-DEL *DEG_CFG_OVERRIDES* 'DK_NORMAL_GROUP_SPACING))
)

;; Onceki varsayilan olculer kayitliysa yeni 70x40/8 varsayilanina gecir.
;; Bunlar disindaki kullanici degerlerine dokunulmaz.
(if (and (assoc 'DTT_RECT_WIDTH *DEG_CFG_OVERRIDES*)
         (assoc 'DTT_RECT_HEIGHT *DEG_CFG_OVERRIDES*)
         (or
           (and
             (equal (atof (cdr (assoc 'DTT_RECT_WIDTH *DEG_CFG_OVERRIDES*))) 40.0 0.000001)
             (equal (atof (cdr (assoc 'DTT_RECT_HEIGHT *DEG_CFG_OVERRIDES*))) 20.0 0.000001))
           (and
             (equal (atof (cdr (assoc 'DTT_RECT_WIDTH *DEG_CFG_OVERRIDES*))) 50.0 0.000001)
             (equal (atof (cdr (assoc 'DTT_RECT_HEIGHT *DEG_CFG_OVERRIDES*))) 30.0 0.000001))))
  (progn
    (setq *DEG_CFG_OVERRIDES* (DEG:ALIST-DEL *DEG_CFG_OVERRIDES* 'DTT_RECT_WIDTH))
    (setq *DEG_CFG_OVERRIDES* (DEG:ALIST-DEL *DEG_CFG_OVERRIDES* 'DTT_RECT_HEIGHT))
    (if (and (assoc 'DTT_ATT_TEXT_HEIGHT *DEG_CFG_OVERRIDES*)
             (equal (atof (cdr (assoc 'DTT_ATT_TEXT_HEIGHT *DEG_CFG_OVERRIDES*))) 4.0 0.000001))
      (setq *DEG_CFG_OVERRIDES* (DEG:ALIST-DEL *DEG_CFG_OVERRIDES* 'DTT_ATT_TEXT_HEIGHT))
    )
  )
)

;; ----------------------------
;; N2 (E_OK) bloklarýný tamamen yok saymak için yardýmcýlar (R312 ile ayný)
;; Not: "E_OK" kelimesi kullanýlmaz; N2 pattern'i esas alýnýr.
;; ----------------------------
(defun DEG:PT->LIST (pt)
  (cond
    ((= (type pt) 'LIST) pt)
    ((= (type pt) 'VARIANT) (DEG:PT->LIST (vlax-variant-value pt)))
    ((= (type pt) 'SAFEARRAY) (vlax-safearray->list pt))
    (T pt)
  )
)

(defun DEG:BLOCK-NAMES (blkObj / names n eff)
  (setq names '())
  (setq n (vl-catch-all-apply 'vla-get-Name (list blkObj)))
  (if (not (vl-catch-all-error-p n))
    (setq names (cons n names))
  )
  (setq eff (vl-catch-all-apply 'vla-get-EffectiveName (list blkObj)))
  (if (not (vl-catch-all-error-p eff))
    (setq names (cons eff names))
  )
  ;; deg-block-name varsa onu da ekle (bazý yerlerde EffectiveName dönüyor)
  (setq eff (vl-catch-all-apply 'deg-block-name (list blkObj)))
  (if (not (vl-catch-all-error-p eff))
    (setq names (cons eff names))
  )
  ;; deg-block-name-raw varsa onu da ekle
  (setq eff (vl-catch-all-apply 'deg-block-name-raw (list blkObj)))
  (if (not (vl-catch-all-error-p eff))
    (setq names (cons eff names))
  )
  (vl-remove nil names)
)

(defun DEG:RELAX-PATTERN (pat / p)
  ;; N2 pattern'inden daha gevþek bir eþleme üüretir (örn: "*E_OK_*" -> "*E_OK*")
  (setq p pat)
  (if (and p (= (type p) 'STR))
    (progn
      (while (vl-string-search "_*" p) (setq p (vl-string-subst "*" "_*" p)))
      (while (vl-string-search "*_" p) (setq p (vl-string-subst "*" "*_" p)))
    )
  )
  p
)

(defun DEG:IGNORE-BLOCK-OBJ? (blkObj / pat pat2 names nm hit nmU)
  ;; N2 (E_OK) bloklarý tamamen yok sayýlýr (N2 pattern'i esas alýnýr)
  (setq pat (DEG:VAL 'N2))
  (setq pat2 (DEG:RELAX-PATTERN pat))
  (setq names (DEG:BLOCK-NAMES blkObj))
  (setq hit nil)
  (foreach nm names
    (setq nmU (strcase nm))
    (if (or (wcmatch nmU pat)
            (and pat2 (wcmatch nmU pat2)))
      (setq hit T)
    )
  )
  hit
)

(defun DEG:SS-REMOVE-IGNORED-BLOCKS (ss / i e obj ss2)
  ;; Seçim setindeki N2 (E_OK) bloklarýný tamamen çýkarýr.
  (setq ss2 (ssadd))
  (if ss
    (progn
      (setq i 0)
      (while (< i (sslength ss))
        (setq e (ssname ss i))
        (if e
          (progn
            (setq obj (vlax-ename->vla-object e))
            (if (not (DEG:IGNORE-BLOCK-OBJ? obj))
              (ssadd e ss2)
            )
          )
        )
        (setq i (1+ i))
      )
    )
  )
  ss2
)

(defun DEG:SS-FILTER-BY-TYPE (ss typePat / i e ed ss2)
  (setq ss2 (ssadd))
  (if ss
    (progn
      (setq i 0)
      (while (< i (sslength ss))
        (setq e (ssname ss i)
              ed (if e (entget e)))
        (if (and ed (wcmatch (cdr (assoc 0 ed)) typePat))
          (ssadd e ss2)
        )
        (setq i (1+ i))
      )
    )
  )
  ss2
)

(defun DEG:SS-CONTAINS-ENAME? (ss ent / i found)
  (setq found nil)
  (if (and ss ent)
    (progn
      (setq i 0)
      (while (and (< i (sslength ss)) (not found))
        (if (= (ssname ss i) ent)
          (setq found T)
        )
        (setq i (1+ i))
      )
    )
  )
  found
)

(defun DEG:SS-LEN (ss / n)
  (if ss
    (progn
      (setq n (vl-catch-all-apply 'sslength (list ss)))
      (if (or (vl-catch-all-error-p n) (null n)) 0 n)
    )
    0
  )
)

(defun DEG:IGNORE-OBJ? (obj / on)
  ;; VLA objesi bir BlockReference ise ve N2'ye uyuyorsa yok say
  (setq on (vl-catch-all-apply 'vla-get-ObjectName (list obj)))
  (if (vl-catch-all-error-p on)
    nil
    (if (= on "AcDbBlockReference")
      (DEG:IGNORE-BLOCK-OBJ? obj)
      nil
    )
  )
)

(defun DEG:TYPE (code / a)
  (if (setq a (assoc code *DEG_CODEMAP*))
    (cadr a)
  )
)



(defun DEG:ENAME (x)
  (cond
    ((= (type x) 'ENAME) x)
    ((= (type x) 'VLA-OBJECT) (vlax-vla-object->ename x))
    ((and (= (type x) 'STR) (handent x)) (handent x))
    (t nil)
  )
)

(defun DEG:VLA (x / e)
  (setq e (DEG:ENAME x))
  (if e (vlax-ename->vla-object e))
)

(defun DEG:ENAMES (lst)
  (vl-remove nil (mapcar 'DEG:ENAME lst))
)

(defun degk--split-commas (s / txt p part out)
  (setq txt (vl-string-trim " \t\r\n" (if s s "")))
  (while (/= txt "")
    (setq p (vl-string-search "," txt))
    (if p
      (progn
        (setq part (substr txt 1 p))
        (setq txt  (substr txt (+ p 2)))
      )
      (progn
        (setq part txt)
        (setq txt  "")
      )
    )
    (setq part (vl-string-trim " \t\r\n" part))
    (if (/= part "") (setq out (append out (list part))))
  )
  out
)

(defun DEG:SPLIT-LAYERS (s / txt p part out)
  (setq txt (vl-string-trim " \t\r\n" (if s s "")))
  (while (/= txt "")
    (setq p (vl-string-search "," txt))
    (if p
      (progn
        (setq part (substr txt 1 p))
        (setq txt  (substr txt (+ p 2)))
      )
      (progn
        (setq part txt)
        (setq txt  "")
      )
    )
    (setq part (norm-layer (vl-string-trim " \t\r\n" part)))
    (if (/= part "") (setq out (append out (list part))))
  )
  out
)

(defun DEG:VAL-LIST (code)
  (DEG:SPLIT-LAYERS (DEG:VAL code))
)

(defun DEG:CFG-LIST (key)
  (DEG:SPLIT-LAYERS (DEG:CFG-GET key))
)

(defun DEG:VALS (codes / out)
  (foreach c codes
    (setq out (append out (DEG:VAL-LIST c)))
  )
  out
)

(defun DEGN-DN--cfg-list-or-codes (key codes / raw)
  (setq raw (vl-string-trim " \t\r\n" (DEG:CFG-GET key)))
  (if (/= raw "")
    (DEG:SPLIT-LAYERS raw)
    (DEG:VALS codes)
  )
)

(defun DEGN-DN--cfg-list-or-mix (key codes extra / raw out)
  (setq raw (vl-string-trim " \t\r\n" (DEG:CFG-GET key)))
  (if (/= raw "")
    (DEG:SPLIT-LAYERS raw)
    (append (DEG:VALS codes) (DEG:SPLIT-LAYERS extra))
  )
)

(defun DEGN-DN--match-list-p (s lst / hit itm)
  (setq hit nil)
  (foreach itm lst
    (if (and itm (/= itm "") (deg-wcmatch s itm))
      (setq hit T)
    )
  )
  hit
)

(defun DEG:LAYER-IN-CODES? (layer codes)
  (member (norm-layer layer) (DEG:VALS codes))
)


(defun DEG:TOL (code / a)
  (if (setq a (assoc code *DEG_TOL_CODES*))
    (caddr a)
  )
)


(defun deg-fire-flasher-filter (plLayer blkName blkLayer / L B BL)
  (setq L  (strcase plLayer)
        B  (strcase blkName)
        BL (strcase blkLayer))
  (cond
    ((DEGN-DN--match-list-p B (DEGN-DN--cfg-list-or-codes 'DN_FILTER_IGNORE_BLOCKS '(N1 K2 N2))) nil)

    ((DEGN-DN--match-list-p L (DEGN-DN--cfg-list-or-codes 'DN_FILTER_FIRE_LAYER_PATTERNS '(K11 K10 K9)))
     (not (DEGN-DN--match-list-p B (DEGN-DN--cfg-list-or-codes 'DN_FILTER_FIRE_BLOCK_EXCLUDES '(K13 K14 K15))))
    )

    ((DEGN-DN--match-list-p L (DEGN-DN--cfg-list-or-codes 'DN_FILTER_CO_LAYER_PATTERNS '(K8)))
     (DEGN-DN--match-list-p B (DEGN-DN--cfg-list-or-codes 'DN_FILTER_CO_BLOCKS '(K7)))
    )

    ((DEGN-DN--match-list-p L (DEGN-DN--cfg-list-or-codes 'DN_FILTER_FLASOR_LAYERS '(K1)))
     (DEGN-DN--match-list-p B (DEGN-DN--cfg-list-or-codes 'DN_FILTER_FLASOR_BLOCKS '(K12)))
    )

    ((DEGN-DN--match-list-p L (DEGN-DN--cfg-list-or-codes 'DN_FILTER_SOUND_LAYER_PATTERNS '(K13 K14 K15)))
     (DEGN-DN--match-list-p B (DEGN-DN--cfg-list-or-codes 'DN_FILTER_SOUND_BLOCK_PATTERNS '(K13 K14 K15)))
    )

    (T T)
  )
)




(setq *deg-grid-size* 2000.0) ;; hücre boyutu (ççizim birimi ile)

(defun deg--ifloor (x / i)
  (setq i (fix x))
  (if (and (< x 0.0) (/= x i)) (1- i) i)
)

(defun deg-cellkey (ix iy /) (list ix iy))

(defun deg-pt->cellkey (pt size / ix iy)
  (setq ix (deg--ifloor (/ (car pt) size)))
  (setq iy (deg--ifloor (/ (cadr pt) size)))
  (deg-cellkey ix iy)
)

(defun deg-grid-get (grid key / a)
  (setq a (assoc key grid))
  (if a (cdr a) nil)
)

(defun deg-grid-put (grid key obj / a lst)
  (setq a (assoc key grid))
  (if a
    (progn
      (setq lst (cdr a))
      (subst (cons key (cons obj lst)) a grid)
    )
    (cons (cons key (list obj)) grid)
  )
)

(defun deg-build-ref-grid (refInfos size / grid inf robj mn mx mnpt mxpt
                                   x0 x1 y0 y1 ix0 ix1 iy0 iy1 ix iy key)
  (setq grid '())
  (foreach inf refInfos
    (setq robj (car inf))
    (if (and robj (vlax-curve-p robj))
      (progn
        (vla-getBoundingBox robj 'mn 'mx)
        (setq mnpt (vlax-safearray->list mn)
              mxpt (vlax-safearray->list mx))
        (setq x0 (car mnpt) y0 (cadr mnpt)
              x1 (car mxpt) y1 (cadr mxpt))
        (setq ix0 (deg--ifloor (/ x0 size))
              ix1 (deg--ifloor (/ x1 size))
              iy0 (deg--ifloor (/ y0 size))
              iy1 (deg--ifloor (/ y1 size)))
        (setq ix ix0)
        (while (<= ix ix1)
          (setq iy iy0)
          (while (<= iy iy1)
            (setq key (deg-cellkey ix iy))
            (setq grid (deg-grid-put grid key robj))
            (setq iy (1+ iy))
          )
          (setq ix (1+ ix))
        )
      )
    )
  )
  grid
)

(defun deg-grid-candidates (grid pt size / key ix iy dx dy res lst h seen)
  (setq key (deg-pt->cellkey pt size))
  (setq ix (car key) iy (cadr key))
  (setq res '() seen '())
  (setq dx -1)
  (while (<= dx 1)
    (setq dy -1)
    (while (<= dy 1)
      (setq lst (deg-grid-get grid (deg-cellkey (+ ix dx) (+ iy dy))))
      (foreach obj lst
        (setq h (vlax-get obj 'Handle))
        (if (not (member h seen))
          (progn
            (setq seen (cons h seen))
            (setq res  (cons obj res))
          )
        )
      )
      (setq dy (1+ dy))
    )
    (setq dx (1+ dx))
  )
  res
)

(defun deg-touch-cp (plObj blkObj tol / insPt cp d)
  (setq insPt (deg-get-inspt blkObj))
  (setq cp    (deg-safe-closest-point plObj insPt))
  (setq d     (distance insPt cp))
  (if (<= d tol) (list cp d) nil)
)



(defun draw-tol-circle (pt r / )
  (entmake
    (list
      '(0 . "CIRCLE")
      (cons 10 pt)
      (cons 40 r)
      '(62 . 1) ; red
    )
  )
)

(defun draw-tol-hit-circle (pt r / )
  (entmake
    (list
      '(0 . "CIRCLE")
      (cons 10 pt)
      (cons 40 r)
      '(62 . 3) ; göreen
    )
  )
)



(defun draw-tol-circle (pt r / )
  (entmake
    (list
      '(0 . "CIRCLE")
      (cons 10 pt)
      (cons 40 r)
      '(62 . 1) ; red
    )
  )
)


(defun vlax-curve-p (obj)
  (and obj
       (vlax-method-applicable-p obj 'GetClosestPointTo)
  )
)

(defun DEG-ENSURE-LAYER (layName layColor / layObj)
  (if (not (tblsearch "LAYER" layName))
    (entmake
      (list
        '(0 . "LAYER")
        '(100 . "AcDbSymbolTableRecord")
        '(100 . "AcDbLayerTableRecord")
        (cons 2 layName)
        (cons 62 layColor)
        '(70 . 0)
      )
    )
    (progn
      (setq layObj (tblobjname "LAYER" layName))
      (entmod
        (subst (cons 62 layColor)
               (assoc 62 (entget layObj))
               (entget layObj)
        )
      )
    )
  )
  layName
)

(setq *DEG-BLOCK-WRITTEN* *DEG-BLOCK-WRITTEN*)

(defun DEG-DGT--app () "DEG_DGT_RESET")

(defun DEG-DGT--regapp (/ app)
  (setq app (DEG-DGT--app))
  (if (not (tblsearch "APPID" app)) (regapp app))
  app
)

(defun DEG-DGT--xdata-strings (e / xd rec appData out item)
  (setq xd (assoc -3 (entget e (list (DEG-DGT--app)))))
  (setq appData nil)
  (cond
    ((and xd (listp (cadr xd)) (= (caadr xd) (DEG-DGT--app)))
      (setq appData (cadr xd)))
    ((and xd (listp (cdr xd)) (listp (car (cdr xd))))
      (setq rec (car (cdr xd)))
      (if (= (car rec) (DEG-DGT--app)) (setq appData rec)))
  )
  (setq out nil)
  (if appData
    (foreach item (cdr appData)
      (if (and (listp item) (= (car item) 1000))
        (setq out (append out (list (cdr item))))
      )
    )
  )
  out
)

(defun DEG-DGT--xdata-kind (e / vals)
  (setq vals (DEG-DGT--xdata-strings e))
  (if vals (car vals) nil)
)

(defun DEG-DGT--mark-xdata (e kind vals / data)
  (if e
    (progn
      (DEG-DGT--regapp)
      (setq data (append (list (DEG-DGT--app) (cons 1000 kind))
                         (mapcar '(lambda (s) (cons 1000 (if s s ""))) vals)))
      (vl-catch-all-apply 'entmod (list (append (entget e) (list (list -3 data)))))
      (vl-catch-all-apply 'entupd (list e))
    )
  )
  e
)


(defun DEG-DGT--clear-xdata (e / ed newed x3 app rec)
  (if e
    (progn
      (setq app (DEG-DGT--app))
      (setq ed (entget e '("*")))
      (setq newed nil)
      (foreach x3 ed
        (setq rec (if (and (= (car x3) -3) (listp (cadr x3))) (cadr x3) nil))
        (if (and rec (= (car rec) app))
          (setq newed newed)
          (setq newed (append newed (list x3)))
        )
      )
      (if (and newed (/= (length newed) (length ed)))
        (progn
          (vl-catch-all-apply 'entmod (list newed))
          (vl-catch-all-apply 'entupd (list e))
        )
      )
    )
  )
  e
)
(defun DEG-DGT--mark-color (x / e ed c62 c420 c430 kind)
  (setq e (deg--to-ename x))
  (setq kind (if e (DEG-DGT--xdata-kind e)))
  (if (and e (not (and kind (= kind "COLOR"))))
    (progn
      (setq ed (entget e))
      (setq c62  (assoc 62 ed))
      (setq c420 (assoc 420 ed))
      (setq c430 (assoc 430 ed))
      (DEG-DGT--mark-xdata e "COLOR"
        (list
          (if c62 (itoa (cdr c62)) "")
          (if c420 (itoa (cdr c420)) "")
          (if c430 (cdr c430) "")
        )
      )
    )
  )
  e
)

(defun DEG-DGT--mark-circle (e / kind)
  (setq kind (if e (DEG-DGT--xdata-kind e)))
  (if (and e (not (and kind (= kind "CIRCLE"))))
    (DEG-DGT--mark-xdata e "CIRCLE" nil)
  )
  e
)

(defun DEG-DGT--remove-codes (ed codes / out p)
  (setq out nil)
  (foreach p ed
    (if (not (member (car p) codes))
      (setq out (append out (list p)))
    )
  )
  out
)

(defun DEG-DGT--insert-after-code (ed code ins / out done p)
  (setq out nil done nil)
  (foreach p ed
    (setq out (append out (list p)))
    (if (and (not done) (= (car p) code))
      (progn
        (setq out (append out ins))
        (setq done T)
      )
    )
  )
  (if done out (append out ins))
)

(defun DEG-DGT--restore-color (e c62s c420s c430s / ed add c62v c420v)
  (if e
    (progn
      (setq ed (entget e))
      (setq ed (DEG-DGT--remove-codes ed '(62 420 430)))
      (setq add nil)
      (if (and c62s (/= c62s ""))
        (setq c62v (atoi c62s))
        (setq c62v 256)
      )
      (setq add (append add (list (cons 62 c62v))))
      (if (and c420s (/= c420s ""))
        (progn
          (setq c420v (atoi c420s))
          (setq add (append add (list (cons 420 c420v))))
        )
      )
      (if (and c430s (/= c430s ""))
        (setq add (append add (list (cons 430 c430s))))
      )
      (setq ed (DEG-DGT--insert-after-code ed 8 add))
      (vl-catch-all-apply 'entmod (list ed))
      (vl-catch-all-apply 'entupd (list e))
    )
  )
  e
)

(defun DEG-DGT--make-circle (pt rad layerName col / e)
  (setq e
    (entmakex
      (list
        (cons 0 "CIRCLE")
        (cons 8 layerName)
        (cons 62 col)
        (cons 10 pt)
        (cons 40 rad)
      )
    )
  )
  (DEG-DGT--mark-circle e)
  e
)

(defun DEG-DGT--set-color-aci (x aci / e o)
  (setq e (deg--to-ename x))
  (if e
    (progn
      (DEG-DGT--mark-color e)
      (setq o (vlax-ename->vla-object e))
      (if o
        (vl-catch-all-apply
          '(lambda ()
             (if (vlax-property-available-p o 'Color)
               (vla-put-Color o aci)
             )
           )
          nil
        )
      )
    )
  )
  e
)

(defun DEG-DGT-RESET (/ ss i e vals kind c62s c420s c430s lay delLayers resetCnt delCnt)
  (vl-load-com)
  (DEG-DGT--regapp)
  (setq resetCnt 0 delCnt 0)
  (setq ss (ssget "_X" '((0 . "LINE,LWPOLYLINE,POLYLINE"))))
  (if ss
    (progn
      (setq i 0)
      (while (< i (sslength ss))
        (setq e (ssname ss i))
        (setq vals (DEG-DGT--xdata-strings e))
        (if (and vals (= (car vals) "COLOR"))
          (progn
            (setq c62s  (cadr vals))
            (setq c420s (caddr vals))
            (setq c430s (cadddr vals))
            (DEG-DGT--restore-color e c62s c420s c430s)
            (DEG-DGT--clear-xdata e)
            (setq resetCnt (1+ resetCnt))
          )
        )
        (setq i (1+ i))
      )
    )
  )
  (setq delLayers (mapcar 'norm-layer (list (DEG:TOL 'Q1) (DEG:TOL 'Q2) (DEG:VAL 'R2))))
  (setq ss (ssget "_X" '((0 . "CIRCLE"))))
  (if ss
    (progn
      (setq i 0)
      (while (< i (sslength ss))
        (setq e (ssname ss i))
        (setq kind (DEG-DGT--xdata-kind e))
        (setq lay (norm-layer (cdr (assoc 8 (entget e)))))
        (if (or (and kind (= kind "CIRCLE")) (member lay delLayers))
          (progn
            (entdel e)
            (setq delCnt (1+ delCnt))
          )
        )
        (setq i (1+ i))
      )
    )
  )
  (DEG:WIN-MESSAGE (strcat "DGT reset tamamlandi.\nPolyline renkleri: " (itoa resetCnt) "\nSilinen cember: " (itoa delCnt)))
  (princ)
)

(defun color-red (plineList / aci)
  (setq aci (DEG:CFG-ACI-OR 'DGT_CHAIN_COLOR 1))
  (foreach p plineList
    (DEG-DGT--set-color-aci p aci)
  )
)

(defun handle-in-list? (h lst)
  (if (member h lst) T nil)
)


(defun deg-endpoint-touch? (plObj blkObj tol / sp ep ins)
  (setq sp  (vlax-curve-getStartPoint plObj))
  (setq ep  (vlax-curve-getEndPoint   plObj))
  (setq ins (deg-get-inspt blkObj))
  (and ins
       (or (< (distance sp ins) tol)
           (< (distance ep ins) tol)))
)

(defun deg-get-inspt (objOrPt / res v curvePt)
  (cond
    ((and (listp objOrPt) (>= (length objOrPt) 2))
      (deg-pt3 objOrPt)
    )
    (T
      (setq res (vl-catch-all-apply 'vlax-get-property (list objOrPt 'InsertionPoint)))
      (if (vl-catch-all-error-p res)
        (cond
          ((and (boundp '*degForceRefPt*)
                (deg-pt3 *degForceRefPt*))
            (deg-pt3 *degForceRefPt*))
          ((= (type objOrPt) 'VLA-OBJECT)
            (setq curvePt
              (vl-catch-all-apply
                (read "vlax-curve-getStartPoint")
                (list objOrPt)))
            (if (vl-catch-all-error-p curvePt)
              nil
              (deg-pt3 curvePt)))
          (T nil))
        (progn
          (setq v (if (= (type res) 'variant) (vlax-variant-value res) res))
          (cond
            ((= (type v) 'safearray) (deg-pt3 (vlax-safearray->list v)))
            ((listp v) (deg-pt3 v))
            (T nil)
          )
        )
      )
    )
  )
)

(defun vlax-safearray-p (x)
  (eq (type x) 'safearray)
)


(defun deg-pt3 (pt / v)
  (cond
    ((null pt) nil)
    ((= (type pt) 'VARIANT) (deg-pt3 (vlax-variant-value pt)))
    ((= (type pt) 'SAFEARRAY) (deg-pt3 (vlax-safearray->list pt)))
    ((and (listp pt) (>= (length pt) 3)
          (numberp (car pt)) (numberp (cadr pt)) (numberp (caddr pt)))
      (list (car pt) (cadr pt) (caddr pt)))
    ((and (listp pt) (= (length pt) 2)
          (numberp (car pt)) (numberp (cadr pt)))
      (list (car pt) (cadr pt) 0.0))
    (T nil)
  )
)

(defun deg-safe-closest-point (crv pt / p res)
  (setq p (deg-pt3 pt))
  (if (and crv p)
    (progn
      (setq res (vl-catch-all-apply (read "vlax-curve-getClosestPointTo") (list crv p)))
      (if (vl-catch-all-error-p res)
        nil
        (deg-pt3 res)
      )
    )
    nil
  )
)

(defun deg-safe-dist-at-point (crv pt / cp res)
  (setq cp (deg-safe-closest-point crv pt))
  (if (and crv cp)
    (progn
      (setq res (vl-catch-all-apply (read "vlax-curve-getDistAtPoint") (list crv cp)))
      (if (and (not (vl-catch-all-error-p res)) (numberp res))
        res
        0.0
      )
    )
    0.0
  )
)

(defun deg-key (s /)
  (strcase (vl-string-translate "Ýý" "Ii" (if s s "")))
)

(defun norm-layer (s /)
  (deg-key s)
)

(defun deg-eq (a b)
  (= (deg-key a) (deg-key b))
)

(defun deg-member (x lst / k)
  (setq k (deg-key x))
  (while (and lst (/= k (deg-key (car lst))))
    (setq lst (cdr lst))
  )
  (if lst T nil)
)

(defun deg-wcmatch (s pat)
  (wcmatch (deg-key s) (deg-key pat))
)

(defun get-entity-text (obj / res)
  (setq res (vl-catch-all-apply 'vlax-get-property (list obj 'TextString)))
  (if (vl-catch-all-error-p res)
    (setq res (vl-catch-all-apply 'vlax-get-property (list obj 'Contents)))
  )
  (if (vl-catch-all-error-p res)
    nil
    res
  )
)

(defun project-point-on-curve (crv pt / cp)
  (setq cp (deg-safe-closest-point crv pt))
  cp
)

(defun distance-along-poly (crv pt / projPt)
  (setq projPt (deg-safe-closest-point crv pt))
  (deg-safe-dist-at-point crv projPt)
)

(defun connection-point (o1 o2 tol / res lst p1a p1b p2a p2b hit)
  (setq res
    (vl-catch-all-apply
      (function
        (lambda ()
          (vlax-invoke o1 'IntersectWith o2 0)))))
  (if (not (vl-catch-all-error-p res))
    (progn
      (setq lst (vl-catch-all-apply 'DEG:PT->LIST (list res)))
      (if (vl-catch-all-error-p lst) (setq lst nil))
      (if (and (listp lst) (>= (length lst) 2))
        (setq hit (list (nth 0 lst) (nth 1 lst) 0.0))
      )
    )
  )
  (if hit
    hit
    (progn
      (setq p1a (vlax-curve-getStartPoint o1))
      (setq p1b (vlax-curve-getEndPoint   o1))
      (setq p2a (vlax-curve-getStartPoint o2))
      (setq p2b (vlax-curve-getEndPoint   o2))
      (cond
        ((< (distance p1a p2a) tol) p1a)
        ((< (distance p1a p2b) tol) p1a)
        ((< (distance p1b p2a) tol) p1b)
        ((< (distance p1b p2b) tol) p1b)
        (T nil)
      )
    )
  )
)

(defun deg-endpoint-pair-connection (a1 a2 b1 b2 tol / pairs pair best bestD d)
  (setq pairs (list (list a1 b1) (list a1 b2) (list a2 b1) (list a2 b2))
        best nil
        bestD nil)
  (foreach pair pairs
    (if (and (deg-pt3 (car pair)) (deg-pt3 (cadr pair)))
      (progn
        (setq d (distance (deg-pt3 (car pair)) (deg-pt3 (cadr pair))))
        (if (and (<= d tol) (or (null bestD) (< d bestD)))
          (setq bestD d
                best
                  (list
                    (/ (+ (car (car pair)) (car (cadr pair))) 2.0)
                    (/ (+ (cadr (car pair)) (cadr (cadr pair))) 2.0)
                    (/ (+ (if (caddr (car pair)) (caddr (car pair)) 0.0)
                          (if (caddr (cadr pair)) (caddr (cadr pair)) 0.0))
                       2.0)))
        )
      )
    )
  )
  best
)

(defun deg-curves-endpoint-connection (o1 o2 tol / a1 a2 b1 b2)
  (if (and o1 o2)
    (progn
      (setq a1 (vl-catch-all-apply 'vlax-curve-getStartPoint (list o1))
            a2 (vl-catch-all-apply 'vlax-curve-getEndPoint   (list o1))
            b1 (vl-catch-all-apply 'vlax-curve-getStartPoint (list o2))
            b2 (vl-catch-all-apply 'vlax-curve-getEndPoint   (list o2)))
      (if (or (vl-catch-all-error-p a1)
              (vl-catch-all-error-p a2)
              (vl-catch-all-error-p b1)
              (vl-catch-all-error-p b2))
        nil
        (deg-endpoint-pair-connection a1 a2 b1 b2 tol)
      )
    )
  )
)

(defun ref-find-info (robj infos / h r)
  (setq h (vlax-get robj 'Handle))
  (setq r nil)
  (while (and infos (not r))
    (if (= (vlax-get (caar infos) 'Handle) h)
      (setq r (car infos))
      (setq infos (cdr infos))
    )
  )
  r
)

(defun in-ref-infos? (o infos / h)
  (setq h (vlax-get o 'Handle))
  (if (vl-some '(lambda (inf) (= (vlax-get (car inf) 'Handle) h)) infos) T nil)
)

(defun deg-doseme-inis-block-p (blkObj / nm)
  (setq nm
    (if (= (type blkObj) 'VLA-OBJECT)
      (deg-block-name blkObj)
      ""))
  (or (= nm (DEG:VAL 'M1))
      (deg-wcmatch nm (DEG:VAL 'M2))
      (deg-wcmatch nm (DEG:VAL 'M3))
      (deg-wcmatch nm (DEG:VAL 'M4)))
)

(defun bbox-test-points (blkObj / ins res minVar maxVar minPt maxPt x1 y1 x2 y2 xc yc pts i f)
  (setq pts '())
  (setq ins (deg-get-inspt blkObj))
  (if ins (setq pts (cons (deg-pt3 ins) pts)))
  (setq res (vl-catch-all-apply 'vla-getBoundingBox (list blkObj 'minVar 'maxVar)))
  (if (not (vl-catch-all-error-p res))
    (progn
      (setq minPt (DEG:PT->LIST minVar)
            maxPt (DEG:PT->LIST maxVar)
            x1 (car minPt)
            y1 (cadr minPt)
            x2 (car maxPt)
            y2 (cadr maxPt)
            xc (/ (+ x1 x2) 2.0)
            yc (/ (+ y1 y2) 2.0))
      (setq pts
        (append
          (list
            (list x1 y1 0.0) (list x1 y2 0.0) (list x2 y1 0.0) (list x2 y2 0.0)
            (list xc yc 0.0) (list xc y1 0.0) (list xc y2 0.0) (list x1 yc 0.0) (list x2 yc 0.0)
          )
          pts
        )
      )
      (setq i 1)
      (while (< i 8)
        (setq f (/ i 8.0))
        (setq pts
          (append
            (list
              (list (+ x1 (* (- x2 x1) f)) y1 0.0)
              (list (+ x1 (* (- x2 x1) f)) y2 0.0)
              (list x1 (+ y1 (* (- y2 y1) f)) 0.0)
              (list x2 (+ y1 (* (- y2 y1) f)) 0.0)
            )
            pts
          )
        )
        (setq i (1+ i))
      )
    )
  )
  pts
)
(defun poly-touch-block? (plObj blkObj tol / insPt cpt)
  (setq insPt (deg-get-inspt blkObj))
  (if (and plObj insPt)
    (progn
      (setq cpt (deg-safe-closest-point plObj insPt))
      (or
        (and (deg-pt3 insPt)
             (deg-pt3 cpt)
             (< (distance (deg-pt3 insPt) (deg-pt3 cpt)) tol))
        (and (deg-doseme-inis-block-p blkObj)
             (block-ref-contact-point plObj blkObj tol))
      )
    )
    nil
  )
)

(defun deg-poly-touch-block-base-p (plObj blkObj tol / insPt cpt)
  (setq insPt (deg-get-inspt blkObj))
  (if (and plObj (deg-pt3 insPt))
    (progn
      (setq cpt (deg-safe-closest-point plObj insPt))
      (and
        (deg-pt3 cpt)
        (< (distance (deg-pt3 insPt) (deg-pt3 cpt)) tol)))
    nil)
)



(defun deg-ss-blocks-touching-poly (plObj ss tol excludeObj / res i ent obj nm hEx)
  (setq res '())
  (setq hEx (if excludeObj (vlax-get excludeObj 'Handle) ""))
  (if (and plObj (wcmatch (deg-norm (vlax-get plObj 'Layer)) "*KIT*"))
    (progn (setq ss nil))
  )
  (if (and plObj ss)
    (progn
      (setq i 0)
      (while (< i (sslength ss))
        (setq ent (ssname ss i))
        (if ent
          (progn
            (setq obj (vlax-ename->vla-object ent))
            (if (and obj (/= (vlax-get obj 'Handle) hEx))
              (progn
                (setq nm (deg-block-name obj))
                (if (and nm (wcmatch nm "E_*")
                         (deg-poly-touch-block-base-p plObj obj tol)
                         (/= (strcase nm) (DEG:VAL 'P1)))
                  (setq res (cons obj res))
                )
              )
            )
          )
        )
        (setq i (1+ i))
      )
    )
  )
  (reverse res)
)

(defun deg-uniq-vla-by-handle (lst / res seen h o)
  (setq res '() seen '())
  (foreach o lst
    (if o
      (progn
        (setq h (vlax-get o 'Handle))
        (if (and h (not (member h seen)))
          (progn
            (setq seen (cons h seen))
            (setq res  (cons o res))
          )
        )
      )
    )
  )
  (reverse res)
)

(defun deg-block-tol (baseTol blkObj / dosemeTol)
  (if (and blkObj (deg-doseme-inis-block-p blkObj))
    (progn
      (setq dosemeTol (DEG:CFG-TOL-NUM-OR 'DN_DOSEME_TOL 10.0))
      (if (> dosemeTol baseTol) dosemeTol baseTol)
    )
    baseTol
  )
)



(defun deg-make-circle (pt rad / layerName col)
  (setq pt  (deg-pt3 pt))
  (setq rad (if (and (numberp rad) (> rad 0.0)) rad 7.0))
  (if (not pt)
    nil
    (progn
      (if (<= rad 7.0)
        (progn
          (setq layerName (DEG:TOL 'Q1))
          (setq col (DEG:CFG-ACI-OR 'DGT_TOL_SMALL_COLOR 2))
        )
        (progn
          (setq layerName (DEG:TOL 'Q2))
          (setq col (DEG:CFG-ACI-OR 'DGT_TOL_BIG_COLOR 3))
        )
      )
      (deg-ensure-layer layerName col)
      (DEG-DGT--make-circle pt rad layerName col)
    )
  )
)

(defun get-sembol-adi-from-block (blkObj / attList att tag val sym adet n numstr idx ch)
  (setq sym   nil
        adet  nil)
  (if (= :vlax-true (vla-get-HasAttributes blkObj))
    (progn
      (setq attList (vlax-invoke blkObj 'GetAttributes))
      (foreach att attList
        (setq tag (strcase (vla-get-TagString att)))
        (setq val (vla-get-TextString att))
        (cond
          ((or (= tag "SEMBOL_ADI") (= tag "SEMBOL ADI"))
           (setq sym val)
          )
          ((= tag "ADET")
           (setq adet val)
          )
        )
      )
    )
  )
  (if sym
    (progn
      (setq numstr "")
      (if adet
        (progn
          (setq idx 1)

          (while (<= idx (strlen adet))
            (setq ch (substr adet idx 1))
            (if (and (>= (ascii ch) 48) (<= (ascii ch) 57))
              (setq numstr (strcat numstr ch))
            )
            (setq idx (1+ idx))
          )
        )
      )
      (setq n (if (> (strlen numstr) 0) (atoi numstr) 0))
      (if (<= n 0) (setq n 1))
      (list (cons sym n))
    )
    '()
  )
)

(defun get-adet-from-block (blkObj / attList att tag val numstr idx ch n)
  (setq n 0)
  (if (= :vlax-true (vla-get-HasAttributes blkObj))
    (progn
      (setq attList (vlax-invoke blkObj 'GetAttributes))
      (foreach att attList
        (setq tag (strcase (vla-get-TagString att)))
        (setq val (vla-get-TextString att))
        (if (= tag "ADET")
          (progn
            (setq numstr ""
                  idx 1)
            (while (<= idx (strlen val))
              (setq ch (substr val idx 1))
              (if (and (>= (ascii ch) 48) (<= (ascii ch) 57))
                (setq numstr (strcat numstr ch)))
              (setq idx (1+ idx))
            )
            (if (> (strlen numstr) 0)
              (setq n (atoi numstr)))
          )
        )
      )
    )
  )
  n
)

(defun get-linye-numarasýi-from-block (blkObj / attList att tag val res)
  (setq res nil)
  (if (= :vlax-true (vla-get-HasAttributes blkObj))
    (progn
      (setq attList (vlax-invoke blkObj 'GetAttributes))
      (foreach att attList
        (setq tag (strcase (vla-get-TagString att)))
        (setq val (vla-get-TextString att))
        (if (or (= tag "LINYE_NUMARASI")
                (= tag "LÝNYE_NUMARASI"))
          (setq res val)
        )
      )
    )
  )
  res
)

(defun block-ref-contact-point (plObj blkObj tol / res lst
                                         insPt pts allPts p cpt d bestD bestP)
  (setq res
    (vl-catch-all-apply
      (function
        (lambda ()
          (vlax-invoke plObj 'IntersectWith blkObj 0)))))
  (if (not (vl-catch-all-error-p res))
    (progn
      (setq lst (vl-catch-all-apply 'DEG:PT->LIST (list res)))
      (if (vl-catch-all-error-p lst) (setq lst nil))
      (if (and (listp lst) (>= (length lst) 2))
        (setq bestP (list (nth 0 lst) (nth 1 lst) 0.0))
      )
    )
  )
  (if (not bestP)
    (progn
      (setq insPt (deg-get-inspt blkObj))
      (setq pts   (bbox-test-points blkObj))
      (setq allPts (cons insPt pts))
      (foreach p allPts
        (if p
          (progn
            (setq cpt (deg-safe-closest-point plObj p))
            (if cpt
              (progn
                (setq d (distance p cpt))
                (if (and (< d tol)
                         (or (not bestD) (< d bestD)))
                  (setq bestD d
                        bestP cpt)
                )
              )
            )
          )
        )
      )
    )
  )
  bestP
)

(defun parse-linye-key (s / i len ch prefix numstr)
  (if (not s) (setq s ""))
  (setq len (strlen s))
  (setq i 1
        prefix ""
        numstr "")
  (while (and (<= i len)
              (or (and (>= (ascii (substr s i 1)) 65) (<= (ascii (substr s i 1)) 90))
                  (and (>= (ascii (substr s i 1)) 97) (<= (ascii (substr s i 1)) 122))))
    (setq prefix (strcat prefix (substr s i 1)))
    (setq i (1+ i))
  )
  (while (<= i len)
    (setq ch (substr s i 1))
    (if (and (>= (ascii ch) 48) (<= (ascii ch) 57))
      (setq numstr (strcat numstr ch)))
    (setq i (1+ i))
  )
  (cons (strcase prefix) (if (> (strlen numstr) 0) (atoi numstr) 0))
)

(defun deg-trim-string (s)
  (if s
    (vl-string-trim " " s)
    ""
  )
)

(defun deg-block-linye-key (blkObj / ln)
  (setq ln (deg-trim-string (get-linye-numarasýi-from-block blkObj)))
  (if ln ln "")
)

(defun deg-build-sembol-list-from-blocks (blocks / symAssoc sembolList b vals sym n old pair)
  (setq symAssoc '())
  (foreach b blocks
    (foreach vals (get-sembol-adi-from-block b)
      (setq sym (car vals)
            n   (cdr vals)
            old (assoc sym symAssoc))
      (if old
        (setq symAssoc
              (subst (cons sym (+ n (cdr old))) old symAssoc))
        (setq symAssoc (cons (cons sym n) symAssoc))
      )
    )
  )
  (setq symAssoc (reverse symAssoc)
        sembolList '())
  (foreach pair symAssoc
    (setq sembolList
          (append sembolList
                  (list (strcat (itoa (cdr pair)) "x" (car pair)))))
  )
  sembolList
)

(defun deg-group-blocks-by-linye (blocks / blankBlocks nonBlankOrder nonBlankAssoc b ln old grouped)
  (setq blankBlocks   '()
        nonBlankOrder '()
        nonBlankAssoc '())
  (foreach b blocks
    (setq ln (deg-block-linye-key b))
    (if (> (strlen ln) 0)
      (progn
        (if (not (assoc ln nonBlankAssoc))
          (setq nonBlankOrder (append nonBlankOrder (list ln))))
        (setq old (assoc ln nonBlankAssoc))
        (if old
          (setq nonBlankAssoc
                (subst (cons ln (append (cdr old) (list b))) old nonBlankAssoc))
          (setq nonBlankAssoc (append nonBlankAssoc (list (cons ln (list b)))))
        )
      )
      (setq blankBlocks (append blankBlocks (list b)))
    )
  )
  (cond
    (nonBlankOrder
      (if (= (length nonBlankOrder) 1)
        (progn
          (setq ln  (car nonBlankOrder)
                old (assoc ln nonBlankAssoc))
          (setq nonBlankAssoc
                (subst (cons ln (append (cdr old) blankBlocks)) old nonBlankAssoc))
        )
      )
      (setq grouped '())
      (foreach ln nonBlankOrder
        (setq old (assoc ln nonBlankAssoc))
        (if old
          (setq grouped (append grouped (list (cons ln (cdr old)))))
        )
      )
      grouped
    )
    (blocks
      (list (cons "" blocks))
    )
    (T nil)
  )
)

(defun deg-build-data-rows-by-linye (blocks layerName mesafe len blockMesafe toplam kitLayerP
                                    / groups rows grp ln rowBlocks blockNamesStr sembolList
                                      adetFactor adetRaw toplamx)
  (setq groups (deg-group-blocks-by-linye blocks)
        rows   '())
  (if (and kitLayerP (null groups))
    (setq groups (list (cons "" nil))))
  (foreach grp groups
    (setq ln        (car grp)
          rowBlocks (cdr grp))
    (setq adetFactor 1)
    (foreach b rowBlocks
      (setq adetRaw (get-adet-from-block b))
      (if (> adetRaw 0)
        (if (= adetFactor 1)
          (setq adetFactor adetRaw)
          (if (> adetRaw adetFactor)
            (setq adetFactor adetRaw)
          )
        )
      )
    )
    (setq toplamx nil)
    (if (deg--layer-is-data-tv-tel layerName)
      (setq toplamx (* toplam adetFactor))
    )
    (if kitLayerP
      (setq rows
            (append rows
                    (list (list ln layerName mesafe len blockMesafe toplam toplamx "" nil))))
      (progn
        (setq blockNamesStr (deg-block-count-string rowBlocks))
        (if (and blockNamesStr (/= blockNamesStr ""))
          (progn
            (setq sembolList (deg-build-sembol-list-from-blocks rowBlocks))
            (setq rows
                  (append rows
                          (list (list ln layerName mesafe len blockMesafe toplam toplamx blockNamesStr sembolList))))
          )
        )
      )
    )
  )
  rows
)

(defun deg-block-name (blkObj / nm dyn)
  (setq nm (vla-get-Name blkObj))
  (if (and nm (= (substr nm 1 1) "*"))
    (progn
      (if (vlax-property-available-p blkObj 'EffectiveName)
        (setq nm (vla-get-EffectiveName blkObj))
        (if (and (vlax-property-available-p blkObj 'DynamicBlockTableRecord)
                 (= :vlax-true (vla-get-IsDynamicBlock blkObj)))
          (progn
            (setq dyn (vla-get-DynamicBlockTableRecord blkObj))
            (setq nm (vla-get-Name dyn))
          )
        )
      )
    )
  )
  (strcase nm)
)


(defun deg-block-name-raw (blkObj / nm dyn)
  (setq nm (vla-get-Name blkObj))
  (if (and nm (= (substr nm 1 1) "*"))
    (progn
      (if (vlax-property-available-p blkObj 'EffectiveName)
        (setq nm (vla-get-EffectiveName blkObj))
        (if (and (vlax-property-available-p blkObj 'DynamicBlockTableRecord)
                 (= :vlax-true (vla-get-IsDynamicBlock blkObj)))
          (progn
            (setq dyn (vla-get-DynamicBlockTableRecord blkObj))
            (setq nm (vla-get-Name dyn))
          )
        )
      )
    )
  )
  nm
)


(defun deg-block-count-string (blocks / namesAssoc blkObj blkName blkNameU old res
                                      adetRaw adetUse)
  (setq namesAssoc '())
  (foreach blkObj blocks
    (setq blkName  (deg-block-name-raw blkObj))
    (setq blkNameU (strcase blkName))

    (setq adetRaw (get-adet-from-block blkObj))
    (setq adetUse (if (> adetRaw 0) adetRaw 1))

    (if (and
          (not (wcmatch blkNameU (DEG:VAL 'J4)))
          (not (deg-member blkNameU
                     (DEG:VALS '(P1 I2 M1 J1 J2 J3)))))
      (progn
        (setq old (assoc blkName namesAssoc))
        (if old
          (setq namesAssoc
                (subst (cons blkName (+ adetUse (cdr old))) old namesAssoc))
          (setq namesAssoc (cons (cons blkName adetUse) namesAssoc))
        )
      )
    )
  )

  (setq namesAssoc (reverse namesAssoc))
  (setq res "")
  (foreach p namesAssoc
    (setq res (strcat res (itoa (cdr p)) "x" (car p) ",")))
  (if (> (strlen res) 0)
    (substr res 1 (1- (strlen res)))   ;; sondaki virgülü sil
    ""
  )
)



(defun deg-build-knx-chain (testMode blkRefObj ss blkSS
                          / knxLayers chainLayer
                            tolKnxStart tolKnxBlock tolKnxEnd
                            knxList startList dataRows
                            i ent obj layerName
                            queue curPline visitedPlineHandles visitedBlockHandles
                            chainPlines chainBlocks
                            blkEnt blkObj blkName hP hB
                            totalLen len toplam
                            blockNamesStr
                            symAssoc sembolList vals sym n old
                            linyeList ln linyeStr)

  (setq knxLayers  (list (DEG:VAL 'A1) (DEG:VAL 'A7)))
  (setq tolKnxStart (DEG:CFG-TOL-NUM-OR 'DG_KNX_START_TOL 50.0))   ;; referans BLOÐU – KNX polyline baþlangýç toleransý
  (setq tolKnxBlock (DEG:CFG-TOL-NUM-OR 'DG_KNX_BLOCK_TOL 30.0))   ;; KNX dalý üüzerindeki blok toleransý
  (setq tolKnxEnd   (DEG:CFG-TOL-NUM-OR 'DG_KNX_END_TOL 30.0))   ;; KNX polylineler arasýý baðlantý toleransý
  (setq dataRows   '())

  (if ss
    (progn
      (setq knxList '())
      (setq i 0)
      (while (< i (sslength ss))
        (setq ent (ssname ss i)
              obj (vlax-ename->vla-object ent)
              layerName (norm-layer (vlax-get obj 'Layer)))
        (if (member layerName knxLayers)
          (setq knxList (cons obj knxList))
        )
        (setq i (1+ i))
      )
    )
  )

  (if (and blkRefObj knxList)
    (progn
      (setq startList '())
      (foreach obj knxList
        (if (poly-touch-block? obj blkRefObj tolKnxStart)
          (setq startList (cons obj startList))
        )
      )

      (if startList
        (progn
          (setq visitedPlineHandles '())

          (foreach obj startList
            (setq hP (vlax-get obj 'Handle))
            (if (not (handle-in-list? hP visitedPlineHandles))
              (progn
                (setq queue               (list obj))
                (setq chainPlines         '())
                (setq chainBlocks         '())
                (setq chainLayer          (norm-layer (vlax-get obj 'Layer)))
                (setq visitedPlineHandles (cons hP visitedPlineHandles))
                (setq visitedBlockHandles '())

                (while queue
                  (setq curPline (car queue)
                        queue    (cdr queue))
                  (setq chainPlines (cons curPline chainPlines))

                  (if blkSS
                    (progn
                      (setq i 0)
                      (while (< i (sslength blkSS))
                        (setq blkEnt (ssname blkSS i)
                              blkObj (vlax-ename->vla-object blkEnt))
                        (setq blkName (deg-block-name blkObj))
                        (setq hB      (vlax-get blkObj 'Handle))

                        (setq tolLocal
                              (deg-block-tol
                                (if (= blkName (DEG:VAL 'P1)) (DEG:CFG-TOL-NUM-OR 'DG_P1_TOL 3.0) tolKnxBlock)
                                blkObj))

                        (if (and
                              (poly-touch-block? curPline blkObj tolLocal)
                              (not (= blkName (DEG:VAL 'A6)))
                              (not (handle-in-list? hB visitedBlockHandles)))
                          (progn
                            (setq visitedBlockHandles (cons hB visitedBlockHandles))
                            (setq chainBlocks         (cons blkObj chainBlocks))
                            (if testMode
                              (deg-make-circle (deg-get-inspt blkObj) tolLocal)
                            )

                            (foreach other knxList
                              (setq hP (vlax-get other 'Handle))
                              (if (and
                                    (not (handle-in-list? hP visitedPlineHandles))
                                    (poly-touch-block? other blkObj tolLocal))
                                (progn
                                  (setq visitedPlineHandles (cons hP visitedPlineHandles))
                                  (setq queue (cons other queue))
                                )
                              )
                            )
                          )
                        )
                        (setq i (1+ i))
                      )
                    )
                  )

                  (foreach other knxList
                    (setq hP (vlax-get other 'Handle))
                    (if (and
                          (not (handle-in-list? hP visitedPlineHandles))
                          (connection-point curPline other tolKnxEnd))
                      (progn
                        (setq visitedPlineHandles (cons hP visitedPlineHandles))
                        (setq queue (cons other queue))
                      )
                    )
                  )
                ) ;; while queue

                (if chainPlines
                  (progn
                    (if testMode (color-red chainPlines))

                    (setq totalLen 0.0)
                    (foreach p chainPlines
                      (setq totalLen (+ totalLen (vla-get-length p)))
                    )
                    (setq len    totalLen)
                    (setq toplam totalLen)

                    (setq dataRows
                          (append (reverse (deg-build-data-rows-by-linye chainBlocks chainLayer 0.0 len 0.0 toplam nil))
                                  dataRows))
                  )
                )
              )
            )
          )
        )
      )
    )
  )

  (reverse dataRows)
)

(defun deg-build-data (testMode blkRefObj
                       / ss blkSS
                         tolRef tolChain tolReport tolRefDal
                         startPtOnRef startDist
                         i j k ent obj layerName
                         dataList sortedList
                         refInfos kombList
                         changed kobj robj info baseParam baseDist
                         connPt connOnRobj connOnKobj
                         paramConnRobj paramConnKobj
                         processedPlineHandles hCur
                         ds de cpt mesafeTmp
                         bestMesafe bestPx bestPy bestRobj bestEnd
                         mesafe px py
                         blockMesafe bestBlockDist distFromStart distFromRef projPt
                         queue curPline
                         visitedPlineHandles visitedBlockHandles
                         chainPlines chainBlocks
                         blkEnt other otherObj
                         hP hB
                         toplamUzunluk toplam
                         blockNamesStr blkName s
                         symAssoc sembolList vals sym n old
                         adetFactor adetRaw
                         len
                         bestRefObj bestRefPt bestRefD candPt candD
                         linyeStr ln linyeList
                         touchChain touchReport
                         connFound
                         refLayer refL dalL
                         otherLayer
                         markedTol30Handles
                         markedTol7Handles
                         tolRefLocal tolChainLocal tolReportLocal
                         touchingAll touchingRefs cp sp ep
                         tolDalSingle visitedBranchHandles
                         trunkObj branchObj hBranch trunkInfo cp_ref
                         touchingRefTrunk touchingRefOther touchingDal
                         blkEnt2 blkObj2 blkName2 bName
                         insPt
                         kitLayerP
                         overlapRefDalP rootPt rootBridgeP endConnPt
                         myBlocks writtenKey
                       )

  (vl-load-com)

  ;; DK yazýlarý için TEXTSTYLE -> STANDARD (Arial font)
  (setq oldTS (getvar "TEXTSTYLE"))
  (degk--ensure-textstyle "STANDARD" "arial.ttf")
  (setvar "TEXTSTYLE" "STANDARD")

(defun deg-norm (s / tmp)
  (if (null s) ""
    (progn
      (setq tmp (vl-princ-to-string s))
      (setq tmp (vl-string-translate "ÝIý" "iii" tmp))
      (strcase tmp)
    )
  )
)

(defun deg--layer-is-data-tv-tel (layer / n)
  (setq n (deg-norm layer))
  (or (wcmatch n (DEG:VAL 'C9))
      (DEG:LAYER-IN-CODES? n '(C1 C2 C3 C4))
      (wcmatch n (DEG:VAL 'E4))
      (wcmatch n (DEG:VAL 'H5))
      (DEGQ:_cctv-layer-name-p n)
      (wcmatch n (DEG:VAL 'F5)))
)

(defun deg--dp-layer-family (layer / n)
  (setq n (norm-layer layer))
  (cond
    ((or (DEGP--data-layer-name-p n) (DEG:LAYER-IN-CODES? n '(C1 C2 C3 C4)) (wcmatch n (DEG:VAL 'C9))) "DATA")
    ((or (DEG:LAYER-IN-CODES? n '(E1 E2 E3 E5)) (wcmatch n (DEG:VAL 'E4))) "TEL")
    ((or (DEG:LAYER-IN-CODES? n '(F1 F2 F3 F4)) (wcmatch n (DEG:VAL 'F5))) "TV")
    ((DEGQ:_cctv-layer-name-p n) "CCTV")
    ((or (DEG:LAYER-IN-CODES? n '(H1 H2 H3 H4)) (wcmatch n (DEG:VAL 'H5))) "KARTLI")
    ((DEGP--lighting-layer-name-p n) "AYDINLATMA")
    ((DEG:LAYER-IN-CODES? n '(B1 B2 B3 B4)) "PRIZ")
    ((DEG:LAYER-IN-CODES? n '(G1 G2 G3 G4)) "UPS")
    (T n)
  )
)

(defun deg--dp-same-layer-family-p (a b)
  (= (deg--dp-layer-family a) (deg--dp-layer-family b))
)

(defun deg--dp-block-written-key (h layer)
  (strcat h "|" (deg--dp-layer-family layer))
)


  (setq *degRefChainEnts* nil)
  (setq tolRef    (DEG:CFG-TOL-NUM-OR 'DG_REF_TOL 50.0)
        tolChain  (DEG:CFG-TOL-NUM-OR 'DG_CHAIN_TOL 7.0)
        tolReport (DEG:CFG-TOL-NUM-OR 'DG_REPORT_TOL 7.0)
        tolRefDal (DEG:CFG-TOL-NUM-OR 'DG_REF_DAL_TOL 7.0))

  (setq markedTol30Handles '())
  (setq markedTol7Handles  '())

  (setq ss    (cond
                ((and (boundp '*degDGScopePolySS*) *degDGScopePolySS*) *degDGScopePolySS*)
                (T (ssget "_X" '((0 . "LWPOLYLINE"))))
              ))
  (setq blkSS (cond
                ((and (boundp '*degDGScopeBlkSS*) *degDGScopeBlkSS*) *degDGScopeBlkSS*)
                (T (ssget "_X" '((0 . "INSERT"))))
              ))
  (if (<= (DEG:SS-LEN ss) 0)    (setq ss nil))
  (if (<= (DEG:SS-LEN blkSS) 0) (setq blkSS nil))

  (if (not ss)
    (progn
      (princ "\n\nPolyline yok.")
      (setq sortedList nil)
    )
    (progn
      (setq bestRefObj nil
            bestRefPt  nil
            bestRefD   nil)

(if (and (boundp '*degForceRefObj*) *degForceRefObj*)
  (progn
    (setq bestRefObj *degForceRefObj*)
    (setq insPt (deg-get-inspt blkRefObj))
    (setq bestRefPt (if (and (boundp '*degForceRefPt*) *degForceRefPt*)
                      *degForceRefPt*
                      (vlax-curve-getStartPoint bestRefObj)))
    (setq bestRefD (distance (deg-safe-closest-point bestRefObj insPt) insPt))
  )
)

(setq i 0)
      (while (< i (sslength ss))
        (setq ent (ssname ss i)
              obj (vlax-ename->vla-object ent)
              layerName (norm-layer (vlax-get obj 'Layer)))
        (if (DEG:LAYER-IN-CODES? layerName '(B2 B4 A3 A5 E3 F4 C3 C7 E5 C1 C2 F2 C8 C4 G2 G4 H2 D4))
          (progn
            (setq insPt  (deg-get-inspt blkRefObj))
            (setq candPt (deg-safe-closest-point obj insPt))
            (if (deg-endpoint-touch? obj blkRefObj tolRef)
              (progn
                (setq candD (distance candPt insPt))
                (if (or (not bestRefD) (< candD bestRefD))
                  (progn
                    (setq bestRefD   candD)
                    (setq bestRefObj obj)
                    (setq bestRefPt  candPt)
                  )
                )
              )
            )
          )
        )
        (setq i (1+ i))
      )

      (if (not bestRefObj)
        (progn
          (princ "\n\nSeçilen bloða deðen KOMBINE polyline bulunamadý.")
          (setq *degHideToplamx* nil)
          (setq *degHideSortiToplam* nil)
          (setq dataList (deg-build-knx-chain testMode blkRefObj ss blkSS))
          (setq sortedList dataList)
        )
        (progn
          (setq refLayer (norm-layer (vlax-get bestRefObj 'Layer)))
          (setq *degLastRefLayer* refLayer)
          (setq *degLastIsCCTV*
            (or (DEGQ:_cctv-layer-name-p refLayer)
                (and (DEGP--dp-data-mode-p) (DEGP--data-layer-name-p refLayer))))

          (setq isCctvKartli
                 (or (DEGQ:_cctv-layer-name-p refLayer)
                     (and (DEGP--dp-data-mode-p) (DEGP--data-layer-name-p refLayer))
                     (wcmatch (deg-norm refLayer) (DEG:VAL 'H5))))
          (if isCctvKartli
            (progn
              (setq tolChain  (DEG:CFG-TOL-NUM-OR 'DG_CHAIN_TOL 7.0))
              (setq tolReport (DEG:CFG-TOL-NUM-OR 'DG_REPORT_TOL 7.0))
              (setq tolRefDal (DEG:CFG-TOL-NUM-OR 'DG_REF_DAL_TOL 7.0))
            )
          )

          (setq *degHideToplamx* (deg--layer-is-priz-or-lighting refLayer))
          (setq *degHideSortiToplam* (not *degHideToplamx*))

          (cond
            ((and (DEGP--dp-data-mode-p) (DEGP--data-layer-name-p refLayer))
             (setq refL (DEGP--data-ref-layers))
             (setq dalL (DEGP--data-dal-layers))
            )
            ((and (DEGP--dp-lighting-mode-p)
                  (DEGP--lighting-layer-name-p refLayer))
             (setq refL
               (if (DEGP--lighting-comb-like-layer-p refLayer)
                 (DEGP--lighting-comb-layers)
                 (DEGP--lighting-line-layers)))
             (setq dalL (DEGP--lighting-line-layers))
            )
            ((member refLayer (DEG:VALS '(B2 B4)))
             (setq refL (DEG:VALS '(B2 B4)))
             (setq dalL (DEG:VALS '(B1 B3)))
            )
            ((member refLayer (DEG:VALS '(A2 A4)))
             (setq refL (DEG:VALS '(A2 A4)))
             (setq dalL (append (DEG:VALS '(A2 A4 A7)) (DEG:CFG-LIST 'DG_KIT_LAYER) (DEG:CFG-LIST 'DG_ANAHTAR_LAYER) (DEG:DG-EXTRA-LAYERS)))
            )
            ((member refLayer (DEG:VALS '(A3 A5)))
             (setq refL (DEG:VALS '(A3 A5)))
             (setq dalL (append (DEG:VALS '(A2 A4 A7)) (DEG:CFG-LIST 'DG_KIT_LAYER) (DEG:CFG-LIST 'DG_ANAHTAR_LAYER) (DEG:DG-EXTRA-LAYERS)))
            )
            ((member refLayer (DEG:VALS '(F2 F4)))
             (setq refL (DEG:VALS '(F2 F4)))
             (setq dalL (DEG:VALS '(F1 F3)))
            )
            ((member refLayer (DEG:VALS '(D1 D2 D3 D4)))
             (setq refL (DEG:VALS '(D4 D3)))
             (setq dalL (DEG:VALS '(D1 D2)))
            )
            ((member refLayer (DEG:VALS '(H2 H4)))
             (setq refL (DEG:VALS '(H2 H4)))
             (setq dalL (DEG:VALS '(H1 H3)))
            )
            ((member refLayer (DEG:VALS '(E5 E3)))
             (setq refL (DEG:VALS '(E5 E3)))
             (setq dalL (DEG:VALS '(E1 E2)))
            )
            ((member refLayer (DEG:VALS '(C4 C3)))
             (setq refL (DEG:VALS '(C4 C3)))
             (setq dalL (DEG:VALS '(C1 C2 F1 F3 E2 E1)))
            )
            ((member refLayer (DEG:VALS '(C8 C7)))
             (setq refL (DEG:VALS '(C8 C7)))
             (setq dalL (DEG:VALS '(C6)))
            )
            ((member refLayer (DEG:VALS '(G2 G4)))
             (setq refL (DEG:VALS '(G2 G4)))
             (setq dalL (DEG:VALS '(G1 G3)))
            )
            (T
             (princ
               (strcat
                 "\nUyarý: Tanýnmayan referans layer: " refLayer
                 " – tüm layer’lar serbest çalýþýyor."))
             (setq refL (DEG:VALS '(B2 B4 A3 A5 F2 F4 D4 H2 D3 E5 E3 C4 C3 C8 C7 G2 G4)))
             (setq dalL (DEG:VALS '(B1 B3 A2 A4 A7 F1 D1 H1 D2 F3 E1 E2 C1 C2 C6 G1 G3)))
            )
          )

          (setq tolReport (DEG:CFG-TOL-NUM-OR 'DG_REPORT_TOL 7.0))

          (setq startPtOnRef bestRefPt)
          (setq startDist (deg-safe-dist-at-point bestRefObj startPtOnRef))

          (setq refInfos (list (list bestRefObj startDist 0.0)))

          (setq kombList '())
          (setq i 0)
          (while (< i (sslength ss))
            (setq ent (ssname ss i)
                  obj (vlax-ename->vla-object ent)
                  layerName (norm-layer (vlax-get obj 'Layer)))
            (if (and (/= (vlax-get obj 'Handle) (vlax-get bestRefObj 'Handle))
                     (member layerName refL))
              (setq kombList (cons obj kombList))
            )
            (setq i (1+ i))
          )

          (setq changed T)
          (while changed
            (setq changed nil)
            (foreach kobj kombList
              (if (not (ref-find-info kobj refInfos))
                (progn
                  (setq connFound nil)
                  (setq kStart (vlax-curve-getStartPoint kobj))
                  (setq kEnd   (vlax-curve-getEndPoint   kobj))
                  (setq overlapRefDalP
                    (member (norm-layer (vlax-get kobj 'Layer)) dalL))

                  ;; Aydinlatmada A2/A4 hem referans hem dal listesinde olabilir.
                  ;; Secilen referansa baglanan diger A2/A4 polylinelarini ana hat
                  ;; devami saymak, ayni dugumdeki kardes dallari yutuyordu.
                  (if (not overlapRefDalP)
                    (foreach info refInfos
                      (if (not connFound)
                        (progn
                          (setq robj      (car  info))
                          (setq baseParam (cadr info))
                          (setq baseDist  (caddr info))

                          (setq cpt (deg-safe-closest-point robj kStart))
                          (if (< (distance kStart cpt) tolRef)
                            (progn
                              (setq paramConnRobj (deg-safe-dist-at-point robj cpt))
                              (setq baseDist (+ baseDist (abs (- paramConnRobj baseParam))))
                              (setq paramConnKobj (deg-safe-dist-at-point kobj kStart))
                              (setq refInfos (cons (list kobj paramConnKobj baseDist)
                                                   refInfos))
                              (setq connFound T)
                            )
                          )

                          (if (not connFound)
                            (progn
                              (setq cpt (deg-safe-closest-point robj kEnd))
                              (if (< (distance kEnd cpt) tolRef)
                                (progn
                                  (setq paramConnRobj (deg-safe-dist-at-point robj cpt))
                                  (setq baseDist (+ baseDist (abs (- paramConnRobj baseParam))))
                                  (setq paramConnKobj (deg-safe-dist-at-point kobj kEnd))
                                  (setq refInfos (cons (list kobj paramConnKobj baseDist)
                                                       refInfos))
                                  (setq connFound T)
                                )
                              )
                            )
                          )
                        )
                      )
                    )
                  )

                  (if connFound
                    (setq changed T)
                  )
                )
              )
            )
          )

          (if blkSS
            (progn
              (setq changed T)
              (while changed
                (setq changed nil)
                (foreach kobj kombList
                  (if (not (ref-find-info kobj refInfos))
                    (progn
                      (setq connFound nil)
                      (setq overlapRefDalP
                        (member (norm-layer (vlax-get kobj 'Layer)) dalL))
                      (setq j 0)
                      (while (and (< j (sslength blkSS)) (not connFound))
                        (setq blkEnt (ssname blkSS j)
                              blkObj (vlax-ename->vla-object blkEnt))
                        (setq blkName (deg-block-name blkObj))
                        (setq tolRefLocal
                          (deg-block-tol
                            (cond
                              ((= blkName (DEG:VAL 'P1))
                                (DEG:CFG-TOL-NUM-OR 'DG_P1_TOL 3.0))
                              ((deg-doseme-inis-block-p blkObj) tolRef)
                              (T tolChain))
                            blkObj))
                        (if (and
                              (or (not overlapRefDalP)
                                  (deg-doseme-inis-block-p blkObj))
                              (deg-poly-touch-block-base-p kobj blkObj tolRefLocal))
                          (progn
                            (foreach info refInfos
                              (if (not connFound)
                                (progn
                                  (setq robj (car info))
                                  (if (deg-poly-touch-block-base-p robj blkObj tolRefLocal)
                                    (progn
                                      (setq baseParam (cadr info)
                                            baseDist  (caddr info))
                                      (setq insPt (deg-get-inspt blkObj))
                                      (if (deg-doseme-inis-block-p blkObj)
                                        (progn
                                          (setq connOnRobj (block-ref-contact-point robj blkObj tolRefLocal))
                                          (setq connOnKobj (block-ref-contact-point kobj blkObj tolRefLocal))
                                        )
                                        (progn
                                          (setq connOnRobj (deg-safe-closest-point robj insPt))
                                          (setq connOnKobj (deg-safe-closest-point kobj insPt))
                                          (if (not (and insPt connOnRobj connOnKobj
                                                        (< (distance insPt connOnRobj) tolRefLocal)
                                                        (< (distance insPt connOnKobj) tolRefLocal)))
                                            (setq connOnRobj nil
                                                  connOnKobj nil)
                                          )
                                        )
                                      )
                                      (if (and connOnRobj connOnKobj)
                                        (progn
                                          (setq paramConnRobj (deg-safe-dist-at-point robj connOnRobj))
                                          (setq baseDist (+ baseDist (abs (- paramConnRobj baseParam))))
                                          (setq paramConnKobj (deg-safe-dist-at-point kobj connOnKobj))
                                          (setq refInfos
                                                (cons (list kobj paramConnKobj baseDist)
                                                      refInfos))
                                          (setq connFound T
                                                changed   T)
                                        )
                                      )
                                    )
                                  )
                                )
                              )
                            )
                          )
                        )
                        (setq j (1+ j))
                      )
                    )
                  )
                )
              )
            )
          )

          (setq *degRefChainEnts* (mapcar 'car refInfos))

          (setq dataList '()
                processedPlineHandles '()
                i 0)

          (while (< i (sslength ss))
            (setq ent  (ssname ss i)
                  obj  (vlax-ename->vla-object ent)
                  layerName (norm-layer (vlax-get obj 'Layer))
                  hCur (vlax-get obj 'Handle))

            (setq kitLayerP (wcmatch (deg-norm layerName) "*KIT*,E_ANAHTAR_HATTI"))

            (if (and
                  (member layerName dalL)
                  (not (in-ref-infos? obj refInfos))
                  (not (handle-in-list? hCur processedPlineHandles))
                )

              (progn
                (setq ds (vlax-curve-getStartPoint obj))
                (setq de (vlax-curve-getEndPoint   obj))

                (setq bestMesafe nil
                      bestPx     nil
                      bestPy     nil
                      bestRobj   nil)

                (foreach info refInfos
                  (setq robj      (car  info))
                  (setq baseParam (cadr info))
                  (setq baseDist  (caddr info))

                  (setq cpt (deg-safe-closest-point robj ds))
                  (if (< (distance ds cpt) tolRefDal)
                    (progn
                      (setq connOnRobj    cpt)
                      (setq paramConnRobj (deg-safe-dist-at-point robj connOnRobj))
                      (setq mesafeTmp (+ baseDist (abs (- paramConnRobj baseParam))))
                      (if (or (not bestMesafe) (< mesafeTmp bestMesafe))
                        (progn
                          (setq bestMesafe mesafeTmp)
                          (setq bestPx (car cpt))
                          (setq bestPy (cadr cpt))
                          (setq bestRobj robj)
                          (setq bestEnd "S")
                        )
                      )
                    )
                  )

                  (setq cpt (deg-safe-closest-point robj de))
                  (if (< (distance de cpt) tolRefDal)
                    (progn
                      (setq connOnRobj    cpt)
                      (setq paramConnRobj (deg-safe-dist-at-point robj connOnRobj))
                      (setq mesafeTmp (+ baseDist (abs (- paramConnRobj baseParam))))
                      (if (or (not bestMesafe) (< mesafeTmp bestMesafe))
                        (progn
                          (setq bestMesafe mesafeTmp)
                          (setq bestPx (car cpt))
                          (setq bestPy (cadr cpt))
                          (setq bestRobj robj)
                          (setq bestEnd "E")
                        )
                      )
                    )
                  )
                )

                (if bestMesafe
                  (progn
                    (setq rootPt (list bestPx bestPy 0.0))
                    (setq blockMesafe 0.0)
                    (if (and blkSS bestEnd (not kitLayerP))
                      (progn
                        (setq bestBlockDist nil)
                        (setq totalLen (vla-get-length obj))
                        (setq j 0)
                        (while (< j (sslength blkSS))
                          (setq blkEnt (ssname blkSS j)
                                blkObj (vlax-ename->vla-object blkEnt))
                          (setq blkName (deg-block-name blkObj))
                          (if (not (= blkName (DEG:VAL 'P1)))
                            (progn
                              (setq tolChainLocal (deg-block-tol tolChain blkObj))
                              (if (deg-poly-touch-block-base-p obj blkObj tolChainLocal)
                                (progn
                                  (setq insPt  (deg-get-inspt blkObj))
                                  (setq projPt (deg-safe-closest-point obj insPt))
                                  (setq distFromStart (deg-safe-dist-at-point obj projPt))
                                  (setq distFromRef
                                        (cond
                                          ((= bestEnd "S") distFromStart)
                                          ((= bestEnd "E") (- totalLen distFromStart))
                                          (T distFromStart)))
                                  (if (or (not bestBlockDist) (< distFromRef bestBlockDist))
                                    (setq bestBlockDist distFromRef)
                                  )
                                )
                              )
                            )
                          )
                          (setq j (1+ j))
                        )
                        (if bestBlockDist
                          (setq blockMesafe bestBlockDist)
                          (setq blockMesafe 0.0)
                        )
                      )
                    )

                    (setq mesafe bestMesafe
                          px     bestPx
                          py     bestPy)

                    (if (and testMode px py)
                      (progn
                        (deg-ensure-layer (DEG:VAL 'R2) (DEG:CFG-ACI-OR 'DGT_SORTI_COLOR 4))
                        (DEG-DGT--make-circle
                          (list px py 0.0)
                          10.0
                          (DEG:VAL 'R2)
                          (DEG:CFG-ACI-OR 'DGT_SORTI_COLOR 4)
                        )
                      )
                    )

                    (setq queue               (list obj))
                    (setq visitedPlineHandles (list hCur))
                    (setq visitedBlockHandles '())
                    (setq chainPlines         '())
                    (setq chainBlocks         '())

                    (while queue
                      (setq curPline (car queue)
                            queue    (cdr queue))

                      (setq chainPlines (cons curPline chainPlines))

                      (if (and blkSS (not kitLayerP))
                        (progn
                          (setq j 0)
                          (while (< j (sslength blkSS))
                            (setq blkEnt (ssname blkSS j))
                            (setq blkObj (vlax-ename->vla-object blkEnt))
                            (setq hB     (vlax-get blkObj 'Handle))
                            (setq blkName (deg-block-name blkObj))
                            (setq insPt (deg-get-inspt blkObj))

                            (setq tolChainLocal  (deg-block-tol (if (= blkName (DEG:VAL 'P1)) (DEG:CFG-TOL-NUM-OR 'DG_P1_TOL 3.0) tolChain) blkObj))
                            (setq tolReportLocal (deg-block-tol (if (= blkName (DEG:VAL 'P1)) (DEG:CFG-TOL-NUM-OR 'DG_P1_TOL 3.0) tolReport) blkObj))
                            (setq rootBridgeP
                              (and rootPt insPt
                                   (<= (distance rootPt insPt)
                                       (max tolRefDal tolChainLocal))))

                            (setq touchChain  (deg-poly-touch-block-base-p curPline blkObj tolChainLocal))
                            (setq touchReport (deg-poly-touch-block-base-p curPline blkObj tolReportLocal))

                            (if (or touchChain touchReport)
                              (progn
                                (if (and touchReport
                                         (not (handle-in-list? hB visitedBlockHandles)))
                                  (progn
                                    (setq visitedBlockHandles (cons hB visitedBlockHandles))
                                    (setq chainBlocks         (cons blkObj chainBlocks))

                                    (if (and testMode
                                             (not (handle-in-list? hB markedTol30Handles)))
                                      (progn
                                        (setq markedTol30Handles (cons hB markedTol30Handles))
                                        (setq rad (if (and (= (type blkRefObj) 'VLA-OBJECT)
                   (= hB (vlax-get blkRefObj 'Handle)))
              tolRef
              tolReportLocal))
                                        (deg-make-circle (deg-get-inspt blkObj) rad)
                                      )
                                    )
                                  )
                                )

                                (if (and touchChain
                                         (not (= blkName (DEG:VAL 'P1)))
                                         (not rootBridgeP))
                                  (progn
                                    (if (and testMode
                                             (not (handle-in-list? hB markedTol7Handles)))
                                      (progn
                                        (setq markedTol7Handles (cons hB markedTol7Handles))
                                        (deg-make-circle (deg-get-inspt blkObj) tolChainLocal)
                                      )
                                    )

                                    (setq k 0)
                                    (while (< k (sslength ss))
                                      (setq other    (ssname ss k)
                                            otherObj (vlax-ename->vla-object other))
                                      (setq hP (vlax-get otherObj 'Handle))
                                      (setq otherLayer (norm-layer (vlax-get otherObj 'Layer)))

                                      (if (and
                                            (member otherLayer dalL)
                                            (not (in-ref-infos? otherObj refInfos))
                                            (not (handle-in-list? hP visitedPlineHandles))
                                            (deg--dp-same-layer-family-p layerName otherLayer)
                                            (deg-poly-touch-block-base-p otherObj blkObj tolChainLocal)
                                          )
                                        (progn
                                          (setq visitedPlineHandles
                                                (cons hP visitedPlineHandles))
                                          (setq queue (cons otherObj queue))
                                        )
                                      )
                                      (setq k (1+ k))
                                    )
                                  )
                                )
                              )
                            )

                            (setq j (1+ j))
                          )
                        )
                      )

                      ;; Blok olmayan, gercekten uc uca devam eden dal parcalarini
                      ;; da izle. Ortak ana-hat kokunde kardes dallar birlestirilmez.
                      (setq k 0)
                      (while (< k (sslength ss))
                        (setq other    (ssname ss k)
                              otherObj (vlax-ename->vla-object other)
                              hP       (vlax-get otherObj 'Handle)
                              otherLayer (norm-layer (vlax-get otherObj 'Layer)))
                        (if (and
                              (member otherLayer dalL)
                              (not (in-ref-infos? otherObj refInfos))
                              (not (handle-in-list? hP visitedPlineHandles))
                              (deg--dp-same-layer-family-p layerName otherLayer)
                              (setq endConnPt
                                (deg-curves-endpoint-connection
                                  curPline otherObj tolChain))
                              (or (null rootPt)
                                  (> (distance rootPt endConnPt) tolRefDal)))
                          (progn
                            (setq visitedPlineHandles
                              (cons hP visitedPlineHandles))
                            (setq queue (cons otherObj queue))
                          )
                        )
                        (setq k (1+ k))
                      )
                    )

                    (if testMode (color-red chainPlines))

                    (foreach p chainPlines
                      (setq processedPlineHandles
                            (cons (vlax-get p 'Handle) processedPlineHandles))
                    )

                    (setq toplamUzunluk 0.0)
                    (foreach p chainPlines
                      (setq toplamUzunluk (+ toplamUzunluk (vla-get-length p)))
                    )

                    (setq toplam (+ mesafe toplamUzunluk))
                    (setq blockMesafe 0.0)
                    (if (and blkSS chainPlines (not kitLayerP))
                      (progn
                        (setq chainList (reverse chainPlines))
                        (setq bestBlockDistChain nil)

                        (setq j 0)
                        (while (< j (sslength blkSS))
                          (setq blkEnt (ssname blkSS j)
                                blkObj (vlax-ename->vla-object blkEnt))
                          (setq blkName (deg-block-name blkObj)
                                nm      (strcase blkName))

                          (if (not (or (= nm (DEG:VAL 'P1))
                                       (wcmatch nm (DEG:VAL 'I3))
                                       (wcmatch nm (DEG:VAL 'M2))
                                       (wcmatch nm (DEG:VAL 'J4))))
                            (progn
                              (setq insPt (deg-get-inspt blkObj))

                              (setq tolChainLocal
                                    (cond
                                      ((wcmatch nm (DEG:VAL 'I4))      7.0)
                                      ((= nm (DEG:VAL 'M1))     7.0)
                                      ((= nm (DEG:VAL 'P1))             3.0)
                                      (T
                                       (setq res (vl-catch-all-apply
                                                   'vla-getBoundingBox
                                                   (list blkObj 'minVar 'maxVar)))
                                       (if (vl-catch-all-error-p res)
                                         40.0
                                         (progn
                                           (setq minPt (vlax-safearray->list minVar)
                                                 maxPt (vlax-safearray->list maxVar)
                                                 xmin (car minPt)
                                                 ymin (cadr minPt)
                                                 xmax (car maxPt)
                                                 ymax (cadr maxPt)
                                                 c1   (list xmin ymin 0.0)
                                                 c2   (list xmin ymax 0.0)
                                                 c3   (list xmax ymin 0.0)
                                                 c4   (list xmax ymax 0.0)
                                                 ins2 (deg-get-inspt blkObj)
                                                 r    (apply 'max
                                                             (mapcar
                                                               '(lambda (p) (distance ins2 p))
                                                               (list c1 c2 c3 c4)))
                                           )
                                           (if (< r 30.0)
                                             r
                                             40.0
                                           )
                                         )
                                       )
                                      )
                                    )
                              )

                              (setq offset 0.0)

                              (foreach pl chainList
                                (if (deg-poly-touch-block-base-p pl blkObj tolChainLocal)
                                  (progn
                                    (setq projPt        (deg-safe-closest-point pl insPt))
                                    (setq distFromStart (deg-safe-dist-at-point pl projPt))
                                    (setq lenPl         (vla-get-length pl))

                                    (setq localDist
                                          (if (and bestEnd (eq pl obj))
                                            (cond
                                              ((= bestEnd "S") distFromStart)
                                              ((= bestEnd "E") (- lenPl distFromStart))
                                              (T              distFromStart))
                                            distFromStart))

                                    (setq totalDist (+ offset localDist))

                                    (if (or (not bestBlockDistChain)
                                            (< totalDist bestBlockDistChain))
                                      (setq bestBlockDistChain totalDist)
                                    )
                                  )
                                )
                                (setq offset (+ offset (vla-get-length pl)))
                              )
                            )
                          )

                          (setq j (1+ j))
                        )

                        (if bestBlockDistChain
                          (setq blockMesafe bestBlockDistChain)
                          (progn
                            (setq blockMesafe 0.0)
                            (if chainBlocks
                              (progn
                                (setq hasValidBlock nil)
                                (foreach b chainBlocks
                                  (setq nm (strcase (deg-block-name b)))
                                  (if (not (or (= nm (DEG:VAL 'P1))
                                               (wcmatch nm (DEG:VAL 'I3))
                                               (wcmatch nm (DEG:VAL 'M2))
                                               (wcmatch nm (DEG:VAL 'J4))))
                                    (setq hasValidBlock T)
                                  )
                                )
                                (if hasValidBlock
                                  (progn
                                    (setq len (vla-get-length obj))
                                    (setq blockMesafe len)
                                  )
                                )
                              )
                            )
                          )
                        )
                      )
                    )


                    (setq adetFactor 1)
                    (foreach b chainBlocks
                      (setq adetRaw (get-adet-from-block b))
                      (if (> adetRaw 0)
                        (if (= adetFactor 1)
                          (setq adetFactor adetRaw)
                          (if (> adetRaw adetFactor)
                            (setq adetFactor adetRaw)
                          )
                        )
                      )
                    )

                    (setq toplamx nil)
                    (if (deg--layer-is-data-tv-tel layerName)
                      (setq toplamx (* toplam adetFactor))
                    )
                    (if (not *DEG-BLOCK-WRITTEN*)
                      (setq *DEG-BLOCK-WRITTEN* '()))
                    (setq myBlocks '())
                    (if chainBlocks
                      (foreach b chainBlocks
                        (setq blkName (deg-block-name b)
                              nm      (strcase blkName)
                              hB      (vlax-get b 'Handle))
                        (cond
                          ((or (= nm (DEG:VAL 'I1))
                               (= nm (DEG:VAL 'I2))
                               (= nm (DEG:VAL 'M1)))
                           (setq myBlocks (cons b myBlocks)))
                          (T
                           (if (not (member (deg--dp-block-written-key hB layerName) *DEG-BLOCK-WRITTEN*))
                             (progn
                               (setq myBlocks (cons b myBlocks))
                               (setq *DEG-BLOCK-WRITTEN*
                                     (cons (deg--dp-block-written-key hB layerName) *DEG-BLOCK-WRITTEN*))
                             )
                           )
                          )
                        )
                      )
                    )

                    (setq len (vla-get-length obj))

                    (if (null blockMesafe)
                      (setq blockMesafe mesafe)
                    )

                    (setq dataList
                          (append dataList
                                  (deg-build-data-rows-by-linye myBlocks layerName mesafe len blockMesafe toplam kitLayerP)))
)
                )
              )
            )

            (setq i (1+ i))
          )

          
(if (and blkSS refInfos)
            (progn
              (setq tolDalSingle (DEG:CFG-TOL-NUM-OR 'DG_DAL_SINGLE_TOL 5.0))
              (setq *deg-ref-grid* (deg-build-ref-grid refInfos *deg-grid-size*))
              (setq i 0)
              (while (< i (sslength blkSS))
                (setq blkEnt  (ssname blkSS i)
                      blkObj  (vlax-ename->vla-object blkEnt)
                      blkName (deg-block-name blkObj))


(setq trunkObj    nil
      bestDist    nil
      bestCp      nil
      trunkObjEnd nil
      bestEndDist nil
      bestEndCp   nil)

(setq insPt (deg-get-inspt blkObj))

(setq trunkObj nil
      bestDist nil
      bestCp   nil)

(setq candList (deg-grid-candidates *deg-ref-grid* insPt *deg-grid-size*))

                  (if (null candList)
                    (setq candList (mapcar 'car refInfos))
                  )


(foreach robj candList
  (if (and (null trunkObj) robj (vlax-curve-p robj)
           (deg-poly-touch-block-base-p robj blkObj tolDalSingle))
    (progn
      (setq bestCp   (deg-safe-closest-point robj insPt))
      (setq bestDist (distance insPt bestCp))
      (setq trunkObj robj)
    )
  )
)
(if trunkObj
  (progn
    (if (or (= blkName (DEG:VAL 'P1))
            (= blkName (DEG:VAL 'I1))
            (= blkName (DEG:VAL 'I2))
            (deg-wcmatch blkName (DEG:VAL 'M2))
        )
      (progn
      )
      (progn
        (if (> bestDist 30.0)
          (progn
            (setq trunkObj nil)
            (setq bestCp   nil)
          )
        )
      )
    )
  )
)

                (if (and trunkObj bestDist (< bestDist tolDalSingle))
                  (progn
                    (setq trunkInfo (ref-find-info trunkObj refInfos))
                    (if trunkInfo
                      (progn
                        (setq baseParam (cadr  trunkInfo)
                              baseDist  (caddr trunkInfo))

                        (setq cp_ref bestCp)

                        (setq sp (vlax-curve-getStartPoint trunkObj)
                              ep (vlax-curve-getEndPoint   trunkObj))
                        (if (or (< (distance cp_ref sp) tolDalSingle)
                                (< (distance cp_ref ep) tolDalSingle))
                          (progn
                            (setq paramConnRobj (deg-safe-dist-at-point trunkObj cp_ref))
                            (setq mesafe (+ baseDist (abs (- paramConnRobj baseParam))))
                            (setq len    0.0)
                            (setq toplam mesafe)
                            (setq chainBlocks (list blkObj))

                            (if blkSS
                              (progn
                                (setq j 0)
                                (while (< j (sslength blkSS))
                                  (setq blkEnt2  (ssname blkSS j)
                                        blkObj2  (vlax-ename->vla-object blkEnt2)
                                        blkName2 (deg-block-name blkObj2))
                                  (if (and (= blkName2 (DEG:VAL 'P1))
                                           (/= (vlax-get blkObj2 'Handle)
                                               (vlax-get blkObj  'Handle))
                                           (deg-poly-touch-block-base-p
                                             trunkObj
                                             blkObj2
                                             (DEG:CFG-TOL-NUM-OR 'DG_P1_TOL 3.0))
                                           (equal (get-linye-numarasýi-from-block blkObj2)
                                                  (get-linye-numarasýi-from-block blkObj))
                                      )
                                    (setq chainBlocks (cons blkObj2 chainBlocks))
                                  )
                                  (setq j (1+ j))
                                )
                              )
                            )

                            (setq adetFactor 1)
                            (foreach b chainBlocks
                              (setq adetRaw (get-adet-from-block b))
                              (if (> adetRaw 0)
                                (if (= adetFactor 1)
                                  (setq adetFactor adetRaw)
                                  (if (> adetRaw adetFactor)
                                    (setq adetFactor adetRaw)
                                  )
                                )
                              )
                            )

                            (setq layerName (norm-layer (vlax-get trunkObj 'Layer)))
                            (setq toplamx nil)
                            (if (deg--layer-is-data-tv-tel layerName)
                              (setq toplamx (* toplam adetFactor))
                            )

                            (setq dataList
                                  (append dataList
                                          (deg-build-data-rows-by-linye chainBlocks layerName mesafe len mesafe toplam nil)))

                            (if testMode
                              (deg-make-circle (deg-get-inspt blkObj) tolDalSingle)
                            )
                          )
                        )
                      )
                    )
                  )
                )

                (setq i (1+ i))
              )
            )
          )


          
          (setq directRefRows '())
          (if (and blkSS refInfos)
            (progn
              (setq j 0)
              (while (< j (sslength blkSS))
                (setq blkEnt (ssname blkSS j)
                      blkObj (vlax-ename->vla-object blkEnt)
                      blkName (deg-block-name blkObj))

                (if (and blkName (wcmatch blkName "E_*"))
                  (progn
                    (setq tolReportLocal (deg-block-tol (if (= blkName (DEG:VAL 'P1)) (DEG:CFG-TOL-NUM-OR 'DG_P1_TOL 3.0) tolReport) blkObj))

                    (setq bestRefObj2 nil
                          bestRefPt2  nil
                          bestRefD2   nil)

                    (foreach info refInfos
                      (setq robj (car info))
                      (if (deg-poly-touch-block-base-p robj blkObj tolReportLocal)
                        (progn
                          (setq insPt (deg-get-inspt blkObj))
                          (setq cpt   (deg-safe-closest-point robj insPt))
                          (setq candD (distance insPt cpt))
                          (if (or (not bestRefD2) (< candD bestRefD2))
                            (setq bestRefD2  candD
                                  bestRefObj2 robj
                                  bestRefPt2  cpt)
                          )
                        )
                      )
                    )

                    (if bestRefObj2
                      (progn
                        (setq info2 (ref-find-info bestRefObj2 refInfos))
                        (if info2
                          (progn
                            (setq baseParam (cadr info2)
                                  baseDist  (caddr info2))

                            (setq paramCP (deg-safe-dist-at-point bestRefObj2 bestRefPt2))
                            (setq mesafe  (+ baseDist (abs (- paramCP baseParam))))
                            (setq len     0.0)
                            (setq toplam  mesafe)
                            (setq extraBlocks (deg-ss-blocks-touching-poly bestRefObj2 blkSS tolReportLocal blkObj))
                            (setq chainBlocks (deg-uniq-vla-by-handle (cons blkObj extraBlocks)))
                            (setq layerName (norm-layer (vlax-get bestRefObj2 'Layer)))
                            (setq kitLayerP (wcmatch (deg-norm layerName) "*KIT*,E_ANAHTAR_HATTI"))

                            ;; Dal satirinda kullanilmis ortak kok blogunu ana hat
                            ;; satirinda ikinci kez raporlama.
                            (setq myBlocks '())
                            (foreach b chainBlocks
                              (setq hB (vlax-get b 'Handle)
                                    writtenKey
                                      (deg--dp-block-written-key hB layerName))
                              (if (not (member writtenKey *DEG-BLOCK-WRITTEN*))
                                (progn
                                  (setq myBlocks (cons b myBlocks))
                                  (setq *DEG-BLOCK-WRITTEN*
                                    (cons writtenKey *DEG-BLOCK-WRITTEN*))
                                )
                              )
                            )
                            (if myBlocks
                              (setq directRefRows
                                (append directRefRows
                                  (deg-build-data-rows-by-linye
                                    myBlocks layerName mesafe len mesafe toplam kitLayerP)))
                            )
                          )
                        )
                      )
                    )
                  )
                )

                (setq j (1+ j))
              )
            )
          )

          (if directRefRows
            (setq dataList (append dataList (reverse directRefRows)))
          )


(setq dataList
                (append dataList
                        (deg-build-knx-chain testMode blkRefObj ss blkSS)))

          (setq sortedList
            (vl-sort dataList
              '(lambda (a b / ka kb pa pb na nb)
                 (setq ka (parse-linye-key (car a))
                       kb (parse-linye-key (car b))
                       pa (car ka)
                       pb (car kb)
                       na (cdr ka)
                       nb (cdr kb))
                 (cond
                   ((< (strcase pa) (strcase pb)) T)
                   ((> (strcase pa) (strcase pb)) nil)
                   (T (< na nb))))))
        )
      )
    )
  )
  sortedList
)

(defun sanitize-filename (name / res i c)
  (if (not name) (setq name "output"))
  (setq name (vl-string-translate "\n\r\t" "   " name))
  (setq res "")
  (setq i 1)
  (while (<= i (strlen name))
    (setq c (substr name i 1))
    (if (wcmatch c "[\\/:*?\"<>|]")
      (setq c "_")
    )
    (setq res (strcat res c))
    (setq i (1+ i))
  )
  (setq res (vl-string-trim " " res))
  (if (= res "") (setq res "output"))
  res
)



(defun deg--blank? (s /)
  (or (null s) (= (vl-string-trim " \t\r\n" s) ""))
)

(defun deg--layer-is-priz-or-lighting (layer / n)
  (setq n (norm-layer layer))
  (or (member n (DEG:VALS '(B2 B4 B1 B3 A3 A5 A2 A4 G2 G4 G1 G3 C1 C2 C3 C4)))
      (DEGP--lighting-layer-name-p n))
)

(defun deg--layer-is-data (layer / u lst)
  (setq u (deg--norm-tr layer))
  (setq lst (mapcar 'deg--norm-tr (DEG:VALS '(C1 C2 C3 C4))))
  (or (wcmatch u (DEG:VAL 'C9))
      (member u lst)
  )
)

(defun deg-clear-deg-done-xdata ( / ss i e ed)
  (regapp (DEG:VAL 'R1))
  (setq ss (ssget "X" '((0 . "LWPOLYLINE"))))
  (if ss
    (progn
      (setq i 0)
      (while (< i (sslength ss))
        (setq e (ssname ss i))
        (setq ed (entget e (DEG:VALS '(R1))))
        (if (assoc -3 ed)
          (progn
            (setq ed (vl-remove (assoc -3 ed) ed))
            (entmod ed)
            (entupd e)
          )
        )
        (setq i (1+ i))
      )
    )
  )
  (princ)
)

(defun deg-reset-session ( )
  (setq *deg-dallar* nil)
  (setq *degt-dallar* nil)
  (setq *deg-visited* nil)
  (setq *degt-visited* nil)
  (setq *deg-done* nil)
  (setq *degt-done* nil)
  (setq *deg-loop-cache* nil)
  (setq *deg-dal-cache* nil)

  (setq *deg-blk-visited* nil)
  (setq *degt-blk-visited* nil)
  (setq *deg-block-cache* nil)
  (setq *degt-block-cache* nil)

  (setq *DEG-BLOCK-WRITTEN* nil)
  (setq *degRefChainEnts* nil)
  (setq *degn-last-idx* nil)
  (setq *degn-last-poly* nil)

  (setq *deg-ref-grid* nil)

  (princ)
)

(defun DEG:PLAN-UNIT-KEY (/ v)
  (setq v (strcase (DEGDO--trim (DEG:CFG-GET 'PLAN_UNIT))))
  (cond
    ((= v "CM") "cm")
    ((or (= v "METRE") (= v "M")) "m")
    (T "mm")
  )
)

(defun DEG:LEN-DIVISOR (/ u)
  (setq u (DEG:PLAN-UNIT-KEY))
  (cond
    ((= u "mm") 1000.0)
    ((= u "cm") 100.0)
    (T 1.0)
  )
)

(defun DEG:LEN-CONVERT (v / x)
  (cond
    ((= (type v) 'STR)
      (setq x (atof (vl-string-subst "." "," v)))
    )
    ((numberp v)
      (setq x (float v))
    )
    (T
      (setq x 0.0)
    )
  )
  (/ x (DEG:LEN-DIVISOR))
)

(defun DEG:LEN-UNIT-LABEL ()
  (DEG:PLAN-UNIT-KEY)
)

(defun DEG:LEN-HEADER (label)
  (strcat label " (" (DEG:LEN-UNIT-LABEL) ")")
)

(defun DEG:DP-LEN-STR (v / x s)
  (setq x (DEG:LEN-CONVERT v))
  (if (< (abs x) 1.0)
    (progn
      (setq s (rtos x 2 2))
      (vl-string-subst "," "." s)
    )
    (itoa (deg-fmt-int v))
  )
)

(defun deg-fmt3 (v / s)
  (setq s (rtos (DEG:LEN-CONVERT v) 2 3))
  (vl-string-subst "," "." s)
)





(defun deg--pad3 (n / s)
  (setq s (itoa n))
  (cond
    ((= (strlen s) 1) (strcat "00" s))
    ((= (strlen s) 2) (strcat "0" s))
    (T s)
  )
)

(defun deg-fmt3fixed (v / x sgn ip fp n)
  (setq x (DEG:LEN-CONVERT v))
  (setq sgn (if (< x 0.0) "-" ""))
  (setq x (abs x))
  (setq n (fix (+ (* x 1000.0) 0.5)))
  (setq ip (fix (/ n 1000)))
  (setq fp (rem n 1000))
  (strcat sgn (itoa ip) "," (deg--pad3 fp))
)

(defun deg-fmt3t (v)
  (deg-fmt3fixed v)
)







(defun deg-excel-format-cd-3dec (csvPath / xl wbs wb ws rng)
  (vl-load-com)
  (if (and csvPath (/= csvPath ""))
    (progn
      (setq xl (vl-catch-all-apply 'vlax-get-or-create-object (list "Excel.Application")))
      (if (not (vl-catch-all-error-p xl))
        (progn
          (vlax-put-property xl 'Visible :vlax-true)
          (vlax-put-property xl 'DisplayAlerts :vlax-false)

          (setq wbs (vlax-get-property xl 'Workbooks))
          (setq wb  (vl-catch-all-apply 'vlax-invoke-method (list wbs 'Open csvPath)))
          (if (vl-catch-all-error-p wb)
            (princ "\n\nExcel CSV açýlamadý.")
            (progn
              (setq ws (vlax-get-property wb 'ActiveSheet))
              (setq rng (vlax-invoke-method ws 'Range "C:D"))
              (vlax-put-property rng 'NumberFormat "0.000")
              (vlax-release-object rng)
            )
          )
        )
        (princ "\n\nExcel COM baþlatýlamadý.")
      )
    )
  )
  (princ)
)

(defun deg-fmt-int (v / x)
  (setq x (DEG:LEN-CONVERT v))
  (if (>= x 0.0)
    (fix (+ x 0.5))
    (- (fix (+ (abs x) 0.5)))
  )
)

(defun deg--sorti-metraj (row / s bm)
  (setq s  (nth 2 row)
        bm (nth 4 row))
  (+ (if (numberp s)  s  0.0)
     (if (numberp bm) bm 0.0))
)

(defun deg-csv-join-fields (lst / out x)
  (setq out "")
  (foreach x lst
    (setq out
          (if (= out "")
            (if x x "")
            (strcat out ";" (if x x ""))))
  )
  out
)

(defun deg-csv-counted-item->pair (s / txt len i ch cnt name)
  (setq txt (vl-string-trim " \t\r\n" (if s s "")))
  (setq len (strlen txt)
        i   1
        cnt "")
  (while (and (<= i len)
              (setq ch (substr txt i 1))
              (>= (ascii ch) 48)
              (<= (ascii ch) 57))
    (setq cnt (strcat cnt ch)
          i   (1+ i))
  )
  (if (and (> (strlen cnt) 0)
           (<= i len)
           (or (= (substr txt i 1) "x")
               (= (substr txt i 1) "X")))
    (setq name (vl-string-trim " \t\r\n" (substr txt (1+ i))))
    (progn
      (setq cnt  "")
      (setq name txt)
    )
  )
  (list cnt name)
)

(defun deg-csv-counted-string->flat-list (s / items item out pair)
  (setq out '())
  (if (and s (/= (vl-string-trim " \t\r\n" s) ""))
    (progn
      (setq items (degk--split-commas s))
      (foreach item items
        (if (/= (vl-string-trim " \t\r\n" item) "")
          (progn
            (setq pair (deg-csv-counted-item->pair item))
            (setq out  (append out pair))
          )
        )
      )
    )
  )
  out
)

(defun deg-csv-counted-list->flat-list (lst / item out pair)
  (setq out '())
  (foreach item lst
    (if (/= (vl-string-trim " \t\r\n" (if item item "")) "")
      (progn
        (setq pair (deg-csv-counted-item->pair item))
        (setq out  (append out pair))
      )
    )
  )
  out
)

(defun deg-csv-counted-flat-list->fields (flat pairCount / out n)
  (setq out (if flat flat '()))
  (setq n   (fix (/ (length out) 2)))
  (while (< n pairCount)
    (setq out (append out (list "" ""))
          n   (1+ n))
  )
  (deg-csv-join-fields out)
)

(defun deg-csv-counted-string->fields (s / flat)
  (setq flat (deg-csv-counted-string->flat-list s))
  (deg-csv-counted-flat-list->fields flat (fix (/ (length flat) 2)))
)

(defun deg-csv-counted-list->fields (lst / flat)
  (setq flat (deg-csv-counted-list->flat-list lst))
  (deg-csv-counted-flat-list->fields flat (fix (/ (length flat) 2)))
)

(defun deg-csv-build-paired-headers (prefix pairCount / out i)
  (setq out '()
        i   1)
  (while (<= i pairCount)
    (setq out (append out (list (strcat prefix (itoa i) " Adet")
                                (strcat prefix (itoa i) " Adi")))
          i   (1+ i))
  )
  (deg-csv-join-fields out)
)


(defun deg--norm-tr (s / tmp)
  (if (null s) ""
    (progn
      (setq tmp (vl-princ-to-string s))
      (setq tmp (vl-string-translate "ÝIý" "iii" tmp))
      (strcase tmp)
    )
  )
)

(defun deg--is-cctv-kartli-layer (layer / n)
  (setq n (deg--norm-tr layer))
  (DEGQ:_cctv-layer-name-p n)
)

(defun deg-detect-ref-layer (blkRefObj / ss i ent obj layerName insPt candPt candD bestRefObj bestRefD)
  (vl-load-com)
  (setq ss (ssget "_X" '((0 . "LWPOLYLINE"))))
  (setq bestRefObj nil bestRefD nil)

  (if ss
    (progn
      (setq insPt (deg-get-inspt blkRefObj))
      (setq i 0)
      (while (< i (sslength ss))
        (setq ent (ssname ss i)
              obj (vlax-ename->vla-object ent)
              layerName (norm-layer (vlax-get obj 'Layer)))

        (if (or (= layerName (DEG:VAL 'B2))
                (= layerName (DEG:VAL 'B4))
                (= layerName (DEG:VAL 'A3))
                (= layerName (DEG:VAL 'A5))
                (= layerName (DEG:VAL 'E3))
                (= layerName (DEG:VAL 'F4))
                (= layerName (DEG:VAL 'C3))
                (= layerName (DEG:VAL 'C7))
                (= layerName (DEG:VAL 'E5))
                (= layerName (DEG:VAL 'F2))
                (= layerName (DEG:VAL 'C8))
                (= layerName (DEG:VAL 'C4))
                (= layerName (DEG:VAL 'G2))
                (= layerName (DEG:VAL 'G4))
                (= layerName (DEG:VAL 'H2))
                (= layerName (DEG:VAL 'D4))
                (= layerName (DEG:VAL 'D3))
                (= layerName (DEG:VAL 'H4)))
          (progn
            (setq candPt (deg-safe-closest-point obj insPt))
            (if (deg-endpoint-touch? obj blkRefObj 50.0)
              (progn
                (setq candD (distance candPt insPt))
                (if (or (not bestRefD) (< candD bestRefD))
                  (progn
                    (setq bestRefD candD)
                    (setq bestRefObj obj)
                  )
                )
              )
            )
          )
        )
        (setq i (1+ i))
      )
    )
  )

  (if bestRefObj
    (norm-layer (vlax-get bestRefObj 'Layer))
    nil
  )
)

(defun deg-popup-results (sortedList title / msg cnt i row total v)
  (setq cnt (length sortedList))
  (setq total 0.0)
  (foreach row sortedList
    (setq v (nth 5 row))
    (if (numberp v) (setq total (+ total v)))
  )

  (setq msg (strcat title "\nSatýr: " (itoa cnt) "\n\n"))
  (setq i 0)
  (foreach row sortedList
    (if (< i 25)
      (progn
        (setq msg
          (strcat msg
                  (if (nth 0 row) (nth 0 row) "") " | "
                  (if (nth 1 row) (nth 1 row) "") " | "
                  (if (nth 5 row) (strcat (DEG:DP-LEN-STR (nth 5 row)) (if *degLastIsCCTV* " (m)" (strcat " " (DEG:LEN-UNIT-LABEL)))) (if *degLastIsCCTV* "0 (m)" (strcat "0 " (DEG:LEN-UNIT-LABEL))))
                  "\n"
          )
        )
        (setq i (1+ i))
      )
    )
  )
  (if (> cnt 25)
    (setq msg (strcat msg "\n... (" (itoa (- cnt 25)) " satýr daha)\n"))
    (setq msg (strcat msg "\n"))
  )

  (setq msg
    (strcat msg
            "==============================\n" "TOPLAM: " (DEG:DP-LEN-STR total) (if *degLastIsCCTV* " (m)" (strcat " " (DEG:LEN-UNIT-LABEL))) "\n" "==============================\n"
    )
  )
(DEG:WIN-MESSAGE msg)
)


(defun deg-filter-out-kombine-rows (lst / out row lay n layN)
  (setq out nil)
  (foreach row lst
    (setq lay  (nth 1 row)
          n    (if lay (deg--norm-tr lay) "")
          layN (norm-layer lay))
    (if (not (or (vl-string-search "KOMBINE" (strcase n))
                 (member layN (DEGP--dp-data-comb-layers))
                 (DEG:LAYER-IN-CODES? layN '(D3 D4))))
      (setq out (cons row out))
    )
  )
  (reverse out)
)


(defun deg-nearest-vertex (plObj pickPt / ent ed typ elev pts e vd p bestPt bestD d)
  (vl-load-com)

  ;; Referans noktaya en yakin VERTEX'i bul (vlax-curve param/distance kullanmadan)
  ;; plObj: VLA-OBJECT veya ENAME
  ;; pickPt: (x y z) seçim noktasý

  (setq ent
    (cond
      ((= (type plObj) 'VLA-OBJECT) (vlax-vla-object->ename plObj))
      ((= (type plObj) 'ENAME) plObj)
      (T nil)
    )
  )

  (if (not (and ent pickPt))
    (if pickPt pickPt (list 0.0 0.0 0.0))
    (progn
      (setq ed  (entget ent))
      (setq typ (cdr (assoc 0 ed)))
      (setq elev (cdr (assoc 38 ed)))
      (if (not (numberp elev)) (setq elev 0.0))
      (if (and pickPt (= (length pickPt) 3))
        (setq pickPt (list (car pickPt) (cadr pickPt) elev))
      )
      (setq pts nil)

      (cond
        ;; LWPOLYLINE: vertexler DXF 10 gruplari
        ((= typ "LWPOLYLINE")
          (foreach vd ed
            (if (= (car vd) 10)
              (progn
                (setq p (cdr vd))
                (if (= (length p) 2)
                  (setq p (list (car p) (cadr p) elev))
                )
                (setq pts (cons p pts))
              )
            )
          )
          (setq pts (reverse pts))
        )

        ;; 2D/3D POLYLINE: VERTEX entity'lerini tara
        ((= typ "POLYLINE")
          (setq e (entnext ent))
          (while e
            (setq ed (entget e))
            (cond
              ((= (cdr (assoc 0 ed)) "VERTEX")
                (setq p (cdr (assoc 10 ed)))
                (if (= (length p) 2)
                  (setq p (list (car p) (cadr p) elev))
                )
                (setq pts (cons p pts))
                (setq e (entnext e))
              )
              ((= (cdr (assoc 0 ed)) "SEQEND")
                (setq e nil)
              )
              (T (setq e (entnext e)))
            )
          )
          (setq pts (reverse pts))
        )
      )

      (if (not pts)
        pickPt
        (progn
          (setq bestPt (car pts))
          (setq bestD  (distance bestPt pickPt))
          (foreach p (cdr pts)
            (setq d (distance p pickPt))
            (if (< d bestD)
              (progn (setq bestD d) (setq bestPt p))
            )
          )
          bestPt
        )
      )
    )
  )
)

(defun deg-make-temp-ref-block (insPt lay / bname ent)
  (vl-load-com)
  (setq bname "DEG_TMP_REF")
  (if (not (tblsearch "BLOCK" bname))
    (progn
      (entmake (list '(0 . "BLOCK") (cons 2 bname) '(70 . 0) (list 10 0.0 0.0 0.0)))
      (entmake (list '(0 . "POINT") '(8 . "0") (list 10 0.0 0.0 0.0)))
      (entmake '((0 . "ENDBLK")))
    )
  )
  (setq ent
    (entmakex
      (list '(0 . "INSERT")
            (cons 2 bname)
            (cons 8 (if lay lay "0"))
            (cons 10 insPt)
            (cons 41 1.0) (cons 42 1.0) (cons 43 1.0)
            (cons 50 0.0))
    )
  )
  ent
)

(defun deg-del-ename-safe (e)
  (if (and e (entget e)) (entdel e))
)

(defun DG_ORIG
  ( / blkEnt blkRefObj
     sortedList row
     continue
     txtEnt txtObj pageName s
     tmp
     filepath csvfile line anyBlkFound
     maxBlkPairs maxSymPairs flatBlk flatSym blkFields symFields
     scopeSel scopePolySS scopeBlkSS
  )

  (deg-reset-session)
  (deg-clear-deg-done-xdata)
  (vl-load-com)
  (setq continue T)

  (while continue
    (setq *degDGScopePolySS* nil)
    (setq *degDGScopeBlkSS*  nil)

    (setq blkEnt (entsel "\nReferans polyline'ý seçin: "))
    (if (not blkEnt)
      (progn
        (setq continue nil)
        (princ "\n\nDEG bitti (referans polyline seçilmedi).")
      )
      (progn
        (setq tmp (car blkEnt))   ;; ref polyline ename
        (setq s   (cadr blkEnt))  ;; pick point

        (if (not (and tmp
                      (wcmatch (cdr (assoc 0 (entget tmp))) "LWPOLYLINE,POLYLINE")
                      (not (DEGQ:_cctv-layer-name-p (cdr (assoc 8 (entget tmp)))))))
          (progn
            (setq continue nil)
            (if (and tmp
                     (wcmatch (cdr (assoc 0 (entget tmp))) "LWPOLYLINE,POLYLINE")
                     (DEGQ:_cctv-layer-name-p (cdr (assoc 8 (entget tmp)))))
              (princ "\n\nDG: KOMBINE raporu DP komutuna tasindi. DP komutu ile tek KOMBINE polyline secin.")
              (princ "\n\nLutfen gecerli bir polyline secin.")
            )
          )
          (progn
            (princ "\nSonra alan seçin (polyline ve blocklar): ")
            (setq scopeSel (ssget '((0 . "LWPOLYLINE,POLYLINE,INSERT"))))

            (if (not scopeSel)
              (progn
                (setq continue nil)
                (princ "\n\nDEG bitti (alan seçilmedi).")
              )
              (progn
                (setq scopePolySS (DEG:SS-FILTER-BY-TYPE scopeSel "LWPOLYLINE,POLYLINE"))
                (setq scopeBlkSS  (DEG:SS-FILTER-BY-TYPE scopeSel "INSERT"))
                (if (<= (DEG:SS-LEN scopePolySS) 0) (setq scopePolySS nil))
                (if (<= (DEG:SS-LEN scopeBlkSS) 0)  (setq scopeBlkSS  nil))
                (if (not scopePolySS) (setq scopePolySS (ssadd)))
                (if (and tmp (not (DEG:SS-CONTAINS-ENAME? scopePolySS tmp)))
                  (ssadd tmp scopePolySS)
                )
                (setq *degDGScopePolySS* scopePolySS)
                (setq *degDGScopeBlkSS*  scopeBlkSS)

                (setq txtObj (vlax-ename->vla-object tmp))     ;; ref polyline obj
                (setq pageName (deg-nearest-vertex txtObj s))  ;; refPt (x y z)
                (setq blkRefObj pageName)
                (setq *degForceRefObj* txtObj)
                (setq *degForceRefPt* pageName)

                (setq sortedList (deg-build-data nil blkRefObj))
                (setq *degForceRefObj* nil)
                (setq *degForceRefPt* nil)

            (setq txtEnt (entsel
              "\nCSV dosya ismi için TEXT'e týklayýn veya elle girmek için Enter (boþ Enter = bitir): "
            ))

            (if txtEnt
              (progn
                (setq txtObj (vlax-ename->vla-object (car txtEnt)))
                (setq s      (get-entity-text txtObj))
                (if s
                  (setq pageName s)
                  (setq pageName (getstring T "\nTEXT okunamadý, dosya ismini elle yazýn: "))
                )
              )
              (progn
                (setq pageName (getstring T "\nCSV dosya ismini yazýn (boþ Enter = bitir): "))
              )
            )

            (if (or (null pageName) (= pageName ""))
              (progn
                (setq continue nil)
                (princ "\n\nDEG bitti (dosya ismi girilmedi).")
              )
              (progn
                (setq pageName (sanitize-filename pageName))


                (if (not sortedList)
                  (princ "\n\nBu referans için hesaplanacak veri bulunamad.")
                  (progn
                    (setq *degFolder*
                      (DEGDO--csv-folder *degFolder* pageName "CSV kaydedilecek konumu secin")
                    )
                    (if (not *degFolder*)
                      (progn
                        (setq continue nil)
                        (princ "\n\nDO > KAYIT sayfasinda klasor lokasyonu girin.")
                      )
                    )
                    (if (and continue *degFolder*)
                      (progn
                        (setq filepath (DEGDO--csv-filepath *degFolder* pageName))
                        (setq csvfile  (open filepath "w"))

                        (if csvfile
                          (progn
                            (setq maxBlkPairs 0
                                  maxSymPairs 0)

                            (foreach row sortedList
                              (if (not (and (deg--layer-is-priz-or-lighting (nth 1 row))
                                            (deg--blank? (nth 0 row))
                                            (not (deg--layer-is-data (nth 1 row)))
                                            (not (wcmatch (deg--norm-tr (nth 1 row)) "*KIT*"))))
                                (progn
                                  (setq flatBlk (deg-csv-counted-string->flat-list (nth 7 row))
                                        flatSym (deg-csv-counted-list->flat-list   (nth 8 row)))
                                  (if (> (fix (/ (length flatBlk) 2)) maxBlkPairs)
                                    (setq maxBlkPairs (fix (/ (length flatBlk) 2))))
                                  (if (> (fix (/ (length flatSym) 2)) maxSymPairs)
                                    (setq maxSymPairs (fix (/ (length flatSym) 2))))
                                )
                              )
                            )

                            (if (< maxBlkPairs 1) (setq maxBlkPairs 1))
                            (if (< maxSymPairs 1) (setq maxSymPairs 1))

                            (write-line
                              (strcat
                                (cond
                                  (*degHideSortiToplam*
                                    (if *degHideToplamx*
                                      "Linye;Layer" (strcat "Linye;Layer;" (DEG:LEN-HEADER "ToplamxAdet"))
                                    )
                                  )
                                  (T
                                    (if *degHideToplamx*
                                      (strcat "Linye;Layer;Sorti Metraj (m);Toplam (m)")
                                      (strcat "Linye;Layer;Sorti Metraj (m);Toplam (m);" (DEG:LEN-HEADER "ToplamxAdet"))
                                    )
                                  )
                                )
                                ";"
                                (deg-csv-build-paired-headers "BagliBlok" maxBlkPairs)
                                ";"
                                (deg-csv-build-paired-headers "Sembol" maxSymPairs)
                              )
                              csvfile)

                            (setq anyBlkFound nil)

                            (foreach row sortedList
                              (if (not (and (deg--layer-is-priz-or-lighting (nth 1 row))
                                            (deg--blank? (nth 0 row))
                                            (not (deg--layer-is-data (nth 1 row)))
                                            (not (wcmatch (deg--norm-tr (nth 1 row)) "*KIT*"))))
                                (progn
                                  (setq line
                                    (cond
                                      (*degHideSortiToplam*
                                        (if *degHideToplamx*
                                          (strcat
                                            (nth 0 row) ";"
                                            (nth 1 row))
                                          (strcat
                                            (nth 0 row) ";"
                                            (nth 1 row) ";"
                                            (if (nth 6 row) (itoa (deg-fmt-int (nth 6 row))) ""))
                                        )
                                      )
                                      (T
                                        (if *degHideToplamx*
                                          (strcat
                                            (nth 0 row) ";"
                                            (nth 1 row) ";"
                                            (if (deg--sorti-metraj row) (itoa (deg-fmt-int (deg--sorti-metraj row))) "") ";"
                                            (itoa (deg-fmt-int (nth 5 row))))
                                          (strcat
                                            (nth 0 row) ";"
                                            (nth 1 row) ";"
                                            (if (deg--sorti-metraj row) (itoa (deg-fmt-int (deg--sorti-metraj row))) "") ";"
                                            (itoa (deg-fmt-int (nth 5 row))) ";"
                                            (if (nth 6 row) (itoa (deg-fmt-int (nth 6 row))) ""))
                                        )
                                      )
                                    ))
                                  (setq blkFields (deg-csv-counted-flat-list->fields
                                                    (deg-csv-counted-string->flat-list (nth 7 row))
                                                    maxBlkPairs)
                                        symFields (deg-csv-counted-flat-list->fields
                                                    (deg-csv-counted-list->flat-list (nth 8 row))
                                                    maxSymPairs))
                                  (setq line
                                        (strcat line
                                                ";"
                                                blkFields
                                                ";"
                                                symFields))
                                  (if (or (and (nth 7 row) (not (deg--blank? (nth 7 row))))
                                          (and (nth 8 row) (> (length (nth 8 row)) 0)))
                                    (setq anyBlkFound T)
                                  )
                                  (write-line line csvfile)
                                )
                              )
                            )



                            (close csvfile)
                            (princ)
                            (princ (strcat "\nOluþturulan dosya: " filepath))
                          )
                          (princ (strcat "\nDosya açýlamadý / oluþturulamadý: " filepath))
                        )
                      )
                    )
                  )
                )
              )
            )
            )
          )
        )
      )
    )
  )

  (setq *degDGScopePolySS* nil)
  (setq *degDGScopeBlkSS*  nil)
  (princ)
)
)
(defun deg-expand-loop (s / pos leftPart rightPart len i ch numL numR prefixL
                           startN endN width res n numStr)
  (if (and s (setq pos (vl-string-search ",...," s)))
    (progn
      (setq leftPart  (substr s 1 pos))
      (setq rightPart (substr s (+ pos 6)))

      (setq len (strlen leftPart)
            numL ""
            i   len)
      (while (and (> i 0)
                  (setq ch (substr leftPart i 1))
                  (>= (ascii ch) 48) (<= (ascii ch) 57))
        (setq numL (strcat ch numL))
        (setq i (1- i))
      )
      (setq prefixL (substr leftPart 1 i))

      (setq len (strlen rightPart)
            numR ""
            i   1)
      (while (and (<= i len)
                  (setq ch (substr rightPart i 1))
                  (>= (ascii ch) 48) (<= (ascii ch) 57))
        (setq numR (strcat numR ch))
        (setq i (1+ i))
      )

      (if (and (> (strlen numL) 0) (> (strlen numR) 0))
        (progn
          (setq startN (atoi numL)
                endN   (atoi numR)
                width  (max (strlen numL) (strlen numR)))
          (if (< startN endN)
            (progn
              (setq res '()
                    n   startN)
              (while (<= n endN)
                (setq numStr (itoa n))
                (while (< (strlen numStr) width)
                  (setq numStr (strcat "0" numStr))
                )
                (setq res (cons (strcat prefixL numStr) res))
                (setq n (1+ n))
              )
              (reverse res)
            )
            (list s)
          )
        )
        (list s)
      )
    )
    (if s (list s) '())
  )
)

(defun get-loop-adi-from-block (blkObj / attList att tag val res)
  (setq res nil)
  (if (= :vlax-true (vla-get-HasAttributes blkObj))
    (progn
      (setq attList (vlax-invoke blkObj 'GetAttributes))
      (foreach att attList
        (setq tag (strcase (vla-get-TagString att)))
        (setq val (vla-get-TextString att))
        (if (or (= tag "SIRA_NO")
                (= tag "SIRA NO"))
          (setq res val)
        )
      )
    )
  )
  res
)


(vl-load-com)

(if (not (boundp '*degn-last-poly*)) (setq *degn-last-poly* nil))
(if (not (boundp '*degn-last-idx*))  (setq *degn-last-idx*  nil))

(DEG:TOL-REFRESH-DN-GLOBALS)
(setq DEGN-DEGA--DRAW-TOL   nil)      ;; T: çember çiz, nil: çizme
(setq DEGN-DEGA--TOL-LAYER  "DEGA_TOL")

(defun DEGN-DEGA--norm-blkname (s / u)
  (setq u (if s (strcase s) ""))
  (setq u (vl-string-translate " -." "___" u))
  u
)

(defun DEGN-DEGA--IS-E-DOSEMEYE-INIS (name / u)
  (setq u (DEGN-DEGA--norm-blkname name))
  (or
    (wcmatch u (DEG:VAL 'M3))
    (wcmatch u (DEG:VAL 'M4))
  )
)

(defun DEGN-DEGA--blockname (ename / ed)
  (setq ed (entget ename))
  (if (assoc 2 ed) (cdr (assoc 2 ed)) "")
)

(defun DEGN-DEGA--upper (s) (if s (strcase s) ""))

(defun DEGN-DEGA--vla (e) (DEG:VLA e))

(defun DEGN-DEGA--dist2 (a b)
  (+ (expt (- (car a) (car b)) 2.0)
     (expt (- (cadr a) (cadr b)) 2.0))
)

(defun DEGN-DEGA--eq-tol (p q tol)
  (<= (DEGN-DEGA--dist2 p q) (* tol tol))
)

(defun DEGN-DEGA--layer-ok-p (ent / lay)
  (setq lay (DEGN-DEGA--upper (cdr (assoc 8 (entget ent)))))
  (or (DEG:LAYER-IN-CODES? lay '(C1 C2 C3 C4 E1 E2 E3 E5 F1 F2 F3 F4))
      (wcmatch lay (DEG:VAL 'C9))
      (wcmatch lay (DEG:VAL 'F5))
      (wcmatch lay (DEG:VAL 'H5))
      (DEGQ:_cctv-layer-name-p lay)
      (wcmatch lay (DEG:VAL 'E4)))
)


;; TV + TELEFON layer kontrolu (DN DATA host seçiminde disari birakmak için)
(defun DEGN-DEGA--layer-tv-tel-p (lay / u)
  (setq u (DEGN-DEGA--upper lay))
  (or (DEG:LAYER-IN-CODES? u '(E1 E2 E3 E5 F1 F2 F3 F4))
      (wcmatch u (DEG:VAL 'F5))  ;; *TV*
      (wcmatch u (DEG:VAL 'E4))  ;; *TELEFON*
  )
)
;; DATA mode strict layer filter (only DATA/CCTV/KARTLI)
(setq DEGN-DEGA--DATA-ONLY nil)
(setq DEGN-DEGA--SCOPE-ACTIVE nil)
(setq DEGN-DEGA--SCOPE-POLYS nil)
(setq DEGN-DEGA--SCOPE-BLOCKS nil)
(setq DEGN-DEGA--SCOPE-POLY-HANDLES nil)
(setq DEGN-DEGA--SCOPE-BLOCK-HANDLES nil)

(defun DEGN-DEGA--scope-reset ()
  (setq DEGN-DEGA--SCOPE-ACTIVE nil)
  (setq DEGN-DEGA--SCOPE-POLYS nil)
  (setq DEGN-DEGA--SCOPE-BLOCKS nil)
  (setq DEGN-DEGA--SCOPE-POLY-HANDLES nil)
  (setq DEGN-DEGA--SCOPE-BLOCK-HANDLES nil)
)

(defun DEGN-DEGA--scope-handle (e)
  (if (and e (= (type e) 'ENAME))
    (cdr (assoc 5 (entget e)))
    nil
  )
)

(defun DEGN-DEGA--scope-add-poly (e / h typ)
  (if (and e (= (type e) 'ENAME))
    (progn
      (setq typ (cdr (assoc 0 (entget e))))
      (if (member typ '("LWPOLYLINE" "POLYLINE"))
        (progn
          (setq h (DEGN-DEGA--scope-handle e))
          (if (and h (not (member h DEGN-DEGA--SCOPE-POLY-HANDLES)))
            (progn
              (setq DEGN-DEGA--SCOPE-POLY-HANDLES (cons h DEGN-DEGA--SCOPE-POLY-HANDLES))
              (setq DEGN-DEGA--SCOPE-POLYS (cons e DEGN-DEGA--SCOPE-POLYS))
            )
          )
        )
      )
    )
  )
)

(defun DEGN-DEGA--scope-add-block (e / h typ)
  (if (and e (= (type e) 'ENAME))
    (progn
      (setq typ (cdr (assoc 0 (entget e))))
      (if (= typ "INSERT")
        (progn
          (setq h (DEGN-DEGA--scope-handle e))
          (if (and h (not (member h DEGN-DEGA--SCOPE-BLOCK-HANDLES)))
            (progn
              (setq DEGN-DEGA--SCOPE-BLOCK-HANDLES (cons h DEGN-DEGA--SCOPE-BLOCK-HANDLES))
              (setq DEGN-DEGA--SCOPE-BLOCKS (cons e DEGN-DEGA--SCOPE-BLOCKS))
            )
          )
        )
      )
    )
  )
)

(defun DEGN-DEGA--scope-set-from-ss (ss seed / i e typ)
  (DEGN-DEGA--scope-reset)
  (setq DEGN-DEGA--SCOPE-ACTIVE T)
  (if ss
    (progn
      (setq i 0)
      (while (< i (sslength ss))
        (setq e (ssname ss i))
        (setq typ (cdr (assoc 0 (entget e))))
        (cond
          ((member typ '("LWPOLYLINE" "POLYLINE")) (DEGN-DEGA--scope-add-poly e))
          ((= typ "INSERT") (DEGN-DEGA--scope-add-block e))
        )
        (setq i (1+ i))
      )
    )
  )
  (DEGN-DEGA--scope-add-poly seed)
  (setq DEGN-DEGA--SCOPE-POLYS (reverse DEGN-DEGA--SCOPE-POLYS))
  (setq DEGN-DEGA--SCOPE-BLOCKS (reverse DEGN-DEGA--SCOPE-BLOCKS))
)

(defun DEGN-DEGA--scope-poly-p (e / h)
  (if (not DEGN-DEGA--SCOPE-ACTIVE)
    T
    (progn
      (setq h (DEGN-DEGA--scope-handle e))
      (if (and h (member h DEGN-DEGA--SCOPE-POLY-HANDLES)) T nil)
    )
  )
)

(defun DEGN-DEGA--scope-block-p (e / h)
  (if (not DEGN-DEGA--SCOPE-ACTIVE)
    T
    (progn
      (setq h (DEGN-DEGA--scope-handle e))
      (if (and h (member h DEGN-DEGA--SCOPE-BLOCK-HANDLES)) T nil)
    )
  )
)

(defun DEGN-DEGA--scope-ss-to-list (ss / out i)
  (setq out nil)
  (if ss
    (progn
      (setq i 0)
      (while (< i (sslength ss))
        (setq out (cons (ssname ss i) out))
        (setq i (1+ i))
      )
    )
  )
  (reverse out)
)

(defun DEGN-DEGA--scope-ss-from-list (lst / ss e)
  (setq ss (ssadd))
  (foreach e lst
    (if (and e (= (type e) 'ENAME))
      (ssadd e ss)
    )
  )
  ss
)

(defun DEGN-DEGA--layer-data-only-str-p (lay / u)
  (setq u (DEGN-DEGA--upper lay))
  (or (wcmatch u (DEG:VAL 'C9))
      (DEGQ:_cctv-layer-name-p u)
      (wcmatch u (DEG:VAL 'H5)))
)

(defun DEGN-DEGA--layer-data-only-p (ent / lay)
  (setq lay (cdr (assoc 8 (entget ent))))
  (DEGN-DEGA--layer-data-only-str-p lay)
)

(defun DEGN-DEGA--all-polylines-data ( / lst e src)
  (setq lst '())
  (if DEGN-DEGA--SCOPE-ACTIVE
    (setq src DEGN-DEGA--SCOPE-POLYS)
    (setq src (DEGN-DEGA--scope-ss-to-list (ssget "X" '((0 . "LWPOLYLINE,POLYLINE")))))
  )
  (foreach e src
    (if (DEGN-DEGA--layer-data-only-p e)
      (setq lst (cons e lst))
    )
  )
  lst
)
(defun DEGN-DEGA--endpoints (pl / o)
  (setq o (DEGN-DEGA--vla pl))
  (list (vlax-curve-getStartPoint o)
        (vlax-curve-getEndPoint   o))
)

(defun DEGN-DEGA--ptparam (pl pt / o p3 cp par d sp ep spPar epPar)
  (setq o (DEGN-DEGA--vla pl))
  (setq p3 (cond
             ((and (listp pt) (= (length pt) 3)) pt)
             ((and (listp pt) (= (length pt) 2)) (list (car pt) (cadr pt) 0.0))
             (T (list 0.0 0.0 0.0))))
  (setq cp (deg-safe-closest-point o p3))
  (if cp
    (setq par
      (vl-catch-all-apply
        'vlax-curve-getParamAtPoint (list o cp))))
  (if (not (numberp par))
    (progn
      (if cp
        (setq d
          (vl-catch-all-apply
            'vlax-curve-getDistAtPoint (list o cp))))
      (if (numberp d)
        (setq par
          (vl-catch-all-apply
            'vlax-curve-getParamAtDist (list o d))))
    )
  )
  (if (not (numberp par))
    (progn
      (setq sp
              (vl-catch-all-apply
                'vlax-curve-getStartPoint (list o))
            ep
              (vl-catch-all-apply
                'vlax-curve-getEndPoint (list o))
            spPar
              (vl-catch-all-apply
                'vlax-curve-getStartParam (list o))
            epPar
              (vl-catch-all-apply
                'vlax-curve-getEndParam (list o)))
      (if (and (listp sp) (listp ep)
               (numberp spPar) (numberp epPar))
        (setq par
          (if (<= (distance p3 sp) (distance p3 ep))
            spPar epPar))
      )
    )
  )
  (if (numberp par) par nil)
)
(defun DEGN-DEGA--distAtParam (pl par / o d p)
  (setq o (DEGN-DEGA--vla pl))
  (if (not (numberp par)) (setq par 0.0))
  (setq d (vl-catch-all-apply 'vlax-curve-getDistAtParam (list o par)))
  (if (not (numberp d))
    (progn
      (setq p
        (vl-catch-all-apply
          'vlax-curve-getPointAtParam (list o par)))
      (if (not (vl-catch-all-error-p p))
        (setq d
          (vl-catch-all-apply
            'vlax-curve-getDistAtPoint (list o p))))
    )
  )
  (if (numberp d) d 0.0)
)

(defun DEGN-DN--pick-on-polyline (pl pickPt / o p3 wcsPt cp)
  ;; ENTSEL noktasi UCS'dedir. Once WCS'ye cevir, sonra secilen
  ;; polyline uzerine izduser; vertexlere kus ucusu karsilastirma yapma.
  (setq o (DEGN-DEGA--vla pl)
        p3
          (cond
            ((and (listp pickPt) (= (length pickPt) 3)) pickPt)
            ((and (listp pickPt) (= (length pickPt) 2))
              (list (car pickPt) (cadr pickPt) 0.0))
            (T '(0.0 0.0 0.0)))
        wcsPt (vl-catch-all-apply 'trans (list p3 1 0)))
  (if (vl-catch-all-error-p wcsPt)
    (setq wcsPt p3)
  )
  (setq cp
    (if o
      (vl-catch-all-apply 'deg-safe-closest-point (list o wcsPt))))
  (if (or (null cp) (vl-catch-all-error-p cp))
    wcsPt
    (deg-pt3 cp)
  )
)

(defun DEGN-DEGA--uniq-pts (pts tol / out p)
  (setq out '())
  (foreach p pts
    (if (not (vl-some '(lambda (x) (DEGN-DEGA--eq-tol p x tol)) out))
      (setq out (cons p out))
    )
  )
  out
)

(defun DEGN-DEGA--all-polylines ( / lst e src)
  (setq lst '())
  (if DEGN-DEGA--SCOPE-ACTIVE
    (setq src DEGN-DEGA--SCOPE-POLYS)
    (setq src (DEGN-DEGA--scope-ss-to-list (ssget "X" '((0 . "LWPOLYLINE,POLYLINE")))))
  )
  (foreach e src
    (if (DEGN-DEGA--layer-ok-p e)
      (setq lst (cons e lst))
    )
  )
  lst
)
(defun DEGN-DEGA--pt->curve-hit (pt pl tol / o cp d)
  (setq o  (DEGN-DEGA--vla pl))
  (setq cp (deg-safe-closest-point o pt))
  (setq d  (distance (list (car pt) (cadr pt) 0.0)
                     (list (car cp) (cadr cp) 0.0)))
  (if (<= d tol) (list cp d) nil) ;; (closestPoint gapDist)
)

(defun DEGN-DEGA--ensure-layer (name / doc lays)
  (setq doc  (vla-get-ActiveDocument (vlax-get-acad-object)))
  (setq lays (vla-get-Layers doc))
  (if (not (tblsearch "LAYER" name))
    (vla-add lays name))
)

(defun DEGN-DEGA--draw-circle (pt r / oldLay)
  (if DEGN-DEGA--DRAW-TOL
    (progn
      (DEGN-DEGA--ensure-layer DEGN-DEGA--TOL-LAYER)
      (setq oldLay (getvar "CLAYER"))
      (setvar "CLAYER" DEGN-DEGA--TOL-LAYER)
      (entmakex (list (cons 0 "CIRCLE")
                      (cons 40 DEGN-DEGA--TOL-LAYER)
                      (cons 10 (list (car pt) (cadr pt) 0.0))
                      (cons 40 r)))
      (setvar "CLAYER" oldLay)
    )
  )
)

(defun DEGN-DEGA--pick-start-end (pl pickPt tol / o sp ep)
  (setq o  (DEGN-DEGA--vla pl))
  (setq sp (vlax-curve-getStartPoint o))
  (setq ep (vlax-curve-getEndPoint   o))
  (cond
    ((DEGN-DEGA--eq-tol pickPt sp tol) sp)
    ((DEGN-DEGA--eq-tol pickPt ep tol) ep)
    (T (if (< (distance pickPt sp) (distance pickPt ep)) sp ep))
  )
)


(setq DEGN-DEGA--CONNS nil)

(defun DEGN-DEGA--endpoints-hit-any-chain (cand chain tol / ce p q hit pl r)
  (setq ce (DEGN-DEGA--endpoints cand))
  (setq p (car ce)  q (cadr ce))
  (setq hit nil)

  (foreach pl chain
    (if (not hit)
      (progn
        (setq r (DEGN-DEGA--pt->curve-hit p pl tol))
        (if r (setq hit (list p pl (car r) (cadr r))))
      )
    )
  )

  (if (not hit)
    (foreach pl chain
      (if (not hit)
        (progn
          (setq r (DEGN-DEGA--pt->curve-hit q pl tol))
          (if r (setq hit (list q pl (car r) (cadr r))))
        )
      )
    )
  )
  hit
)



(setq DEGN-DEGA--CONNS nil)

(defun DEGN-DEGA--endpoints-hit-any-chain (cand chain tol / ce p q hit pl r)
  (setq ce (DEGN-DEGA--endpoints cand))
  (setq p (car ce)  q (cadr ce))
  (setq hit nil)

  (foreach pl chain
    (if (not hit)
      (progn
        (setq r (DEGN-DEGA--pt->curve-hit p pl tol))
        (if r (setq hit (list p pl (car r) (cadr r))))
      )
    )
  )

  (if (not hit)
    (foreach pl chain
      (if (not hit)
        (progn
          (setq r (DEGN-DEGA--pt->curve-hit q pl tol))
          (if r (setq hit (list q pl (car r) (cadr r))))
        )
      )
    )
  )
  hit
)

(defun DEGN-DEGA--blockname (ename / ed) (setq ed (entget ename)) (if (assoc 2 ed) (cdr (assoc 2 ed)) ""))

(defun DEGN-DEGA--e_dosemeye_blocks ( / ss e out n src)
  (setq out '())
  (if DEGN-DEGA--SCOPE-ACTIVE
    (setq src DEGN-DEGA--SCOPE-BLOCKS)
    (setq src (DEGN-DEGA--scope-ss-to-list (ssget "_X" '((0 . "INSERT")))))
  )
  (foreach e src
    (setq n (DEGN-DEGA--blockname e))
    (if (DEGN-DEGA--IS-E-DOSEMEYE-INIS n)
      (setq out (cons e out))
    )
  )
  out
)
(setq DEGN-DEGA--BLCONNS nil)

(defun DEGN-DEGA--blconn-exists-p (blkPt pl / ok)
  (setq ok nil)
  (foreach x DEGN-DEGA--BLCONNS
    (if (and (not ok)
             (= (car x) "TOUCH")
             (= (caddr x) pl)
             (DEGN-DEGA--eq-tol (cadr x) blkPt 1e-6))
      (setq ok T)
    )
  )
  ok
)

(defun DEGN-DEGA--pl-touches-block-tol (plEname blkEname tol / ip hit plObj blkObj cp)
  (setq plObj  (DEGN-DEGA--vla plEname))
  (setq blkObj (DEGN-DEGA--vla blkEname))
  (setq ip (deg-get-inspt blkObj))
  (if ip
    (progn
      (setq ip (cond
                 ((and (listp ip) (= (length ip) 3)) ip)
                 ((and (listp ip) (= (length ip) 2)) (list (car ip) (cadr ip) 0.0))
                 (T (list 0.0 0.0 0.0))))
      (setq hit (DEGN-DEGA--pt->curve-hit ip plEname tol))
      (if (not hit)
        (progn
          (setq cp (block-ref-contact-point plObj blkObj tol))
          (if cp (setq hit (list cp 0.0)))
        )
      )
      hit
    )
    nil
  )
)

(defun DEGN-DEGA--chain (seed / candidates chain changed newc c hit blks blk hostFound hostPl hitB hitB2 ip touchPt gap)
  (setq DEGN-DEGA--CONNS nil)
  (setq DEGN-DEGA--BLCONNS nil)

  (setq blks (DEGN-DEGA--e_dosemeye_blocks))
  (setq candidates (vl-remove seed (if DEGN-DEGA--DATA-ONLY (DEGN-DEGA--all-polylines-data) (DEGN-DEGA--all-polylines))))
  (setq chain (list seed))
  (setq changed T)

  (while changed
    (setq changed nil)
    (setq newc '())

    (while candidates
      (setq c (car candidates))
      (setq candidates (cdr candidates))

      (setq hit (DEGN-DEGA--endpoints-hit-any-chain c chain DEGN-DEGA--TOL))
      (if hit
        (progn
          (setq chain (cons c chain))
          (setq changed T)

          (setq DEGN-DEGA--CONNS
                (cons (list c (nth 0 hit) (nth 1 hit) (nth 2 hit) (nth 3 hit)) DEGN-DEGA--CONNS))

          (DEGN-DEGA--draw-circle (nth 0 hit) DEGN-DEGA--TOL)
          (DEGN-DEGA--draw-circle (nth 2 hit) DEGN-DEGA--TOL)
        )
        (setq newc (cons c newc))
      )
    )
    (setq candidates (reverse newc))

    (foreach blk blks
      (setq hostFound nil)

      (foreach hostPl chain
        (if (not hostFound)
          (progn
            (setq hitB (DEGN-DEGA--pl-touches-block-tol hostPl blk DEGN-DEGA--TOL_DOSEME))
            (if hitB
              (progn
                (setq hostFound T)

                (setq ip (deg-get-inspt (DEGN-DEGA--vla blk)))
                (setq ip (list (car ip) (cadr ip) 0.0))

                (setq touchPt (car hitB) gap (cadr hitB))
                (if (not (DEGN-DEGA--blconn-exists-p ip hostPl))
                  (setq DEGN-DEGA--BLCONNS (cons (list "TOUCH" ip hostPl touchPt gap) DEGN-DEGA--BLCONNS))
                )
                (DEGN-DEGA--draw-circle ip DEGN-DEGA--TOL_DOSEME)
                (DEGN-DEGA--draw-circle touchPt DEGN-DEGA--TOL_DOSEME)

                (setq newc '())
                (while candidates
                  (setq c (car candidates))
                  (setq candidates (cdr candidates))
                  (setq hitB2 (DEGN-DEGA--pl-touches-block-tol c blk DEGN-DEGA--TOL_DOSEME))
                  (if hitB2
                    (progn
                      (setq touchPt (car hitB2) gap (cadr hitB2))
                      (if (not (DEGN-DEGA--blconn-exists-p ip c))
                        (setq DEGN-DEGA--BLCONNS (cons (list "TOUCH" ip c touchPt gap) DEGN-DEGA--BLCONNS))
                      )
                      (DEGN-DEGA--draw-circle ip DEGN-DEGA--TOL_DOSEME)
                      (DEGN-DEGA--draw-circle touchPt DEGN-DEGA--TOL_DOSEME)

                      (setq chain (cons c chain))
                      (setq changed T)
                    )
                    (setq newc (cons c newc))
                  )
                )
                (setq candidates (reverse newc))
              )
            )
          )
        )
      )
    )
  )
  (setq chain (vl-remove nil (mapcar '(lambda (x)
                                       (cond
                                         ((null x) nil)
                                         ((= (type x) 'VLA-OBJECT) (vlax-vla-object->ename x))
                                         (T x)))
                                     chain)))


  chain
)

(defun DEGN-DEGA--node-id (pt tol nodePts / id)
  (setq id nil)
  (foreach it nodePts
    (if (and (not id) (DEGN-DEGA--eq-tol pt (cdr it) tol))
      (setq id (car it))
    )
  )
  id
)

(defun DEGN-DEGA--add-node (pt nodePts / id)
  (setq id (length nodePts))
  (cons (cons id pt) nodePts)
)

(defun DEGN-DEGA--ensure-node (pt tol nodePts / id)
  (setq id (DEGN-DEGA--node-id pt tol nodePts))
  (if id
    (list id nodePts)
    (progn
      (setq nodePts (DEGN-DEGA--add-node pt nodePts))
      (list (car (car nodePts)) nodePts)
    )
  )
)

(defun DEGN-DEGA--adj-get (adj id) (cdr (assoc id adj)))

(defun DEGN-DEGA--adj-add (adj a b w / row)
  (setq row (assoc a adj))
  (if row
    (subst (cons a (cons (cons b w) (cdr row))) row adj)
    (cons (cons a (list (cons b w))) adj)
  )
)

(defun DEGN-DEGA--dget (dist id) (if (assoc id dist) (cdr (assoc id dist)) 1e99))
(defun DEGN-DEGA--dset (dist id v)
  (if (assoc id dist) (subst (cons id v) (assoc id dist) dist) (cons (cons id v) dist))
)

(defun DEGN-DEGA--min-unvisited (dist visited / bestId bestD it)
  (setq bestId nil bestD 1e99)
  (foreach it dist
    (if (and (not (member (car it) visited)) (< (cdr it) bestD))
      (progn (setq bestD (cdr it)) (setq bestId (car it)))
    )
  )
  bestId
)

(defun DEGN-DEGA--dijkstra (adj startId / dist visited u nbrs nb v alt)
  (setq dist (list (cons startId 0.0)))
  (setq visited '())
  (setq u (DEGN-DEGA--min-unvisited dist visited))
  (while u
    (setq visited (cons u visited))
    (setq nbrs (DEGN-DEGA--adj-get adj u))
    (foreach nb nbrs
      (setq v (car nb))
      (setq alt (+ (DEGN-DEGA--dget dist u) (cdr nb)))
      (if (< alt (DEGN-DEGA--dget dist v))
        (setq dist (DEGN-DEGA--dset dist v alt))
      )
    )
    (setq u (DEGN-DEGA--min-unvisited dist visited))
  )
  dist
)

(defun DEGN-DEGA--collect-splitpts-for-pl (pl conns tol / pts c)
  (setq pts (DEGN-DEGA--endpoints pl))

  (foreach c conns
    (if (= (nth 2 c) pl) (setq pts (cons (nth 3 c) pts)))
  )

  (foreach c DEGN-DEGA--BLCONNS
    (if (and (= (car c) "TOUCH") (= (caddr c) pl))
      (setq pts (cons (nth 3 c) pts))
    )
  )

  (DEGN-DEGA--uniq-pts pts tol)
)

(defun DEGN-DEGA--sort-pts-along-pl (pl pts / lst p par)
  (setq lst '())
  (foreach p pts
    (setq par (DEGN-DEGA--ptparam pl p))
    (if (numberp par)
      (setq lst (cons (list par p) lst)))
  )
  (vl-sort lst '(lambda (a b) (< (car a) (car b))))
)

(defun DEGN-DEGA--build-graph (chain conns tol / nodePts adj pl splitPts splSorted i a b ida idb resA resB
                                   distA distB oneMap endPt hostCp gap blkPt touchPt)
  (setq nodePts '())
  (setq adj '())
  (setq DEGN-DEGA--POLYNODESMAP '())

  (foreach pl chain
    (setq splitPts (DEGN-DEGA--collect-splitpts-for-pl pl conns tol))
    (if (and (boundp 'DEGN-DEGA--FORCED-SPLIT-PL)
             (boundp 'DEGN-DEGA--FORCED-SPLIT-PT)
             DEGN-DEGA--FORCED-SPLIT-PL
             DEGN-DEGA--FORCED-SPLIT-PT
             (equal pl DEGN-DEGA--FORCED-SPLIT-PL))
      (setq splitPts
        (cons DEGN-DEGA--FORCED-SPLIT-PT splitPts))
    )
    (setq splSorted (DEGN-DEGA--sort-pts-along-pl pl splitPts))

    (setq oneMap '())
    (foreach it splSorted
      (setq resA (DEGN-DEGA--ensure-node (cadr it) tol nodePts))
      (setq ida (car resA))
      (setq nodePts (cadr resA))
      (setq oneMap (cons (cons (car it) ida) oneMap))
    )
    (setq DEGN-DEGA--POLYNODESMAP (cons (cons pl (reverse oneMap)) DEGN-DEGA--POLYNODESMAP))

    (setq i 0)
    (while (< i (1- (length splSorted)))
      (setq a (nth i splSorted))
      (setq b (nth (1+ i) splSorted))

      (setq ida (cdr (assoc (car a) (cdr (assoc pl DEGN-DEGA--POLYNODESMAP)))))
      (setq idb (cdr (assoc (car b) (cdr (assoc pl DEGN-DEGA--POLYNODESMAP)))))

      (setq distA (DEGN-DEGA--distAtParam pl (car a)))
      (setq distB (DEGN-DEGA--distAtParam pl (car b)))
      (setq w (abs (- distB distA)))

      (setq adj (DEGN-DEGA--adj-add adj ida idb w))
      (setq adj (DEGN-DEGA--adj-add adj idb ida w))

      (setq i (1+ i))
    )
  )

  (foreach c conns
    (setq endPt (nth 1 c))
    (setq hostCp (nth 3 c))
    (setq gap (nth 4 c))

    (setq resA (DEGN-DEGA--ensure-node endPt tol nodePts))
    (setq ida (car resA)) (setq nodePts (cadr resA))

    (setq resB (DEGN-DEGA--ensure-node hostCp tol nodePts))
    (setq idb (car resB)) (setq nodePts (cadr resB))

    (setq adj (DEGN-DEGA--adj-add adj ida idb gap))
    (setq adj (DEGN-DEGA--adj-add adj idb ida gap))
  )

  (foreach c DEGN-DEGA--BLCONNS
    (if (= (car c) "TOUCH")
      (progn
        (setq blkPt   (cadr c))
        (setq touchPt (nth 3 c))
        (setq gap     (nth 4 c))

        (setq resA (DEGN-DEGA--ensure-node blkPt tol nodePts))
        (setq ida (car resA)) (setq nodePts (cadr resA))

        (setq resB (DEGN-DEGA--ensure-node touchPt tol nodePts))
        (setq idb (car resB)) (setq nodePts (cadr resB))

        (setq adj (DEGN-DEGA--adj-add adj ida idb gap))
        (setq adj (DEGN-DEGA--adj-add adj idb ida gap))
      )
    )
  )

  (list nodePts adj DEGN-DEGA--POLYNODESMAP)
)

(defun DEGN-DEGA--build-graph-at
  (chain conns tol forcedPl forcedPt
   / DEGN-DEGA--FORCED-SPLIT-PL DEGN-DEGA--FORCED-SPLIT-PT)
  ;; Yerel/dinamik baglar eski 3 argumanli build-graph API'sini korur.
  (setq DEGN-DEGA--FORCED-SPLIT-PL forcedPl
        DEGN-DEGA--FORCED-SPLIT-PT forcedPt)
  (DEGN-DEGA--build-graph chain conns tol)
)

(defun DEGN-DEGA--closest-on-chain (pt chain / best pl cp curd o thiscp lay)
  (setq best nil pl nil cp nil)

  ;; 1. pas: TV/TELEFON layerlarini atla
  (foreach e chain
    (setq o (DEGN-DEGA--vla e))
    (setq lay (vla-get-Layer o))
    (if (not (DEGN-DEGA--layer-tv-tel-p lay))
      (progn
        (setq thiscp (deg-safe-closest-point o (list (car pt) (cadr pt) 0.0)))
        (setq curd (distance (list (car pt) (cadr pt) 0.0)
                             (list (car thiscp) (cadr thiscp) 0.0)))
        (if (or (not best) (< curd best))
          (progn (setq best curd) (setq pl e) (setq cp thiscp))
        )
      )
    )
  )

  ;; 2. pas: eger hepsi TV/TELEFON ise (pl nil), eski davranis
  (if (not pl)
    (progn
      (setq best nil pl nil cp nil)
      (foreach e chain
        (setq o (DEGN-DEGA--vla e))
        (setq thiscp (deg-safe-closest-point o (list (car pt) (cadr pt) 0.0)))
        (setq curd (distance (list (car pt) (cadr pt) 0.0)
                             (list (car thiscp) (cadr thiscp) 0.0)))
        (if (or (not best) (< curd best))
          (progn (setq best curd) (setq pl e) (setq cp thiscp))
        )
      )
    )
  )

  (list best pl cp)
)


(defun DEGN-DEGA--bracket-nodes-on-pl (pl polyMap cp / par lst i left right a b)
  (setq par (DEGN-DEGA--ptparam pl cp))
  (setq lst polyMap)
  (setq left (car lst))
  (setq right (last lst))
  (setq i 0)
  (while (< i (1- (length lst)))
    (setq a (nth i lst))
    (setq b (nth (1+ i) lst))
    (if (and (<= (car a) par) (<= par (car b)))
      (progn (setq left a) (setq right b) (setq i (length lst)))
    )
    (setq i (1+ i))
  )
  (list par left right)
)

(defun DEGN-DN--poly-route-info
  (pl cp polyNodesMap dist
   / m bkt par left right leftId rightId dcp dl dr da db d1 d2 route leftD rightD anchor)
  (setq m (cdr (assoc pl polyNodesMap)))
  (if (and m cp)
    (progn
      (setq bkt
        (vl-catch-all-apply
          'DEGN-DEGA--bracket-nodes-on-pl
          (list pl m cp)))
      (if (not (vl-catch-all-error-p bkt))
        (progn
          (setq par (car bkt)
                left (cadr bkt)
                right (caddr bkt)
                leftId (if (and left (listp left)) (cdr left))
                rightId (if (and right (listp right)) (cdr right)))
          (if (and (numberp par)
                   left
                   right
                   (listp left)
                   (listp right)
                   leftId
                   rightId)
            (progn
              (setq dcp (DEGN-DEGA--distAtParam pl par)
                    dl (DEGN-DEGA--distAtParam pl (car left))
                    dr (DEGN-DEGA--distAtParam pl (car right)))
              (if (and (numberp dcp)
                       (numberp dl)
                       (numberp dr))
                (progn
                  (setq da (abs (- dcp dl))
                        db (abs (- dr dcp))
                        d1 (+ (DEGN-DEGA--dget dist leftId) da)
                        d2 (+ (DEGN-DEGA--dget dist rightId) db)
                        route (min d1 d2)
                        leftD (DEGN-DEGA--dget dist leftId)
                        rightD (DEGN-DEGA--dget dist rightId)
                        anchor (if (> leftD rightD) leftId rightId))
                  (list route anchor pl cp)
                )
              )
            )
          )
        )
      )
    )
  )
)

(defun DEGN-DN--block-host-info
  (blk chain polyNodesMap dist
   / blkObj ip3 plE plObj cpRes cp info d2d bestInfo bestContact bestRoute)
  ;; DATA/CCTV numaralandirmasinda DATA, TELEFON ve TV hatlarinin
  ;; tamamini gercek temas adayi olarak kullanir.
  (setq blkObj (DEGN-DEGA--vla blk)
        ip3 (if blkObj (deg-get-inspt blkObj))
        bestInfo nil
        bestContact nil
        bestRoute nil)
  (if ip3
    (progn
      (foreach plE chain
        (setq plObj (DEGN-DEGA--vla plE)
              cpRes
                (if plObj
                  (vl-catch-all-apply
                    'block-ref-contact-point
                    (list plObj blkObj DEGN-DEGA--TOL_DOSEME))))
        (if (and cpRes
                 (not (vl-catch-all-error-p cpRes)))
          (progn
            (setq cp cpRes
                  info
                    (DEGN-DN--poly-route-info
                      plE cp polyNodesMap dist))
            (if info
              (progn
                (setq d2d
                  (distance
                    (list (car ip3) (cadr ip3) 0.0)
                    (list (car cp) (cadr cp) 0.0)))
                (if (or
                      (not bestInfo)
                      (< d2d (- bestContact 0.001))
                      (and
                        (equal d2d bestContact 0.001)
                        (< (car info) bestRoute)))
                  (setq bestInfo info
                        bestContact d2d
                        bestRoute (car info))
                )
              )
            )
          )
        )
      )

      ;; Gercek temas bulunamazsa tum DATA/TELEFON/TV zincirinde
      ;; base noktasina en yakin graph kenarini kullan.
      (if (not bestInfo)
        (foreach plE chain
          (setq plObj (DEGN-DEGA--vla plE)
                cp
                  (if plObj
                    (deg-safe-closest-point plObj ip3)))
          (if cp
            (progn
              (setq info
                      (DEGN-DN--poly-route-info
                        plE cp polyNodesMap dist)
                    d2d
                      (distance
                        (list (car ip3) (cadr ip3) 0.0)
                        (list (car cp) (cadr cp) 0.0)))
              (if (and info
                       (or
                         (not bestInfo)
                         (< d2d (- bestContact 0.001))
                         (and
                           (equal d2d bestContact 0.001)
                           (< (car info) bestRoute))))
                (setq bestInfo info
                      bestContact d2d
                      bestRoute (car info))
              )
            )
          )
        )
      )
    )
  )
  (if bestInfo
    (append bestInfo (list bestContact))
  )
)

(defun DEGN-DEGA--block-chain-distance (blk chain tol polyNodesMap dist / info)
  (setq info
    (DEGN-DN--block-host-info
      blk chain polyNodesMap dist))
  (if info (car info))
)

(defun DEGN-DN--children-add (children parent child / row kids)
  (setq row (assoc parent children))
  (if row
    (progn
      (setq kids (cdr row))
      (if (not (member child kids))
        (setq children
          (subst
            (cons parent (append kids (list child)))
            row children)))
    )
    (setq children
      (cons (cons parent (list child)) children))
  )
  children
)

(defun DEGN-DN--neighbor-records (adj node dist / row nb id seen out)
  (setq row (assoc node adj))
  (foreach nb (if row (cdr row) nil)
    (setq id (car nb))
    (if (not (member id seen))
      (progn
        (setq seen (cons id seen))
        (setq out
          (cons
            (list id (DEGN-DEGA--dget dist id))
            out))
      )
    )
  )
  (vl-sort out
    '(lambda (a b)
       (if (equal (cadr a) (cadr b) 0.000001)
         (< (car a) (car b))
         (< (cadr a) (cadr b)))))
)

(defun DEGN-DN--graph-children-bfs (adj dist startId / visited queue node rec child children)
  ;; Graph'i tiklanan dugumden koklenen tek bir agaca cevirir.
  (setq visited (list startId)
        queue (list startId)
        children nil)
  (while queue
    (setq node (car queue)
          queue (cdr queue))
    (foreach rec (DEGN-DN--neighbor-records adj node dist)
      (setq child (car rec))
      (if (not (member child visited))
        (progn
          (setq visited (cons child visited)
                children
                  (DEGN-DN--children-add
                    children node child)
                queue (append queue (list child)))
        )
      )
    )
  )
  children
)

(defun DEGN-DN--node-point (nodePts id / row)
  (setq row (assoc id nodePts))
  (if row (cdr row) nil)
)

(defun DEGN-DN--unit-xy (a b / dx dy len)
  (if (and a b)
    (progn
      (setq dx (- (car b) (car a))
            dy (- (cadr b) (cadr a))
            len (sqrt (+ (* dx dx) (* dy dy))))
      (if (> len 0.000000001)
        (list (/ dx len) (/ dy len))
      )
    )
  )
)

(defun DEGN-DN--ordered-children
  (node parent children nodePts dist
   / kids nodePt parentPt inVec child childPt outVec dot bestDot continuation recs flag childDist edgeLen angleVal)
  (setq kids (cdr (assoc node children))
        nodePt (DEGN-DN--node-point nodePts node)
        parentPt (if parent (DEGN-DN--node-point nodePts parent))
        inVec (DEGN-DN--unit-xy parentPt nodePt)
        bestDot -2.0
        continuation nil)

  ;; Bir ayrimda gelis yonunu en cok koruyan kol ana devamdir.
  ;; Yan dallar once bitirilir, ana devam en sona birakilir.
  (if (and inVec (> (length kids) 1))
    (foreach child kids
      (setq childPt (DEGN-DN--node-point nodePts child)
            outVec (DEGN-DN--unit-xy nodePt childPt))
      (if outVec
        (progn
          (setq dot
            (+ (* (car inVec) (car outVec))
               (* (cadr inVec) (cadr outVec))))
          (if (> dot bestDot)
            (setq bestDot dot
                  continuation child))
        )
      )
    )
  )
  (if (< bestDot 0.70)
    (setq continuation nil))

  (foreach child kids
    (setq childPt (DEGN-DN--node-point nodePts child)
          flag (if (and continuation (= child continuation)) 1 0)
          childDist (DEGN-DEGA--dget dist child)
          edgeLen (if (and nodePt childPt) (distance nodePt childPt) 1e99)
          angleVal (if (and nodePt childPt) (angle nodePt childPt) 0.0)
          recs
            (cons
              (list child flag childDist edgeLen angleVal)
              recs))
  )
  (setq recs
    (vl-sort recs
      '(lambda (a b)
         (cond
           ((/= (cadr a) (cadr b))
            (< (cadr a) (cadr b)))
           ((not (equal (caddr a) (caddr b) 0.000001))
            (< (caddr a) (caddr b)))
           ((not (equal (cadddr a) (cadddr b) 0.000001))
            (< (cadddr a) (cadddr b)))
           ((not (equal (nth 4 a) (nth 4 b) 0.000001))
            (< (nth 4 a) (nth 4 b)))
           (T (< (car a) (car b)))))))
  (mapcar 'car recs)
)

(defun DEGN-DN--graph-edge-ranks
  (children dist startId nodePts / stack visited item node parent child rank ranks ordered)
  ;; DFS sirasi: bir dal ve butun alt dallari bitmeden kardes dala gecilmez.
  (setq stack (list (list startId nil))
        visited nil
        rank 0
        ranks (list (cons startId 0)))
  (while stack
    (setq item (car stack)
          stack (cdr stack)
          node (car item)
          parent (cadr item))
    (if (not (member node visited))
      (progn
        (setq visited (cons node visited))
        (if (/= node startId)
          (progn
            (setq rank (1+ rank))
            (setq ranks (cons (cons node rank) ranks)))
        )
        (setq ordered
          (DEGN-DN--ordered-children
            node parent children nodePts dist))
        (foreach child (reverse ordered)
          (setq stack (cons (list child node) stack)))
      )
    )
  )
  ranks
)

(defun DEGN-DN--block-anchor-node
  (blk chain polyNodesMap dist / info)
  (setq info
    (DEGN-DN--block-host-info
      blk chain polyNodesMap dist))
  (if info (cadr info))
)

(defun DEGN-DEGA--chain-ends (chain tol / pts uniq deg p e ep ends)
  (setq pts '())
  (foreach e chain (setq pts (append pts (DEGN-DEGA--endpoints e))))
  (setq uniq (DEGN-DEGA--uniq-pts pts tol))

  (setq ends '())
  (foreach p uniq
    (setq deg 0)
    (foreach e chain
      (setq ep (DEGN-DEGA--endpoints e))
      (if (or (DEGN-DEGA--eq-tol p (car ep) tol)
              (DEGN-DEGA--eq-tol p (cadr ep) tol))
        (setq deg (1+ deg))))
    (if (= deg 1) (setq ends (cons p ends))))
  ends
)

(defun DEGN-DEGA--blocks-near (pts tolBlock / res e ip lay src)
  (setq res (ssadd))
  (if DEGN-DEGA--SCOPE-ACTIVE
    (setq src DEGN-DEGA--SCOPE-BLOCKS)
    (setq src (DEGN-DEGA--scope-ss-to-list (ssget "X" '((0 . "INSERT")))))
  )
  (foreach e src
    (setq lay (cdr (assoc 8 (entget e))))
    (if (/= (strcase (if lay lay "")) (DEG:VAL 'O2))
      (progn
        (if (or (not DEGN-DEGA--DATA-ONLY) (DEGN-DEGA--layer-data-only-str-p lay))
          (progn
            (setq ip (deg-get-inspt (DEGN-DEGA--vla e)))
            (setq ip (list (car ip) (cadr ip)))
            (if (vl-some '(lambda (p) (<= (distance p ip) tolBlock)) pts)
              (ssadd e res)
            )
          )
        )
      )
    )
  )
  res
)
(defun DEGN-DEGA--ss-add-unique (ss e / i hit he hs cur)
  (if (and ss e (= (type e) 'ENAME))
    (progn
      (setq he (DEGN-DEGA--scope-handle e))
      (setq i 0 hit nil)
      (while (and (< i (sslength ss)) (not hit))
        (setq cur (ssname ss i))
        (setq hs (DEGN-DEGA--scope-handle cur))
        (if (or (equal e cur) (and he hs (= he hs)))
          (setq hit T)
        )
        (setq i (1+ i))
      )
      (if (not hit) (ssadd e ss))
    )
  )
  ss
)

(defun DEGN-DEGA--ss-union-unique (a b / out i)
  (setq out (ssadd))
  (if a
    (progn
      (setq i 0)
      (while (< i (sslength a))
        (setq out (DEGN-DEGA--ss-add-unique out (ssname a i)))
        (setq i (1+ i))
      )
    )
  )
  (if b
    (progn
      (setq i 0)
      (while (< i (sslength b))
        (setq out (DEGN-DEGA--ss-add-unique out (ssname b i)))
        (setq i (1+ i))
      )
    )
  )
  out
)

(defun DEGN-DEGA--block-touches-chain-p (blk chain tol / ip hit pl)
  (setq hit nil)
  (if (and blk (= (type blk) 'ENAME))
    (progn
      (setq ip (deg-get-inspt (DEGN-DEGA--vla blk)))
      (if ip
        (progn
          (setq ip (list (car ip) (cadr ip) 0.0))
          (foreach pl chain
            (if (and (not hit)
                     pl
                     (= (type pl) 'ENAME)
                     (DEGN-DEGA--scope-poly-p pl)
                     (DEGN-DEGA--pt->curve-hit ip pl tol))
              (setq hit T)
            )
          )
        )
      )
    )
  )
  hit
)

(defun DEGN-DEGA--blocks-touching-chain (chain tol / res src e lay)
  (setq res (ssadd))
  (if DEGN-DEGA--SCOPE-ACTIVE
    (setq src DEGN-DEGA--SCOPE-BLOCKS)
    (setq src (DEGN-DEGA--scope-ss-to-list (ssget "X" '((0 . "INSERT")))))
  )
  (foreach e src
    (if (and e (= (type e) 'ENAME) (DEGN-DEGA--scope-block-p e))
      (progn
        (setq lay (cdr (assoc 8 (entget e))))
        (if (/= (strcase (if lay lay "")) (DEG:VAL 'O2))
          (if (DEGN-DEGA--block-touches-chain-p e chain tol)
            (ssadd e res)
          )
        )
      )
    )
  )
  res
)
(defun DEGN-DEGA--pad2 (n / s) (setq s (itoa n)) (if (< (strlen s) 2) (strcat "0" s) s))

(defun DEGN-DN--number-count (blkObj / raw pairs pair n best)
  (setq best 1)
  (setq raw (vl-catch-all-apply 'get-adet-from-block (list blkObj)))
  (if (and (not (vl-catch-all-error-p raw))
           (numberp raw)
           (> raw 0))
    (setq best (max best (fix raw)))
  )
  (setq pairs (vl-catch-all-apply 'get-sembol-adi-from-block (list blkObj)))
  (if (and (not (vl-catch-all-error-p pairs)) (listp pairs))
    (foreach pair pairs
      (if (and (= (type pair) 'LIST)
               (numberp (cdr pair))
               (> (cdr pair) 0))
        (progn
          (setq n (fix (cdr pair)))
          (if (> n best) (setq best n))
        )
      )
    )
  )
  best
)

(defun DEGN-DN--number-range (start count / firstNum lastNum k suffix)
  (setq firstNum (if (numberp start) (fix start) 1)
        count    (if (and (numberp count) (> count 0)) (fix count) 1)
        lastNum  (+ firstNum count -1))
  (if (<= count 3)
    (progn
      (setq suffix ""
            k      firstNum)
      (while (<= k lastNum)
        (setq suffix
          (if (= suffix "")
            (DEGN-DEGA--pad2 k)
            (strcat suffix "," (DEGN-DEGA--pad2 k))))
        (setq k (1+ k))
      )
    )
    (setq suffix
      (strcat
        (DEGN-DEGA--pad2 firstNum)
        ",...,"
        (DEGN-DEGA--pad2 lastNum)))
  )
  (list suffix (1+ lastNum) firstNum lastNum)
)

(defun DEGN-DN--unique-block-order (items / seen out pair obj h)
  (setq seen '()
        out  '())
  (foreach pair items
    (setq obj (cdr pair)
          h   (if obj (vl-catch-all-apply 'vla-get-Handle (list obj)) nil))
    (if (vl-catch-all-error-p h) (setq h nil))
    (if (or (not h) (not (member h seen)))
      (progn
        (if h (setq seen (cons h seen)))
        (setq out (cons pair out))
      )
    )
  )
  (reverse out)
)

(defun DEGN-DEGA--set-attr (blk tag value / obj atts a ok)
  (setq ok nil)
  (setq obj (DEGN-DEGA--vla blk))
  (if (= (vla-get-HasAttributes obj) :vlax-true)
    (progn
      (setq atts (vlax-invoke obj 'GetAttributes))
      (foreach a atts
        (if (= (DEGN-DEGA--upper (vla-get-TagString a)) (DEGN-DEGA--upper tag))
          (progn (vla-put-TextString a value) (setq ok T))
        )
      )
    )
  )
  ok
)

(defun DEGN-DN--attr-tag-key (s / u)
  (setq u (vl-string-trim " \t\r\n" (if s (strcase s) "")))
  (vl-string-translate " -." "___" u)
)

(defun DEGN-DN--att-list (obj / raw hv)
  (setq raw nil)
  (if (and obj (vlax-method-applicable-p obj 'GetAttributes))
    (progn
      (setq hv (vl-catch-all-apply 'vla-get-HasAttributes (list obj)))
      (if (and (not (vl-catch-all-error-p hv)) (= hv :vlax-true))
        (setq raw (vl-catch-all-apply 'vlax-invoke (list obj 'GetAttributes)))
      )
    )
  )
  (cond
    ((vl-catch-all-error-p raw) nil)
    ((= (type raw) 'VARIANT)  (vlax-safearray->list (vlax-variant-value raw)))
    ((= (type raw) 'SAFEARRAY) (vlax-safearray->list raw))
    ((listp raw) raw)
    (T nil)
  )
)

(defun DEGN-DN--make-editable (obj / lay atts a)
  (if (and obj (= (type obj) 'VLA-OBJECT))
    (progn
      (setq lay (vl-catch-all-apply 'vla-get-Layer (list obj)))
      (if (not (vl-catch-all-error-p lay))
        (degk--ensure-layer-editable lay)
      )
      (setq atts (DEGN-DN--att-list obj))
      (foreach a atts
        (setq lay (vl-catch-all-apply 'vla-get-Layer (list a)))
        (if (not (vl-catch-all-error-p lay))
          (degk--ensure-layer-editable lay)
        )
      )
    )
  )
  obj
)

(defun DEGN-DN--put-sira-no (blk value / obj atts a ok tag res)
  (setq ok nil)
  (setq obj (DEG:VLA blk))
  (if obj
    (progn
      (DEGN-DN--make-editable obj)
      (setq atts (DEGN-DN--att-list obj))
      (foreach a atts
        (setq tag (vl-catch-all-apply 'vla-get-TagString (list a)))
        (if (and (not (vl-catch-all-error-p tag))
                 (= (DEGN-DN--attr-tag-key tag) "SIRA_NO"))
          (progn
            (setq res (vl-catch-all-apply 'vla-put-TextString (list a value)))
            (if (not (vl-catch-all-error-p res))
              (setq ok T)
            )
          )
        )
      )
      (if ok (vl-catch-all-apply 'vla-Update (list obj)))
    )
  )
  ok
)
(defun DEGN-DN--block-touch-normal-p (plObj blkObj tol / ins cp)
  (or
    (poly-touch-block? plObj blkObj tol)
    (and
      (setq ins (deg-get-inspt blkObj))
      (setq cp (deg-safe-closest-point plObj ins))
      (deg-pt3 ins)
      (deg-pt3 cp)
      (<= (distance (deg-pt3 ins) (deg-pt3 cp)) tol)
    )
  )
)



(defun DN_ORIG
  ( / tol loopName
     sel ent obj
     pickPt plStart plEnd
     idx
     txtEnt txtObj
     plLayer isDataLayer areaSS oldErr

     startPt chain signalChain ends blocks g nodePts adj polyNodesMap startId dist items sorted i blkEnt d n val wrote dnTreeChildren dnEdgeRanks dnHostResult dnHostInfo dnAnchor dnRank

     dStart dEnd useFromStart totalLen blkSS blkEnt2 blkObj
     j blockOrder insPt projPt curDist key
     attList att tag
     newStr
     blkName tolLocal
     adetUse rangeInfo
     blkLayer blkNameU L skipThis wroteSiraNo dnBlockCount dnWriteCount dnFailCount dnScanCount dnOldSkipCount dnOldFilterCount dnOldTouchFailCount dnOldAddCount dnFallbackLayer0Count dnFallbackIgnoreCount dnFallbackFilterCount dnFallbackTouchFailCount dnFallbackAddCount
     isFireLayer isFlasherLayer
  )

  (vl-load-com)
  (setq oldErr *error*)
  (defun *error* (msg)
    (DEGN-DEGA--scope-reset)
    (setq DEGN-DEGA--DATA-ONLY nil)
    (setq *error* oldErr)
    (if (and msg (not (wcmatch (strcase msg) "*BREAK*,*CANCEL*,*QUIT*")))
      (princ (strcat "\nDN hata: " msg))
    )
    (princ)
  )
  (setq tol DEGN-DEGA--TOL)

  (setq txtEnt (entsel "\nLoop adý için TEXT'e týklayýn veya elle yazmak için Enter: "))
  (if txtEnt
    (progn
      (setq txtObj (vlax-ename->vla-object (car txtEnt)))
      (setq loopName (get-entity-text txtObj))
      (if (not loopName)
        (setq loopName (getstring T "\nTEXT okunamadý, loop adýný elle yazýn: "))
      )
    )
    (setq loopName (getstring T "\nLoop adýný yazýn (boþ Enter = iptal): "))
  )
  (if (or (null loopName) (= loopName ""))
    (progn (princ "\n\nÝptal.") (princ) (exit))
  )

  (setq sel (entsel "\nDal polyline'ýný seçin: "))
  (if (not sel) (progn (princ "\n\nÝptal.") (princ) (exit)))
  (setq ent (car sel))
  (setq pickPt (cadr sel))
  (setq obj (vlax-ename->vla-object ent))

  (setq plLayer (strcase (vla-get-Layer obj)))
  (setq isDataLayer (DEGN-DEGA--layer-data-only-str-p plLayer))

  (setq plStart (vlax-curve-getStartPoint obj))
  (setq plEnd   (vlax-curve-getEndPoint   obj))
  (setq pickPt (DEGN-DN--pick-on-polyline obj pickPt))

  (if isDataLayer
    (progn
      (princ "\nDN DATA: Alan icindeki block ve polyline'lari secin: ")
      (setq areaSS (ssget '((0 . "INSERT,LWPOLYLINE,POLYLINE"))))
      (if (not areaSS)
        (progn
          (DEGN-DEGA--scope-reset)
          (setq DEGN-DEGA--DATA-ONLY nil)
          (setq *error* oldErr)
          (princ)
          (exit)
        )
      )
      (DEGN-DEGA--scope-set-from-ss areaSS ent)
      (setq idx (getint "\nBlok numaralandýrma baþlangýç sayýsý? "))
      (if (null idx) (setq idx 1))

      (setq startPt pickPt)

      (setq DEGN-DEGA--DATA-ONLY nil)
      (setq signalChain (DEGV:_filter-chain-data-tel-tv (DEGN-DEGA--chain ent)))
      (if (not signalChain)
        (progn (princ "\n\nHATA: DATA/TELEFON/TV zinciri bulunamadý.") (princ) (exit))
      )
      (setq chain signalChain)
      
      (setq ends   (DEGN-DEGA--chain-ends chain tol))
      (setq blocks (DEGN-DEGA--blocks-near ends DEGN-DEGA--TOLBLOCK))
      (setq blocks (DEGN-DEGA--ss-union-unique blocks (DEGN-DEGA--blocks-touching-chain chain DEGN-DEGA--TOLBLOCK)))
      (setq g
              (DEGN-DEGA--build-graph-at
                chain DEGN-DEGA--CONNS tol ent startPt))
      (setq nodePts     (nth 0 g))
      (setq adj         (nth 1 g))
      (setq polyNodesMap(nth 2 g))

      (setq startId (DEGN-DEGA--node-id startPt tol nodePts))
      (if (not startId)
        (progn (princ "\n\nHATA: Baþlangýç node bulunamadý.") (princ) (exit))
      )

      (setq dist (DEGN-DEGA--dijkstra adj startId))
      (setq dnTreeChildren
              (DEGN-DN--graph-children-bfs
                adj dist startId)
            dnEdgeRanks
              (DEGN-DN--graph-edge-ranks
                dnTreeChildren dist startId nodePts))

      (if (not blocks)
        (progn (princ "\n\nHATA: Zincir uçlarýnda blok bulunamadý.") (princ) (exit))
      )

      (setq items '())
      (setq i 0)
      (while (< i (sslength blocks))
        (setq blkEnt (ssname blocks i))
        (setq dnHostResult
                (vl-catch-all-apply
                  'DEGN-DN--block-host-info
                  (list blkEnt chain polyNodesMap dist))
              dnHostInfo
                (if (vl-catch-all-error-p dnHostResult)
                  nil dnHostResult)
              d
                (if dnHostInfo (car dnHostInfo)))
        (if (numberp d)
          (progn
            (setq dnAnchor
                    (cadr dnHostInfo)
                  dnRank
                    (if (and dnAnchor
                             (assoc dnAnchor dnEdgeRanks))
                      (cdr (assoc dnAnchor dnEdgeRanks))
                      1000000000))
            (setq items
              (cons
                (list dnRank d i blkEnt)
                items))
          )
        )
        (setq i (1+ i))
      )

      (if (null items)
        (progn (princ "\n\nHATA: Zincire oturan blok bulunamadý.") (princ) (exit))
      )

      (setq sorted
        (vl-sort items
          '(lambda (a b)
             (cond
               ((/= (car a) (car b))
                (< (car a) (car b)))
               ((not (equal (cadr a) (cadr b) 0.000001))
                (< (cadr a) (cadr b)))
               (T (< (caddr a) (caddr b)))))))

      (setq n idx)
      (foreach it sorted
        (setq blkEnt (nth 3 it))
        (setq val (strcat loopName "-" (DEGN-DEGA--pad2 n)))
        (setq wrote (DEGN-DEGA--set-attr blkEnt "SIRA_NO" val))
        (if wrote (setq n (1+ n)))
      )

      (sssetfirst nil nil)

      (princ (strcat "\nDEGN(DATA->DEGA): Yazýlan SIRA_NO: " (itoa (- n idx))))
      (princ)
    )

    (progn

      (setq isFireLayer
            (or (wcmatch plLayer (DEG:VAL 'K11))
                (wcmatch plLayer (DEG:VAL 'K9))))
      (setq isFlasherLayer
            (wcmatch plLayer "*FLAÞÖR*,*SOUNDER*"))

      ;; Eski davranýþ ayný polyline ikinci kez seçildiðinde soruyu atlayýp
      ;; önceki baþlangýç sayýsýný yeniden kullanýyordu. Bu durum özellikle
      ;; çoklu adetli bloklardan sonra numara aralýklarýný çakýþtýrabiliyordu.
      (setq idx (getint "\nBlok numaralandýrma baþlangýç sayýsý? "))
      (if (null idx) (setq idx 1))
      (setq *degn-last-poly* nil
            *degn-last-idx*  nil)

      (setq totalLen (vla-get-length obj))
      (setq pDist    (deg-safe-dist-at-point obj pickPt))
      (setq dStart   pDist)
      (setq dEnd     (- totalLen pDist))
      (setq useFromStart (<= dStart dEnd))

      (setq blkSS (ssget "_X" '((0 . "INSERT"))))
      (setq blockOrder '())
      (setq dnScanCount 0
            dnOldSkipCount 0
            dnOldFilterCount 0
            dnOldTouchFailCount 0
            dnOldAddCount 0
            dnFallbackLayer0Count 0
            dnFallbackIgnoreCount 0
            dnFallbackFilterCount 0
            dnFallbackTouchFailCount 0
            dnFallbackAddCount 0)

      (if blkSS
        (progn
          (setq j 0)
          (while (< j (sslength blkSS))
            (setq blkEnt2  (ssname blkSS j)
                  blkObj   (vlax-ename->vla-object blkEnt2))
            (setq blkName  (deg-block-name blkObj))
            (setq blkLayer (vla-get-Layer blkObj))
            (setq tolLocal (if (deg-wcmatch blkName "*MODL*") (max (DEG:CFG-TOL-NUM-OR 'DN_MODL_TOL 5.0) DEGN-DEGA--TOLBLOCK) DEGN-DEGA--TOLBLOCK))

            (setq blkNameU (strcase blkName)
                  L        (strcase plLayer))
            (setq skipThis
                  (or
                    (DEGN-DN--match-list-p blkNameU (DEGN-DN--cfg-list-or-codes 'DN_SKIP_BLOCKS '(K5 K18 K3 K4)))
                    (and
                      (DEGN-DN--match-list-p L (DEGN-DN--cfg-list-or-mix 'DN_SKIP_LAYER_PATTERNS '(K13 K14 K15) "*KARBONMONOKSIT*"))
                      (DEGN-DN--match-list-p blkNameU (DEGN-DN--cfg-list-or-codes 'DN_SKIP_LAYER_BLOCKS '(K6 K19)))
                    )
                  )
            )

            (setq dnScanCount (1+ dnScanCount))
            (cond
              (skipThis
                (setq dnOldSkipCount (1+ dnOldSkipCount))
              )
              ((not (deg-fire-flasher-filter plLayer blkName blkLayer))
                (setq dnOldFilterCount (1+ dnOldFilterCount))
              )
              ((not (DEGN-DN--block-touch-normal-p obj blkObj tolLocal))
                (setq dnOldTouchFailCount (1+ dnOldTouchFailCount))
              )
              (T
                (progn
                  (setq insPt   (deg-get-inspt blkObj))
                  (setq projPt  (deg-safe-closest-point obj insPt))
                  (setq curDist (deg-safe-dist-at-point obj projPt))
                  (setq key     (if useFromStart curDist (- totalLen curDist)))
                  (setq blockOrder (cons (cons key blkObj) blockOrder))
                  (setq dnOldAddCount (1+ dnOldAddCount))
                )
              )
            )
            (setq j (1+ j))
          )
        )
      )

      (if (and blkSS (null blockOrder))
        (progn
          (setq j 0)
          (while (< j (sslength blkSS))
            (setq blkEnt2 (ssname blkSS j)
                  blkObj  (vlax-ename->vla-object blkEnt2))
            (setq blkName  (deg-block-name blkObj))
            (setq blkLayer (vla-get-Layer blkObj))
            (cond
              ((= (strcase blkLayer) "0")
                (setq dnFallbackLayer0Count (1+ dnFallbackLayer0Count))
              )
              ((DEG:IGNORE-BLOCK-OBJ? blkObj)
                (setq dnFallbackIgnoreCount (1+ dnFallbackIgnoreCount))
              )
              ((not (deg-fire-flasher-filter plLayer blkName blkLayer))
                (setq dnFallbackFilterCount (1+ dnFallbackFilterCount))
              )
              ((not (DEGN-DN--block-touch-normal-p obj blkObj DEGN-DEGA--TOLBLOCK))
                (setq dnFallbackTouchFailCount (1+ dnFallbackTouchFailCount))
              )
              (T
                (progn
                  (setq insPt   (deg-get-inspt blkObj))
                  (setq projPt  (deg-safe-closest-point obj insPt))
                  (setq curDist (deg-safe-dist-at-point obj projPt))
                  (setq key     (if useFromStart curDist (- totalLen curDist)))
                  (setq blockOrder (cons (cons key blkObj) blockOrder))
                  (setq dnFallbackAddCount (1+ dnFallbackAddCount))
                )
              )
            )
            (setq j (1+ j))
          )
        )
      )

      (setq blockOrder (vl-sort blockOrder '(lambda (a b) (< (car a) (car b)))))
      (setq blockOrder (DEGN-DN--unique-block-order blockOrder))
      (setq dnBlockCount (length blockOrder)
            dnWriteCount 0
            dnFailCount 0)

      (foreach pair blockOrder
        (setq blkObj (cdr pair))
        (if (= :vlax-true (vla-get-HasAttributes blkObj))
          (progn
            (setq adetUse   (DEGN-DN--number-count blkObj)
                  rangeInfo (DEGN-DN--number-range idx adetUse)
                  newStr    (car rangeInfo))

            (setq wroteSiraNo
                  (DEGN-DN--put-sira-no blkObj (strcat loopName "-" newStr)))

            (if wroteSiraNo
              (progn
                (setq idx (cadr rangeInfo))
                (setq dnWriteCount (1+ dnWriteCount))
              )
              (setq dnFailCount (1+ dnFailCount))
            )
          )
        )
      )

      (sssetfirst nil nil)
      (princ
        (strcat
          "\n\nDN: Normal mod tamamlandi. Blok: "
          (itoa dnBlockCount)
          ", SIRA_NO yazilan: "
          (itoa dnWriteCount)
          ", yazilamayan: "
          (itoa dnFailCount)
        )
      )
      (if (= dnBlockCount 0)
        (progn
          (princ
            (strcat
              "\nDN debug: INSERT="
              (itoa dnScanCount)
              " eski[add="
              (itoa dnOldAddCount)
              ", skip="
              (itoa dnOldSkipCount)
              ", filter="
              (itoa dnOldFilterCount)
              ", touch="
              (itoa dnOldTouchFailCount)
              "] fallback[add="
              (itoa dnFallbackAddCount)
              ", layer0="
              (itoa dnFallbackLayer0Count)
              ", ignore="
              (itoa dnFallbackIgnoreCount)
              ", filter="
              (itoa dnFallbackFilterCount)
              ", touch="
              (itoa dnFallbackTouchFailCount)
              "]"
            )
          )
          (princ
            (strcat
              "\nDN active filter layers: fire="
              (vl-princ-to-string (DEGN-DN--cfg-list-or-codes 'DN_FILTER_FIRE_LAYER_PATTERNS '(K11 K10 K9)))
              " co="
              (vl-princ-to-string (DEGN-DN--cfg-list-or-codes 'DN_FILTER_CO_LAYER_PATTERNS '(K8)))
              " flasor="
              (vl-princ-to-string (DEGN-DN--cfg-list-or-codes 'DN_FILTER_FLASOR_LAYERS '(K1)))
              " sound="
              (vl-princ-to-string (DEGN-DN--cfg-list-or-codes 'DN_FILTER_SOUND_LAYER_PATTERNS '(K13 K14 K15)))
            )
          )
          (princ
            (strcat
              "\nDN active fire excludeBlock="
              (vl-princ-to-string (DEGN-DN--cfg-list-or-codes 'DN_FILTER_FIRE_BLOCK_EXCLUDES '(K13 K14 K15)))
            )
          )
        )
      )
      (princ)
    )
  )
  (DEGN-DEGA--scope-reset)
  (setq DEGN-DEGA--DATA-ONLY nil)
  (setq *error* oldErr)
  (princ)
)


(defun degw-sanitize-filename (name / res i c)
  (if (not name) (setq name "output"))
  (setq name (vl-string-translate "\n\r\t" "   " name))
  (setq res "")
  (setq i 1)
  (while (<= i (strlen name))
    (setq c (substr name i 1))
    (if (wcmatch c "[\\/:*?\"<>|]")
      (setq c "_")
    )
    (setq res (strcat res c))
    (setq i (1+ i))
  )
  (setq res (vl-string-trim " " res))
  (if (= res "") (setq res "output"))
  res
)

(defun degw-sanitize-filename (name / res i c)
  (if (not name) (setq name "output"))
  (setq name (vl-string-translate "\n\r\t" "   " name))
  (setq res "")
  (setq i 1)
  (while (<= i (strlen name))
    (setq c (substr name i 1))
    (if (wcmatch c "[\\/:*?\"<>|]")
      (setq c "_")
    )
    (setq res (strcat res c))
    (setq i (1+ i))
  )
  (setq res (vl-string-trim " " res))
  (if (= res "") (setq res "output"))
  res
)

(defun degw-sanitize-filename (name / res i c)
  (if (not name) (setq name "output"))
  (setq name (vl-string-translate "\n\r\t" "   " name))
  (setq res "")
  (setq i 1)
  (while (<= i (strlen name))
    (setq c (substr name i 1))
    (if (wcmatch c "[\\/:*?\"<>|]")
      (setq c "_")
    )
    (setq res (strcat res c))
    (setq i (1+ i))
  )
  (setq res (vl-string-trim " " res))
  (if (= res "") (setq res "output"))
  res
)

(defun vlax-objectp (x) (= (type x) 'VLA-OBJECT))

(defun degw-ensure-vlax ( / r )
  (setq r (vl-catch-all-apply 'vl-load-com '()))
  (princ)
)

(defun degw-_v2l (v)
  (cond
    ((= (type v) 'variant) (degw-_v2l (vlax-variant-value v)))
    ((= (type v) 'safearray) (vlax-safearray->list v))
    (T v)
  )
)

(defun degw-layer-visible-p (layerName / doc layers lyr r frz on)
  (degw-ensure-vlax)
  (setq doc (vla-get-ActiveDocument (vlax-get-acad-object)))
  (setq layers (vla-get-Layers doc))
  (setq r (vl-catch-all-apply 'vla-Item (list layers layerName)))
  (if (vl-catch-all-error-p r)
    T
    (progn
      (setq lyr r)
      (setq frz (vla-get-Freeze lyr))
      (setq on  (vla-get-LayerOn lyr))
      (and (= frz :vlax-false) (= on :vlax-true))
    )
  )
)

(defun degw-text-entity-p (obj / onm)
  (setq onm (if obj (strcase (vla-get-ObjectName obj)) ""))
  (or (= onm "ACDBTEXT")
      (= onm "ACDBMTEXT")
      (= onm "ACDBATTRIBUTE")
      (= onm "ACDBATTRIBUTEREFERENCE")
      (= onm "ACDBATTRIBUTEDEFINITION")
      (= onm "ACDBATTDEF")
      (= onm "ACDBLEADER") ; içinde anotasyön olabiliyor
      (= onm "ACDBMLEADER")
  )
)

(defun degw-entity-visible-p (obj / vis r)
  (if (and obj (vlax-property-available-p obj 'Visible))
    (progn
      (setq r (vl-catch-all-apply 'vla-get-Visible (list obj)))
      (if (vl-catch-all-error-p r) T (= r :vlax-true))
    )
    T
  )
)

(defun degw-entity-eligible-for-bbox-p (obj / lyr)
  (and obj
       (not (degw-text-entity-p obj))
       (degw-entity-visible-p obj)
       (progn
         (setq lyr (vl-catch-all-apply 'vla-get-Layer (list obj)))
         (if (vl-catch-all-error-p lyr)
           T
           (degw-layer-visible-p lyr)
         )
       )
  )
)

(defun degw-bbox-union (bbA bbB / mnA mxA mnB mxB)
  (cond
    ((and (not bbA) (not bbB)) nil)
    ((not bbA) bbB)
    ((not bbB) bbA)
    (T
      (setq mnA (car bbA)  mxA (cadr bbA))
      (setq mnB (car bbB)  mxB (cadr bbB))
      (list
        (list (min (car mnA) (car mnB))
              (min (cadr mnA) (cadr mnB))
              (min (caddr mnA) (caddr mnB)))
        (list (max (car mxA) (car mxB))
              (max (cadr mxA) (cadr mxB))
              (max (caddr mxA) (caddr mxB)))
      )
    )
  )
)

(defun degw-get-bbox (obj / bb mn mx r exp lst one)
  (degw-ensure-vlax)
  (setq bb nil)

  (if (and obj (vlax-method-applicable-p obj 'Explode))
    (progn
      (setq exp (degw-explode->list obj))
      (if exp
        (progn
          (foreach one exp
            (if (degw-entity-eligible-for-bbox-p one)
              (progn
                (setq r (vl-catch-all-apply 'vla-getboundingbox (list one 'mn 'mx)))
                (if (not (vl-catch-all-error-p r))
                  (setq bb (degw-bbox-union bb (list (degw-_v2l mn) (degw-_v2l mx))))
                )
              )
            )
          )
        )
      )
      (degw-delete-objects exp)
    )
  )

  (if (not bb)
    (progn
      (setq r (vl-catch-all-apply 'vla-getboundingbox (list obj 'mn 'mx)))
      (if (vl-catch-all-error-p r)
        nil
        (list (degw-_v2l mn) (degw-_v2l mx))
      )
    )
    bb
  )
)

(defun degw-bbox-expand (bb tol)
  (if (not bb)
    nil
    (list
      (list (- (car  (car bb)) tol)
            (- (cadr (car bb)) tol)
            (- (caddr(car bb)) tol))
      (list (+ (car  (cadr bb)) tol)
            (+ (cadr (cadr bb)) tol)
            (+ (caddr(cadr bb)) tol))
    )
  )
)

(defun degw-bbox-overlap-p (bb1 bb2)
  (and bb1 bb2
       (not (or
              (> (car  (car bb1)) (car  (cadr bb2)))
              (> (cadr (car bb1)) (cadr (cadr bb2)))
              (> (caddr(car bb1)) (caddr(cadr bb2)))
              (< (car  (cadr bb1)) (car  (car  bb2)))
              (< (cadr (cadr bb1)) (cadr (car  bb2)))
              (< (caddr(cadr bb1)) (caddr(car  bb2)))
            )
       )
  )
)

(defun degw-block-effective-name (blkObj / nm)
  (degw-ensure-vlax)
  (setq nm (vl-catch-all-apply 'vla-get-effectivename (list blkObj)))
  (if (vl-catch-all-error-p nm)
    (setq nm (vla-get-name blkObj))
  )
  (if nm (strcase nm) "")
)

(defun degw-attrs->list (blkObj / raw v)
  (degw-ensure-vlax)
  (if (and blkObj
           (vlax-property-available-p blkObj 'HasAttributes)
           (= (vla-get-HasAttributes blkObj) :vlax-true))
    (progn
      (setq raw (vl-catch-all-apply 'vlax-invoke (list blkObj 'GetAttributes)))
      (if (vl-catch-all-error-p raw)
        nil
        (progn
          (setq v (degw-_v2l raw))
          (cond
            ((null v) nil)
            ((listp v) v)
            ((vlax-objectp v) (list v))
            (T nil)
          )
        )
      )
    )
    nil
  )
)

(defun degw-get-attrvalue (blkObj tag / atts a val)
  (setq val nil)
  (setq atts (degw-attrs->list blkObj))
  (if atts
    (foreach a atts
      (if (= (strcase (vla-get-TagString a)) (strcase tag))
        (setq val (vla-get-TextString a))
      )
    )
  )
  val
)

(defun degw-explode->list (obj / var lst)
  (degw-ensure-vlax)
  (setq var (vl-catch-all-apply 'vlax-invoke (list obj 'Explode)))
  (if (vl-catch-all-error-p var)
    nil
    (progn
      (setq lst (degw-_v2l var))
      (if (listp lst) lst nil)
    )
  )
)

(defun degw-delete-objects (lst)
  (foreach o lst
    (if (and o (vlax-objectp o))
      (vl-catch-all-apply 'vla-delete (list o))
    )
  )
)

(defun degw-intersect-p (o1 o2 / r a)
  (if (and o1 o2
           (vlax-objectp o1) (vlax-objectp o2)
           (vlax-method-applicable-p o1 'IntersectWith)
           (vlax-method-applicable-p o2 'IntersectWith))
    (progn
      (setq r (vl-catch-all-apply 'vlax-invoke (list o1 'IntersectWith o2 0))) ; acExtendNone=0
      (if (vl-catch-all-error-p r)
        nil
        (progn
          (setq a (degw-_v2l r))
          (and (listp a) (> (length a) 0))
        )
      )
    )
    nil
  )
)

(defun degw-objects-intersect-any-p (lst1 lst2 / o1 o2 hit)
  (setq hit nil)
  (foreach o1 lst1
    (if (not hit)
      (foreach o2 lst2
        (if (and (not hit) (degw-intersect-p o1 o2))
          (setq hit T)
        )
      )
    )
  )
  hit
)

(defun degw-point-in-bbox-p (pt bb / mn mx)
  (and pt bb
       (setq mn (car bb) mx (cadr bb))
       (<= (car mn) (car pt))
       (<= (car pt) (car mx))
       (<= (cadr mn) (cadr pt))
       (<= (cadr pt) (cadr mx))
       (<= (caddr mn) (caddr pt))
       (<= (caddr pt) (caddr mx))
  )
)

(defun degw-bbox-inside-p (inner outer / mn1 mx1 mn2 mx2)
  (and inner outer
       (setq mn1 (car inner) mx1 (cadr inner))
       (setq mn2 (car outer) mx2 (cadr outer))
       (<= (car mn2) (car mn1))
       (<= (cadr mn2) (cadr mn1))
       (<= (caddr mn2) (caddr mn1))
       (<= (car mx1) (car mx2))
       (<= (cadr mx1) (cadr mx2))
       (<= (caddr mx1) (caddr mx2))
  )
)

(defun degw-bbox-center (bb / mn mx)
  (if bb
    (progn
      (setq mn (car bb) mx (cadr bb))
      (list (/ (+ (car mn)   (car mx))   2.0)
            (/ (+ (cadr mn)  (cadr mx))  2.0)
            (/ (+ (caddr mn) (caddr mx)) 2.0))
    )
  )
)

(defun degw-touch-p (blkObj mahalObj / tol bb1 bb2 e1 e2 hit ins ctr)
  (setq tol (DEG:CFG-TOL-NUM-OR 'DW_TOUCH_TOL 1e-6))
  (setq bb1 (degw-bbox-expand (degw-get-bbox blkObj) tol))
  (setq bb2 (degw-bbox-expand (degw-get-bbox mahalObj) tol))
  (setq ins (deg-get-inspt blkObj))
  (setq ctr (degw-bbox-center bb1))
  (cond
    ((not (and bb1 bb2)) nil)
    ((degw-bbox-inside-p bb1 bb2) T)
    ((degw-point-in-bbox-p ins bb2) T)
    ((degw-point-in-bbox-p ctr bb2) T)
    ((not (degw-bbox-overlap-p bb1 bb2)) nil)
    (T
      (setq e1 (degw-explode->list blkObj))
      (setq e2 (degw-explode->list mahalObj))
      (setq hit (and e1 e2 (degw-objects-intersect-any-p e1 e2)))
      (degw-delete-objects e1)
      (degw-delete-objects e2)
      hit
    )
  )
)

(defun degw-get-emahal-unique ( / ss i ent obj nm bb lst pair)
  (degw-ensure-vlax)
  (setq lst '())
  (setq ss (ssget "X" '((0 . "INSERT"))))
  (if ss
    (progn
      (setq i 0)
      (while (< i (sslength ss))
        (setq ent (ssname ss i))
        (setq obj (vlax-ename->vla-object ent))
        (if (and (degw-block-effective-name obj)
                 (wcmatch (strcase (degw-block-effective-name obj)) (strcat "*" (strcase (DEG:VAL 'P2)) "*")))
          (progn
            (setq nm (degw-get-attrvalue obj (DEG:VAL 'P2)))
            (if (and nm (/= nm ""))
              (progn
                (if (not (assoc nm lst))
                  (setq lst (cons (cons nm (list obj)) lst))
                  (progn
                    (setq pair (assoc nm lst))
                    (setq lst (subst (cons nm (cons obj (cdr pair))) pair lst))
                  )
                )
              )
            )
          )
        )
        (setq i (1+ i))
      )
    )
  )
  (reverse lst) ; (("MAHAL1" obj1 obj2 ...) ("MAHAL2" obj3 ...) ...)
)

(defun degw-matrix-inc (matrix key col qty / row assocList pair)
  (setq row (assoc key matrix))          ; (key . ((col . qty) ...))
  (if row
    (progn
      (setq assocList (cdr row))
      (setq pair (assoc col assocList))
      (if pair
        (setq assocList (subst (cons col (+ (cdr pair) qty)) pair assocList))
        (setq assocList (cons (cons col qty) assocList))
      )
      (setq matrix (subst (cons key assocList) row matrix))
    )
    (setq matrix (cons (cons key (list (cons col qty))) matrix))
  )
  matrix
)

(defun degw-roworder-add (rowOrder key)
  (if (member key rowOrder)
    rowOrder
    (cons key rowOrder)
  )
)



;;; ===========================================================
;;; DEG_DRZ_V6_FINAL.LSP
;;; 1. mainFarLim = 200.0
;;; 2. YON KONTROLU: Üst/Sol -> L-Tip, Alt/Sað -> Düz.
;;; 3. L-TIP KOSE DUZELTMESÝ:
;;;    L'nin kosesindeki vertexler (pDown ve pDownRin), birbirine
;;;    zýt yönlere 10 birim kaydýrýlarak (Sol/Sað) bozulma giderildi.
;;; ===========================================================


(defun g365_abs (x) (if (< x 0.0) (- x) x))
(defun g365_clayer () (getvar "CLAYER"))
(defun g365_closep (p q) (<= (distance p q) 1e-6))

;; -----------------------------------------------------------
;; Renk eslestirme (ByLayer/ByBlock dahil)
;; -----------------------------------------------------------
(defun g365_layer_color (lay / rec)
  (setq rec (tblsearch "LAYER" lay))
  (if rec
    (abs (cdr (assoc 62 rec)))
    7
  )
)

(defun g365_effective_color (e / ed c lay)
  (setq ed (entget e))
  (setq lay (cdr (assoc 8 ed)))
  (setq c (cdr (assoc 62 ed)))
  (cond
    ((or (null c) (= c 256) (= c 0)) (g365_layer_color lay))
    (t (abs c))
  )
)

(defun g365_append_pt (lst p)
  (if (or (null lst) (not (g365_closep (car (reverse lst)) p)))
    (append lst (list p))
    lst
  )
)

(defun g365_rev (lst / out)
  (setq out nil)
  (while lst
    (setq out (cons (car lst) out))
    (setq lst (cdr lst))
  )
  out
)

(defun g365_last (lst / x)
  (setq x nil)
  (while lst
    (setq x (car lst))
    (setq lst (cdr lst))
  )
  x
)

(defun g365_clean_pts (pts / out p prevPt)
  (setq out nil prevPt nil)
  (while pts
    (setq p (car pts))
    (if (or (null prevPt) (> (distance p prevPt) 1e-9))
      (progn
        (setq out (append out (list (list (car p) (cadr p) 0.0))))
        (setq prevPt (list (car p) (cadr p) 0.0))
      )
    )
    (setq pts (cdr pts))
  )
  out
)

(defun g365_get_pts_lw (e / ed pts pr)
  (setq ed (entget e) pts nil)
  (while ed
    (setq pr (car ed))
    (if (= (car pr) 10)
      (setq pts (append pts (list (list (car (cdr pr)) (cadr (cdr pr)) 0.0))))
    )
    (setq ed (cdr ed))
  )
  (g365_clean_pts pts)
)

(defun g365_get_pts_pl (e / pts en vd p)
  (setq pts nil)
  (setq en (entnext e))
  (while (and en (/= (cdr (assoc 0 (entget en))) "SEQEND"))
    (setq vd (entget en))
    (if (= (cdr (assoc 0 vd)) "VERTEX")
      (progn
        (setq p (cdr (assoc 10 vd)))
        (setq pts (append pts (list (list (car p) (cadr p) 0.0))))
      )
    )
    (setq en (entnext en))
  )
  (g365_clean_pts pts)
)

(defun g365_get_pts_line (e / ed p0 p1)
  (setq ed (entget e))
  (setq p0 (cdr (assoc 10 ed)))
  (setq p1 (cdr (assoc 11 ed)))
  (if (and p0 p1)
    (list (list (car p0) (cadr p0) 0.0) (list (car p1) (cadr p1) 0.0))
    nil
  )
)

(defun g365_get_pts (e / ed typ)
  (setq ed (entget e))
  (setq typ (cdr (assoc 0 ed)))
  (cond
    ((= typ "LWPOLYLINE") (g365_get_pts_lw e))
    ((= typ "POLYLINE")   (g365_get_pts_pl e))
    ((= typ "LINE")       (g365_get_pts_line e))
    (t nil)
  )
)

(defun g365_ptkey (p / sx sy)
  (setq sx (rtos (car p) 2 6))
  (setq sy (rtos (cadr p) 2 6))
  (strcat sx "," sy)
)

(defun g365_dot2 (ax ay bx by) (+ (* ax bx) (* ay by)))

(defun g365_closest_on_seg (p a b / ax ay bx by px py vx vy wx wy vv uPar cx cy)
  (setq ax (car a) ay (cadr a))
  (setq bx (car b) by (cadr b))
  (setq px (car p) py (cadr p))
  (setq vx (- bx ax))
  (setq vy (- by ay))
  (setq wx (- px ax))
  (setq wy (- py ay))
  (setq vv (+ (* vx vx) (* vy vy)))
  (if (<= vv 1e-12)
    (list a 0.0 (distance p a))
    (progn
      (setq uPar (/ (g365_dot2 wx wy vx vy) vv))
      (if (< uPar 0.0) (setq uPar 0.0))
      (if (> uPar 1.0) (setq uPar 1.0))
      (setq cx (+ ax (* uPar vx)))
      (setq cy (+ ay (* uPar vy)))
      (list (list cx cy 0.0) uPar (distance p (list cx cy 0.0)))
    )
  )
)

(defun g365_closest_on_poly (p pts / n i a b bestDist bestSeg bestU bestPt res curPt curU curDist)
  (setq n (length pts))
  (setq i 0)
  (setq bestDist 1e99)
  (setq bestSeg 0)
  (setq bestU 0.0)
  (setq bestPt (car pts))
  (while (< i (1- n))
    (setq a (nth i pts))
    (setq b (nth (1+ i) pts))
    (setq res (g365_closest_on_seg p a b))
    (setq curPt (nth 0 res))
    (setq curU (nth 1 res))
    (setq curDist (nth 2 res))
    (if (< curDist bestDist)
      (progn
        (setq bestDist curDist)
        (setq bestSeg i)
        (setq bestU curU)
        (setq bestPt curPt)
      )
    )
    (setq i (1+ i))
  )
  (list bestPt bestU bestSeg bestDist)
)

(defun g376_is_closed (pts / a b)
  (and pts (>= (length pts) 3)
       (<= (distance (car pts) (last pts)) 1e-6))
)

(defun g376_nth_safe (pts idx / n)
  (setq n (length pts))
  (if (or (< idx 0) (>= idx n)) nil (nth idx pts))
)

(defun g376_nth_wrap (pts idx / n i)
  (setq n (length pts))
  (if (<= n 0)
    nil
    (progn
      (setq i idx)
      (while (< i 0) (setq i (+ i n)))
      (while (>= i n) (setq i (- i n)))
      (nth i pts)
    )
  )
)

(defun g365_nearest_vidx (pts pick / n i bestI bestD dd)
  (setq n (length pts) i 0 bestI 0 bestD 1e99)
  (while (< i n)
    (setq dd (distance (nth i pts) pick))
    (if (< dd bestD) (setq bestD dd bestI i))
    (setq i (1+ i))
  )
  bestI
)

(defun g365_assoc_add (al key val / it)
  (setq it (assoc key al))
  (if it
    (subst (cons key (append (cdr it) (list val))) it al)
    (cons (cons key (list val)) al)
  )
)

(defun g365_assoc_set (al key val / it)
  (setq it (assoc key al))
  (if it
    (subst (cons key val) it al)
    (cons (cons key val) al)
  )
)

(defun g365_sort_u (lst / out mn scan)
  (setq out nil)
  (while lst
    (setq mn (car lst))
    (setq scan (cdr lst))
    (while scan
      (if (< (car (car scan)) (car mn)) (setq mn (car scan)))
      (setq scan (cdr scan))
    )
    (setq out (append out (list mn)))
    (setq lst (vl-remove mn lst))
  )
  out
)

(defun g365_line_inter (a b c d / x1 y1 x2 y2 x3 y3 x4 y4 den lam ix iy)
  (setq x1 (car a) y1 (cadr a))
  (setq x2 (car b) y2 (cadr b))
  (setq x3 (car c) y3 (cadr c))
  (setq x4 (car d) y4 (cadr d))
  (setq den (- (* (- x1 x2) (- y3 y4)) (* (- y1 y2) (- x3 x4))))
  (if (<= (g365_abs den) 1e-12)
    nil
    (progn
      (setq lam (/ (- (* (- x1 x3) (- y3 y4)) (* (- y1 y3) (- x3 x4))) den))
      (setq ix (+ x1 (* lam (- x2 x1))))
      (setq iy (+ y1 (* lam (- y2 y1))))
      (list ix iy 0.0)
    )
  )
)

(defun g365_seg_param (a b p / vx vy wx wy vv parVal)
  (setq vx (- (car b) (car a)))
  (setq vy (- (cadr b) (cadr a)))
  (setq wx (- (car p) (car a)))
  (setq wy (- (cadr p) (cadr a)))
  (setq vv (+ (* vx vx) (* vy vy)))
  (if (<= vv 1e-12)
    nil
    (/ (+ (* wx vx) (* wy vy)) vv)
  )
)

(defun g365_unit (vx vy / L)
  (setq L (distance (list 0.0 0.0 0.0) (list vx vy 0.0)))
  (if (<= L 1e-9)
    (list 0.0 0.0)
    (list (/ vx L) (/ vy L))
  )
)

(defun g365_left_normal (ux uy) (list (- uy) ux))
(defun g365_dot (ax ay bx by) (+ (* ax bx) (* ay by)))

(defun g384_need_corner (p1 corner p2 dist / v1 v2 u1 u2 l1 l2 dotv)
  (if (or (null p1) (null corner) (null p2) (null dist))
    nil
    (progn
      (setq l1 (distance p1 corner))
      (setq l2 (distance p2 corner))
      (if (and (<= l1 (* 2.0 dist)) (<= l2 (* 2.0 dist)))
        (progn
          (setq v1 (list (- (car p1) (car corner)) (- (cadr p1) (cadr corner))))
          (setq v2 (list (- (car p2) (car corner)) (- (cadr p2) (cadr corner))))
          (setq u1 (g365_unit (car v1) (cadr v1)))
          (setq u2 (g365_unit (car v2) (cadr v2)))
          (setq dotv (g365_abs (g365_dot (car u1) (cadr u1) (car u2) (cadr u2))))
          (< dotv 0.98)
        )
        nil
      )
    )
  )
)

(defun g365_offset_vertex_open (pPrev pCur pNext dist side / vx1 vy1 vx2 vy2 u1 u2 n1 n2
                                     a1 b1 a2 b2 ip
                                     ox oy lim
                                     bx by bL bux buy dotv mLen nx2 ny2 len1 len2)
  (setq vx1 (- (car pCur) (car pPrev)))
  (setq vy1 (- (cadr pCur) (cadr pPrev)))
  (setq vx2 (- (car pNext) (car pCur)))
  (setq vy2 (- (cadr pNext) (cadr pCur)))

  (setq len1 (sqrt (+ (* vx1 vx1) (* vy1 vy1))))
  (setq len2 (sqrt (+ (* vx2 vx2) (* vy2 vy2))))

  (setq u1 (g365_unit vx1 vy1))
  (setq u2 (g365_unit vx2 vy2))

  (setq n1 (g365_left_normal (car u1) (cadr u1)))
  (setq n2 (g365_left_normal (car u2) (cadr u2)))

  (setq n1 (list (* side (car n1)) (* side (cadr n1))))
  (setq n2 (list (* side (car n2)) (* side (cadr n2))))

  (setq lim (* 20.0 dist))

  (setq dotv (g365_dot (car u1) (cadr u1) (car u2) (cadr u2)))
  (if (and (> len1 1e-9) (> len2 1e-9) (> dotv 0.9999))
    (progn
      (setq ox (* (car n1) dist))
      (setq oy (* (cadr n1) dist))
    )
    (progn
      (cond
        ((and (<= len1 1e-9) (> len2 1e-9))
          (setq ox (* (car n2) dist) oy (* (cadr n2) dist))
        )
        ((and (<= len2 1e-9) (> len1 1e-9))
          (setq ox (* (car n1) dist) oy (* (cadr n1) dist))
        )
        (t
          (setq a1 (list (+ (car pPrev) (* (car n1) dist)) (+ (cadr pPrev) (* (cadr n1) dist)) 0.0))
          (setq b1 (list (+ (car pCur)  (* (car n1) dist)) (+ (cadr pCur)  (* (cadr n1) dist)) 0.0))
          (setq a2 (list (+ (car pCur)  (* (car n2) dist)) (+ (cadr pCur)  (* (cadr n2) dist)) 0.0))
          (setq b2 (list (+ (car pNext) (* (car n2) dist)) (+ (cadr pNext) (* (cadr n2) dist)) 0.0))
          (setq ip (g365_line_inter a1 b1 a2 b2))

          (if (and ip (<= (distance ip pCur) lim))
            (progn
              (setq ox (- (car ip) (car pCur)))
              (setq oy (- (cadr ip) (cadr pCur)))
            )
            (progn
              (setq bx (+ (car n1) (car n2)))
              (setq by (+ (cadr n1) (cadr n2)))
              (setq bL (distance (list 0.0 0.0 0.0) (list bx by 0.0)))

              (if (<= bL 1e-9)
                (progn (setq bux (car n2)) (setq buy (cadr n2)))
                (progn (setq bux (/ bx bL)) (setq buy (/ by bL)))
              )

              (setq nx2 (car n2))
              (setq ny2 (cadr n2))
              (setq dotv (g365_dot bux buy nx2 ny2))

              (if (<= dotv 0.001)
                (progn (setq ox (* nx2 dist)) (setq oy (* ny2 dist)))
                (progn
                  (setq mLen (/ dist dotv))
                  (if (> mLen lim) (setq mLen lim))
                  (setq ox (* bux mLen))
                  (setq oy (* buy mLen))
                )
              )
            )
          )
        )
      )
    )
  )

  (list (+ (car pCur) ox) (+ (cadr pCur) oy) 0.0)
)

(defun g365_offset_open_pts (pts dist side / n i p0 p1 pn2 pn1 u nrm out pPrev pCur pNext)
  (setq n (length pts))
  (setq out nil)
  (if (< n 2)
    out
    (progn
      (setq p0 (nth 0 pts))
      (setq p1 (nth 1 pts))
      (setq u (g365_unit (- (car p1) (car p0)) (- (cadr p1) (cadr p0))))
      (setq nrm (g365_left_normal (car u) (cadr u)))
      (setq nrm (list (* side (car nrm)) (* side (cadr nrm))))
      (setq out (append out (list (list (+ (car p0) (* (car nrm) dist)) (+ (cadr p0) (* (cadr nrm) dist)) 0.0))))

      (setq i 1)
      (while (< i (1- n))
        (setq pPrev (nth (1- i) pts))
        (setq pCur  (nth i pts))
        (setq pNext (nth (1+ i) pts))
        (setq out (append out (list (g365_offset_vertex_open pPrev pCur pNext dist side))))
        (setq i (1+ i))
      )

      (setq pn2 (nth (- n 2) pts))
      (setq pn1 (nth (- n 1) pts))
      (setq u (g365_unit (- (car pn1) (car pn2)) (- (cadr pn1) (cadr pn2))))
      (setq nrm (g365_left_normal (car u) (cadr u)))
      (setq nrm (list (* side (car nrm)) (* side (cadr nrm))))
      (setq out (append out (list (list (+ (car pn1) (* (car nrm) dist)) (+ (cadr pn1) (* (cadr nrm) dist)) 0.0))))
      out
    )
  )
)

(defun g365_entmake_open_poly (lay pts / n data e p)
  (setq n (length pts))
  (if (and n (> n 1))
    (progn
      (setq data (list
        (cons 0 "LWPOLYLINE")
        (cons 100 "AcDbEntity")
        (cons 8 lay)
        (cons 100 "AcDbPolyline")
        (cons 90 n)
        (cons 70 0)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g365_ed_remove_codes (ed codes / out pr)
  (setq out nil)
  (while ed
    (setq pr (car ed))
    (if (not (member (car pr) codes))
      (setq out (append out (list pr)))
    )
    (setq ed (cdr ed))
  )
  out
)

(defun g365_ed_ins_after_code (ed code ins / out done pr)
  (setq out nil done nil)
  (while ed
    (setq pr (car ed))
    (setq out (append out (list pr)))
    (if (and (not done) (= (car pr) code))
      (progn
        (setq out (append out ins))
        (setq done T)
      )
    )
    (setq ed (cdr ed))
  )
  (if done out (append out ins))
)

(defun g365_copy_color (srcEnt dstEnt / es oS oD srcCol c420 acad cm)
  (if (and srcEnt dstEnt)
    (progn
      (vl-load-com)
      (setq oS (vlax-ename->vla-object srcEnt))
      (setq oD (vlax-ename->vla-object dstEnt))

      (setq srcCol (vl-catch-all-apply 'vla-get-Color (list oS)))
      (if (not (vl-catch-all-error-p srcCol))
        (vl-catch-all-apply 'vla-put-Color (list oD srcCol))
      )

      (setq es (entget srcEnt))
      (setq c420 (assoc 420 es))
      (if c420
        (progn
          (setq acad (vlax-get-acad-object))
          (setq cm (vla-GetInterfaceObject acad "AutoCAD.AcCmColor"))
          (vl-catch-all-apply 'vla-put-ColorValue (list cm (cdr c420)))
          (vl-catch-all-apply 'vla-put-TrueColor (list oD cm))
        )
      )
    )
  )
  dstEnt
)

(defun g365_force_color_aci (ent aci / ed c62)
  (if ent
    (progn
      (setq ed (entget ent))
      (setq ed (g365_ed_remove_codes ed (list 420 430)))
      (setq c62 (assoc 62 ed))
      (if c62
        (setq ed (subst (cons 62 (fix aci)) c62 ed))
        (setq ed (g365_ed_ins_after_code ed 8 (list (cons 62 (fix aci)))))
      )
      (vl-catch-all-apply 'entmod (list ed))
      (vl-catch-all-apply 'entupd (list ent))
    )
  )
  ent
)

(defun g365_add_mouth_cand (candList signVal boundaryPt bA bB brA0 brA1 sideTag maxLen / ip parB parBr)
  (setq ip (g365_line_inter bA bB brA0 brA1))
  (if ip
    (progn
      (setq parB (g365_seg_param bA bB ip))
      (setq parBr (g365_seg_param brA0 brA1 ip))
      (if (and parB parBr
               (>= parB -1e-6) (<= parB (+ 1.0 1e-6))
               (<= (distance boundaryPt ip) maxLen)
               (<= (distance brA0 ip) maxLen))
        (append candList (list (list signVal ip sideTag)))
        candList
      )
    )
    candList
  )
)

(defun g365_pick_best_by_sign (candList wantNeg / best rec sgn absS)
  (setq best nil)
  (while candList
    (setq rec (car candList))
    (setq sgn (car rec))
    (if (or (and wantNeg (< sgn 0.0)) (and (not wantNeg) (> sgn 0.0)))
      (progn
        (setq absS (g365_abs sgn))
        (if (or (null best) (< absS (g365_abs (car best))))
          (setq best rec)
        )
      )
    )
    (setq candList (cdr candList))
  )
  best
)

(defun g365_pick_best_pos_opposite (candList negSideTag / best rec sgn absS)
  (setq best nil)
  (while candList
    (setq rec (car candList))
    (setq sgn (car rec))
    (if (and (> sgn 0.0) (/= (caddr rec) negSideTag))
      (progn
        (setq absS (g365_abs sgn))
        (if (or (null best) (< absS (g365_abs (car best))))
          (setq best rec)
        )
      )
    )
    (setq candList (cdr candList))
  )
  best
)

(defun g365_bump_open_mouth (boundaryPts idx step brPts dist / n bpt maxLen
                                       inA inB outA outB
                                       brL brR brL0 brL1 brR0 brR1
                                       cand negRec posRec posAlt
                                       enter exit enterTag exitTag
                                       startPoly otherPoly otherRev nOther jj seq farOther)
  (setq n (length boundaryPts))
  (if (or (<= idx 0) (>= idx (1- n)) (null brPts) (< (length brPts) 2))
    nil
    (progn
      (setq bpt (nth idx boundaryPts))
      (setq maxLen (* 8.0 dist))
      (setq brL (g365_offset_open_pts brPts dist  1))
      (setq brR (g365_offset_open_pts brPts dist -1))
      (if (or (null brL) (null brR) (< (length brL) 2) (< (length brR) 2))
        nil
        (progn
          (setq inA  (nth (- idx step) boundaryPts))
          (setq inB  (nth idx boundaryPts))
          (setq outA (nth idx boundaryPts))
          (setq outB (nth (+ idx step) boundaryPts))

          (setq brL0 (nth 0 brL)) (setq brL1 (nth 1 brL))
          (setq brR0 (nth 0 brR)) (setq brR1 (nth 1 brR))

          (setq cand nil)

          (setq cand (g365_add_mouth_cand cand (- (distance bpt inA)) bpt inA inB brL0 brL1  1 maxLen))
          (setq cand (g365_add_mouth_cand cand (- (distance bpt inA)) bpt inA inB brR0 brR1 -1 maxLen))

          (setq cand (g365_add_mouth_cand cand (distance bpt outB) bpt outA outB brL0 brL1  1 maxLen))
          (setq cand (g365_add_mouth_cand cand (distance bpt outB) bpt outA outB brR0 brR1 -1 maxLen))

          (setq negRec (g365_pick_best_by_sign cand 1))
          (setq posRec (g365_pick_best_by_sign cand nil))

          (if (and negRec posRec)
            (progn
              (if (= (caddr negRec) (caddr posRec))
                (progn
                  (setq posAlt (g365_pick_best_pos_opposite cand (caddr negRec)))
                  (if posAlt (setq posRec posAlt))
                )
              )

              (setq enter (cadr negRec))
              (setq exit  (cadr posRec))
              (setq enterTag (caddr negRec))
              (setq exitTag  (caddr posRec))

              (if (= enterTag exitTag)
                nil
                (progn
                  (if (= enterTag 1) (setq startPoly brL) (setq startPoly brR))
                  (if (= exitTag  1) (setq otherPoly brL) (setq otherPoly brR))

                  (setq seq nil)
                  (setq seq (g365_append_pt seq enter))

                  (setq jj 1)
                  (while (< jj (length startPoly))
                    (setq seq (g365_append_pt seq (nth jj startPoly)))
                    (setq jj (1+ jj))
                  )

                  (setq farOther (g365_last otherPoly))
                  (setq seq (g365_append_pt seq farOther))

                  (setq otherRev (g365_rev otherPoly))
                  (setq nOther (length otherPoly))
                  (setq jj 1)
                  (while (< jj (1- nOther))
                    (setq seq (g365_append_pt seq (nth jj otherRev)))
                    (setq jj (1+ jj))
                  )

                  (setq seq (g365_append_pt seq exit))
                  seq
                )
              )
            )
            nil
          )
        )
      )
    )
  )
)

(defun g371_sublist (lst start / i out n)
  (setq out nil)
  (setq n (length lst))
  (setq i start)
  (while (< i n)
    (setq out (append out (list (nth i lst))))
    (setq i (1+ i))
  )
  out
)

(defun g371_sublist_rev (lst idx / i out)
  (setq out nil)
  (setq i idx)
  (while (>= i 0)
    (setq out (append out (list (nth i lst))))
    (setq i (1- i))
  )
  out
)

(defun g371_best_contact (mainPts brPts tol / mN bN mi bi mA mB bA bB best bestD
                                   ip uM uB res pMain pBr d)
  (setq best nil)
  (setq bestD 1e99)
  (setq mN (length mainPts))
  (setq bN (length brPts))
  (if (or (< mN 2) (< bN 2))
    nil
    (progn
      (setq mi 0)
      (while (< mi (1- mN))
        (setq mA (nth mi mainPts))
        (setq mB (nth (1+ mi) mainPts))
        (setq bi 0)
        (while (< bi (1- bN))
          (setq bA (nth bi brPts))
          (setq bB (nth (1+ bi) brPts))

          (setq ip (g365_line_inter mA mB bA bB))
          (if ip
            (progn
              (setq uM (g365_seg_param mA mB ip))
              (setq uB (g365_seg_param bA bB ip))
              (if (and uM uB (>= uM -1e-6) (<= uM (+ 1.0 1e-6)) (>= uB -1e-6) (<= uB (+ 1.0 1e-6)))
                (progn
                  (setq d 0.0)
                  (if (< d bestD)
                    (progn
                      (setq bestD d)
                      (setq best (list d mi uM ip bi uB ip))
                    )
                  )
                )
              )
            )
          )

          (setq res (g365_closest_on_seg bA mA mB))
          (setq pMain (nth 0 res))
          (setq uM (nth 1 res))
          (setq d (nth 2 res))
          (if (< d bestD)
            (progn
              (setq bestD d)
              (setq best (list d mi uM pMain bi 0.0 bA))
            )
          )

          (setq res (g365_closest_on_seg bB mA mB))
          (setq pMain (nth 0 res))
          (setq uM (nth 1 res))
          (setq d (nth 2 res))
          (if (< d bestD)
            (progn
              (setq bestD d)
              (setq best (list d mi uM pMain bi 1.0 bB))
            )
          )

          (setq res (g365_closest_on_seg mA bA bB))
          (setq pBr (nth 0 res))
          (setq uB (nth 1 res))
          (setq d (nth 2 res))
          (if (< d bestD)
            (progn
              (setq bestD d)
              (setq best (list d mi 0.0 mA bi uB pBr))
            )
          )

          (setq res (g365_closest_on_seg mB bA bB))
          (setq pBr (nth 0 res))
          (setq uB (nth 1 res))
          (setq d (nth 2 res))
          (if (< d bestD)
            (progn
              (setq bestD d)
              (setq best (list d mi 1.0 mB bi uB pBr))
            )
          )

          (setq bi (1+ bi))
        )
        (setq mi (1+ mi))
      )

      (if (and best (<= (car best) tol)) best nil)
    )
  )
)

(defun g371_branch_dirs (pts segIdx u touchBr / eps n newPts idxTouch i out)
  (setq eps 1e-6)
  (setq n (length pts))
  (setq out nil)
  (if (or (null pts) (< n 2) (null segIdx) (null u) (null touchBr))
    nil
    (progn
      (if (<= u eps)
        (progn
          (setq newPts pts)
          (setq idxTouch segIdx)
        )
        (if (>= u (- 1.0 eps))
          (progn
            (setq newPts pts)
            (setq idxTouch (1+ segIdx))
          )
          (progn
            (setq newPts nil)
            (setq i 0)
            (while (< i n)
              (setq newPts (append newPts (list (nth i pts))))
              (if (= i segIdx)
                (setq newPts (append newPts (list touchBr)))
              )
              (setq i (1+ i))
            )
            (setq idxTouch (1+ segIdx))
          )
        )
      )

      (if (< idxTouch (1- (length newPts)))
        (setq out (append out (list (g371_sublist newPts idxTouch))))
      )
      (if (> idxTouch 0)
        (setq out (append out (list (g371_sublist_rev newPts idxTouch))))
      )
      out
    )
  )
)

(defun g371_make_branch (touchMain dirPts / out)
  (setq out nil)
  (if (and dirPts (>= (length dirPts) 2))
    (progn
      (if (g365_closep touchMain (car dirPts))
        (setq out (cons touchMain (cdr dirPts)))
        (setq out (cons touchMain dirPts))
      )
    )
  )
  (if (and out (>= (length out) 2)) out nil)
)

(defun g371_branch_side (mainAug iKey brPts left right / touch outPt pPrev pNext tx ty bx by cr)
  (setq touch (nth 0 brPts))
  (setq outPt (nth 1 brPts))
  (setq pPrev (if (> iKey 0) (nth (1- iKey) mainAug) (nth iKey mainAug)))
  (setq pNext (if (< iKey (1- (length mainAug))) (nth (1+ iKey) mainAug) (nth iKey mainAug)))
  (setq tx (- (car pNext) (car pPrev)))
  (setq ty (- (cadr pNext) (cadr pPrev)))
  (setq bx (- (car outPt) (car touch)))
  (setq by (- (cadr outPt) (cadr touch)))
  (setq cr (- (* tx by) (* ty bx)))
  (if (> (g365_abs cr) 1e-9)
    (if (> cr 0.0) 1 -1)
    (if (< (distance outPt (nth iKey left)) (distance outPt (nth iKey right))) 1 -1)
  )
)

(setq g372_nodes nil)
(setq g372_nextId 0)
(setq g372_assigned nil)

(defun g372_reset_tree ()
  (setq g372_nodes nil)
  (setq g372_nextId 0)
  (setq g372_assigned nil)
)

(defun g372_get_node (id) (cdr (assoc id g372_nodes)))

(defun g372_node (id sym / nd)
  (setq nd (g372_get_node id))
  (if nd (cdr (assoc sym nd)) nil)
)

(defun g372_set_node (id sym val / pair nd newnd)
  (setq pair (assoc id g372_nodes))
  (if pair
    (progn
      (setq nd (cdr pair))
      (setq newnd (g365_assoc_set nd sym val))
      (setq g372_nodes (subst (cons id newnd) pair g372_nodes))
    )
  )
  val
)

(defun g372_assigned_p (ent) (if (assoc ent g372_assigned) T nil))

(defun g372_assign (ent val)
  (setq g372_assigned (g365_assoc_set g372_assigned ent val))
  val
)

(defun g372_new_node (ent pts parentId parentKey / id nd)
  (setq id g372_nextId)
  (setq g372_nextId (1+ g372_nextId))
  (setq nd (list
    (cons 'id id)
    (cons 'ent ent)
    (cons 'pts pts)
    (cons 'parent parentId)
    (cons 'pkey parentKey)
    (cons 'touchBySeg nil)
    (cons 'childrenByKey nil)
    (cons 'aug nil)
    (cons 'left nil)
    (cons 'right nil)
    (cons 'keyIndex nil)
    (cons 'branchMap nil)
  ))
  (setq g372_nodes (cons (cons id nd) g372_nodes))
  id
)

(defun g372_ss_to_list (ss / i out)
  (setq out nil i 0)
  (if ss
    (while (< i (sslength ss))
      (setq out (cons (ssname ss i) out))
      (setq i (1+ i))
    )
  )
  out
)

(defun g372_build_tree (rootEnt rootPts allEnts tol / rootId queue pid pPts scan entScan brPts bestRes
                              segIdx uVal touchMain brSegIdx brU touchBr key dirList brPts2
                              firstChild touchBySeg childrenByKey childId)
  (g372_reset_tree)
  (setq rootId (g372_new_node rootEnt rootPts nil nil))
  (g372_assign rootEnt rootId)
  (setq queue (list rootId))

  (while queue
    (setq pid (car queue))
    (setq queue (cdr queue))
    (setq pPts (g372_node pid 'pts))

    (setq scan allEnts)
    (while scan
      (setq entScan (car scan))
      (if (and (/= entScan (g372_node pid 'ent)) (not (g372_assigned_p entScan)))
        (progn
          (setq brPts (g365_get_pts entScan))
          (if (and brPts (>= (length brPts) 2))
            (progn
              (setq bestRes (g371_best_contact pPts brPts tol))
              (if bestRes
                (progn
                  (setq segIdx    (nth 1 bestRes))
                  (setq uVal      (nth 2 bestRes))
                  (setq touchMain (nth 3 bestRes))
                  (setq brSegIdx  (nth 4 bestRes))
                  (setq brU       (nth 5 bestRes))
                  (setq touchBr   (nth 6 bestRes))

                  (setq key (g365_ptkey touchMain))

                  (setq touchBySeg (g372_node pid 'touchBySeg))
                  (setq touchBySeg (g365_assoc_add touchBySeg segIdx (list uVal touchMain key)))
                  (g372_set_node pid 'touchBySeg touchBySeg)

                  (setq dirList (g371_branch_dirs brPts brSegIdx brU touchBr))
                  (setq firstChild nil)
                  (while dirList
                    (setq brPts2 (g371_make_branch touchMain (car dirList)))
                    (if (and brPts2 (>= (length brPts2) 2))
                      (progn
                        (setq childId (g372_new_node entScan brPts2 pid key))
                        (if (null firstChild) (setq firstChild childId))
                        (setq queue (append queue (list childId)))
                        (setq childrenByKey (g372_node pid 'childrenByKey))
                        (setq childrenByKey (g365_assoc_add childrenByKey key childId))
                        (g372_set_node pid 'childrenByKey childrenByKey)
                      )
                    )
                    (setq dirList (cdr dirList))
                  )

                  (if firstChild (g372_assign entScan firstChild))
                )
              )
            )
          )
        )
      )
      (setq scan (cdr scan))
    )
  )

  rootId
)

(defun g372_prepare_node (id dist / pts touchBySeg childrenByKey mainAug segK segTouches sorted left right
                               keyIndexMap scan key childIds iKey childId childPts sidePick branchMap)
  (setq pts (g372_node id 'pts))
  (setq touchBySeg (g372_node id 'touchBySeg))
  (setq childrenByKey (g372_node id 'childrenByKey))

  (if (or (null pts) (< (length pts) 2))
    nil
    (progn
      (setq mainAug nil)
      (setq mainAug (append mainAug (list (nth 0 pts))))
      (setq segK 0)
      (while (< segK (1- (length pts)))
        (setq segTouches (cdr (assoc segK touchBySeg)))
        (if segTouches
          (progn
            (setq sorted (g365_sort_u segTouches))
            (while sorted
              (setq mainAug (g365_append_pt mainAug (cadr (car sorted))))
              (setq sorted (cdr sorted))
            )
          )
        )
        (setq mainAug (g365_append_pt mainAug (nth (1+ segK) pts)))
        (setq segK (1+ segK))
      )

      (setq left  (g365_offset_open_pts mainAug dist  1))
      (setq right (g365_offset_open_pts mainAug dist -1))

      (if (or (null left) (null right) (< (length left) 2) (/= (length left) (length mainAug)))
        (progn
          (g372_set_node id 'aug mainAug)
          (g372_set_node id 'left nil)
          (g372_set_node id 'right nil)
          (g372_set_node id 'keyIndex nil)
          (g372_set_node id 'branchMap nil)
          nil
        )
        (progn
          (setq keyIndexMap nil)
          (setq segK 0)
          (while (< segK (length mainAug))
            (setq keyIndexMap (g365_assoc_set keyIndexMap (g365_ptkey (nth segK mainAug)) segK))
            (setq segK (1+ segK))
          )

          (setq branchMap nil)
          (setq scan childrenByKey)
          (while scan
            (setq key (car (car scan)))
            (setq childIds (cdr (car scan)))
            (setq iKey (cdr (assoc key keyIndexMap)))
            (if iKey
              (progn
                (while childIds
                  (setq childId (car childIds))
                  (setq childPts (g372_node childId 'pts))
                  (if (and childPts (>= (length childPts) 2))
                    (progn
                      (setq sidePick (g371_branch_side mainAug iKey childPts left right))
                      (setq branchMap (g365_assoc_add branchMap key (list sidePick childId)))
                    )
                  )
                  (setq childIds (cdr childIds))
                )
              )
            )
            (setq scan (cdr scan))
          )

          (g372_set_node id 'aug mainAug)
          (g372_set_node id 'left left)
          (g372_set_node id 'right right)
          (g372_set_node id 'keyIndex keyIndexMap)
          (g372_set_node id 'branchMap branchMap)
          T
        )
      )
    )
  )
)

(defun g372_prepare_all (dist / ids p)
  (setq ids nil)
  (setq p g372_nodes)
  (while p
    (setq ids (cons (car (car p)) ids))
    (setq p (cdr p))
  )
  (while ids
    (g372_prepare_node (car ids) dist)
    (setq ids (cdr ids))
  )
  T
)

(defun g372_bump_open_mouth_rec (boundaryPts idx step childId dist / childAug brL brR childBM n bpt maxLen
                                        inA inB outA outB brL0 brL1 brR0 brR1
                                        cand negRec posRec posAlt enter exit enterTag exitTag
                                        startPoly otherPoly seq jj key brList tmp rec bump kk2
                                        nOther idxCur didBump farOther)
  (setq childAug (g372_node childId 'aug))
  (setq brL (g372_node childId 'left))
  (setq brR (g372_node childId 'right))
  (setq childBM (g372_node childId 'branchMap))

  (setq n (length boundaryPts))
  (if (or (<= idx 0) (>= idx (1- n)) (null childAug) (< (length childAug) 2)
          (null brL) (null brR) (< (length brL) 2) (< (length brR) 2))
    nil
    (progn
      (setq bpt (nth idx boundaryPts))
      (setq maxLen (* 8.0 dist))

      (setq inA  (nth (- idx step) boundaryPts))
      (setq inB  (nth idx boundaryPts))
      (setq outA (nth idx boundaryPts))
      (setq outB (nth (+ idx step) boundaryPts))

      (setq brL0 (nth 0 brL)) (setq brL1 (nth 1 brL))
      (setq brR0 (nth 0 brR)) (setq brR1 (nth 1 brR))

      (setq cand nil)
      (setq cand (g365_add_mouth_cand cand (- (distance bpt inA)) bpt inA inB brL0 brL1  1 maxLen))
      (setq cand (g365_add_mouth_cand cand (- (distance bpt inA)) bpt inA inB brR0 brR1 -1 maxLen))
      (setq cand (g365_add_mouth_cand cand (distance bpt outB) bpt outA outB brL0 brL1  1 maxLen))
      (setq cand (g365_add_mouth_cand cand (distance bpt outB) bpt outA outB brR0 brR1 -1 maxLen))

      (setq negRec (g365_pick_best_by_sign cand 1))
      (setq posRec (g365_pick_best_by_sign cand nil))

      (if (and negRec posRec)
        (progn
          (if (= (caddr negRec) (caddr posRec))
            (progn
              (setq posAlt (g365_pick_best_pos_opposite cand (caddr negRec)))
              (if posAlt (setq posRec posAlt))
            )
          )

          (setq enter (cadr negRec))
          (setq exit  (cadr posRec))
          (setq enterTag (caddr negRec))
          (setq exitTag  (caddr posRec))

          (if (= enterTag exitTag)
            nil
            (progn
              (if (= enterTag 1) (setq startPoly brL) (setq startPoly brR))
              (if (= exitTag  1) (setq otherPoly brL) (setq otherPoly brR))

              (setq seq nil)
              (setq seq (g365_append_pt seq enter))

              (setq jj 1)
              (while (< jj (length startPoly))
                (setq key (g365_ptkey (nth jj childAug)))
                (setq brList (cdr (assoc key childBM)))
                (setq didBump nil)

                (if brList
                  (progn
                    (setq tmp brList)
                    (while tmp
                      (setq rec (car tmp))
                      (if (= (car rec) enterTag)
                        (progn
                          (setq bump (g377_bump_force_rec startPoly jj 1 (cadr rec) dist))
                          (if bump
                            (progn
                              (setq kk2 0)
                              (while (< kk2 (length bump))
                                (setq seq (g365_append_pt seq (nth kk2 bump)))
                                (setq kk2 (1+ kk2))
                              )
                              (setq didBump 1)
                            )
                          )
                        )
                      )
                      (setq tmp (cdr tmp))
                    )
                  )
                )

                (if (not didBump)
                  (setq seq (g365_append_pt seq (nth jj startPoly)))
                )
                (setq jj (1+ jj))
              )

              (setq farOther (g365_last otherPoly))
              (setq seq (g365_append_pt seq farOther))

              (setq nOther (length otherPoly))
              (setq idxCur (- nOther 2))
              (while (>= idxCur 1)
                (setq key (g365_ptkey (nth idxCur childAug)))
                (setq brList (cdr (assoc key childBM)))
                (setq didBump nil)

                (if brList
                  (progn
                    (setq tmp brList)
                    (while tmp
                      (setq rec (car tmp))
                      (if (= (car rec) exitTag)
                        (progn
                          (setq bump (g377_bump_force_rec otherPoly idxCur -1 (cadr rec) dist))
                          (if bump
                            (progn
                              (setq kk2 0)
                              (while (< kk2 (length bump))
                                (setq seq (g365_append_pt seq (nth kk2 bump)))
                                (setq kk2 (1+ kk2))
                              )
                              (setq didBump 1)
                            )
                          )
                        )
                      )
                      (setq tmp (cdr tmp))
                    )
                  )
                )

                (if (not didBump)
                  (setq seq (g365_append_pt seq (nth idxCur otherPoly)))
                )

                (setq idxCur (1- idxCur))
              )

              (setq seq (g365_append_pt seq exit))
              seq
            )
          )
        )
        nil
      )
    )
  )
)

(defun g373_mouth_ip (bA bB boundaryPt brA0 brA1 sideTag maxLen / ip parB parBr res u d tolTouch)
  (setq ip (g365_line_inter bA bB brA0 brA1))
  (if ip
    (progn
      (setq parB (g365_seg_param bA bB ip))
      (setq parBr (g365_seg_param brA0 brA1 ip))
      (if (and parB parBr
               (>= parB -1e-6) (<= parB (+ 1.0 1e-6))
               (>= parBr -1e-6) (<= parBr (+ 1.0 1e-6))
               (<= (distance boundaryPt ip) maxLen)
               (<= (distance brA0 ip) maxLen))
        (list parB ip sideTag)
        nil
      )
    )
    (progn
      (setq tolTouch 0.1)
      (setq res (g365_closest_on_seg boundaryPt brA0 brA1))
      (setq u (nth 1 res))
      (setq d (nth 2 res))
      (if (and (<= d tolTouch)
               (or (<= u 1e-3) (>= u (- 1.0 1e-3))))
        (progn
          (setq parB (g365_seg_param bA bB boundaryPt))
          (if (and parB (>= parB -1e-6) (<= parB (+ 1.0 1e-6)))
            (list parB boundaryPt sideTag)
            nil
          )
        )
        nil
      )
    )
  )
)

(defun g372_bump_open_mouth_half_rec (boundaryPts idx step childId dist useIncoming / childAug brL brR childBM n bpt maxLen isClosed bInA bInB bOutA bOutB bA2 bB2 recL1 recR1 recL2 recR2 segL segR d1 d2 snapTol cornerTol cornerTol2
                                            bA bB brL0 brL1 brR0 brR1 recL recR enterRec exitRec
                                            enter exit enterTag exitTag
                                            startPoly otherPoly seq jj key brList tmp rec bump kk2
                                            nOther idxCur didBump farOther)
  (setq childAug (g372_node childId 'aug))
  (setq brL (g372_node childId 'left))
  (setq brR (g372_node childId 'right))
  (setq childBM (g372_node childId 'branchMap))

  (setq n (length boundaryPts))
  (if (or (null boundaryPts) (< n 2) (null childAug) (< (length childAug) 2)
          (null brL) (null brR) (< (length brL) 2) (< (length brR) 2))
    nil
    (progn
      (setq isClosed (g376_is_closed boundaryPts))
      (setq maxLen (* 8.0 dist))

      (if isClosed
        (setq bpt (g376_nth_wrap boundaryPts idx))
        (setq bpt (g376_nth_safe boundaryPts idx))
      )

      (if isClosed
        (progn
          (setq bInA  (g376_nth_wrap boundaryPts (- idx step)))
          (setq bInB  (g376_nth_wrap boundaryPts idx))
          (setq bOutA (g376_nth_wrap boundaryPts idx))
          (setq bOutB (g376_nth_wrap boundaryPts (+ idx step)))
        )
        (progn
          (setq bInA  (g376_nth_safe boundaryPts (- idx step)))
          (setq bInB  (g376_nth_safe boundaryPts idx))
          (setq bOutA (g376_nth_safe boundaryPts idx))
          (setq bOutB (g376_nth_safe boundaryPts (+ idx step)))
        )
      )

      (if useIncoming
        (progn
          (setq bA bInA) (setq bB bInB)
          (setq bA2 bOutA) (setq bB2 bOutB)
        )
        (progn
          (setq bA bOutA) (setq bB bOutB)
          (setq bA2 bInA) (setq bB2 bInB)
        )
      )

      (if (or (null bA) (null bB) (null bpt))
        nil
        (progn
          (setq brL0 (nth 0 brL)) (setq brL1 (nth 1 brL))
          (setq brR0 (nth 0 brR)) (setq brR1 (nth 1 brR))

          (setq snapTol 0.2)
          (if (<= (distance bpt brL0) snapTol)
            (progn
              (setq brL (cons bpt (cdr brL)))
              (setq brL0 bpt)
            )
          )
          (if (<= (distance bpt brR0) snapTol)
            (progn
              (setq brR (cons bpt (cdr brR)))
              (setq brR0 bpt)
            )
          )

          (setq recL1 (g373_mouth_ip bA  bB  bpt brL0 brL1  1 maxLen))
          (setq recR1 (g373_mouth_ip bA  bB  bpt brR0 brR1 -1 maxLen))
          (setq recL2 (if (and bA2 bB2) (g373_mouth_ip bA2 bB2 bpt brL0 brL1  1 maxLen) nil))
          (setq recR2 (if (and bA2 bB2) (g373_mouth_ip bA2 bB2 bpt brR0 brR1 -1 maxLen) nil))

          (setq recL nil) (setq segL 0)
          (if recL1 (progn (setq recL recL1) (setq segL 1)))
          (if recL2
            (if (null recL)
              (progn (setq recL recL2) (setq segL 2))
              (progn
                (setq d1 (distance bpt (cadr recL)))
                (setq d2 (distance bpt (cadr recL2)))
                (if (< d2 d1) (progn (setq recL recL2) (setq segL 2)))
              )
            )
          )

          (setq recR nil) (setq segR 0)
          (if recR1 (progn (setq recR recR1) (setq segR 1)))
          (if recR2
            (if (null recR)
              (progn (setq recR recR2) (setq segR 2))
              (progn
                (setq d1 (distance bpt (cadr recR)))
                (setq d2 (distance bpt (cadr recR2)))
                (if (< d2 d1) (progn (setq recR recR2) (setq segR 2)))
              )
            )
          )

          (setq cornerTol 0.2)
          (if (and recL recR (/= segL segR)
                   (<= (distance bpt (cadr recL)) cornerTol)
                   (<= (distance bpt (cadr recR)) cornerTol))
            (progn (setq recL nil) (setq recR nil))
          )


          (if (and recL recR)
            (progn
              (if (< (car recL) (car recR))
                (progn (setq enterRec recL) (setq exitRec recR))
                (progn (setq enterRec recR) (setq exitRec recL))
              )

              (setq enter (cadr enterRec))
              (setq exit  (cadr exitRec))
              (setq enterTag (caddr enterRec))
              (setq exitTag  (caddr exitRec))

              (if (= enterTag exitTag)
                nil
                (progn
                  (if (= enterTag 1) (setq startPoly brL) (setq startPoly brR))
                  (if (= exitTag  1) (setq otherPoly brL) (setq otherPoly brR))

                  (setq seq nil)
                  (setq seq (g365_append_pt seq enter))

                  (setq jj 1)
                  (while (< jj (length startPoly))
                    (setq key (g365_ptkey (nth jj childAug)))
                    (setq brList (cdr (assoc key childBM)))
                    (setq didBump nil)

                    (if brList
                      (progn
                        (setq tmp brList)
                        (while tmp
                          (setq rec (car tmp))
                          (if (= (car rec) enterTag)
                            (progn
                              (setq bump (g377_bump_force_rec startPoly jj 1 (cadr rec) dist))
                              (if bump
                                (progn
                                  (setq kk2 0)
                                  (while (< kk2 (length bump))
                                    (setq seq (g365_append_pt seq (nth kk2 bump)))
                                    (setq kk2 (1+ kk2))
                                  )
                                  (setq didBump 1)
                                )
                              )
                            )
                          )
                          (setq tmp (cdr tmp))
                        )
                      )
                    )

                    (if (not didBump)
                      (setq seq (g365_append_pt seq (nth jj startPoly)))
                    )
                    (setq jj (1+ jj))
                  )

                  (setq farOther (g365_last otherPoly))
                  (setq seq (g365_append_pt seq farOther))

                  (setq nOther (length otherPoly))
                  (setq idxCur (- nOther 2))
                  (while (>= idxCur 1)
                    (setq key (g365_ptkey (nth idxCur childAug)))
                    (setq brList (cdr (assoc key childBM)))
                    (setq didBump nil)

                    (if brList
                      (progn
                        (setq tmp brList)
                        (while tmp
                          (setq rec (car tmp))
                          (if (= (car rec) exitTag)
                            (progn
                              (setq bump (g377_bump_force_rec otherPoly idxCur -1 (cadr rec) dist))
                              (if bump
                                (progn
                                  (setq kk2 0)
                                  (while (< kk2 (length bump))
                                    (setq seq (g365_append_pt seq (nth kk2 bump)))
                                    (setq kk2 (1+ kk2))
                                  )
                                  (setq didBump 1)
                                )
                              )
                            )
                          )
                          (setq tmp (cdr tmp))
                        )
                      )
                    )

                    (if (not didBump)
                      (setq seq (g365_append_pt seq (nth idxCur otherPoly)))
                    )

                    (setq idxCur (1- idxCur))
                  )

                  (setq seq (g365_append_pt seq exit))
                  seq
                )
              )
            )
            nil
          )
        )
      )
    )
  )
)

(defun g377_get_bpt (boundaryPts idx / isClosed)
  (setq isClosed (g376_is_closed boundaryPts))
  (if isClosed
    (g376_nth_wrap boundaryPts idx)
    (g376_nth_safe boundaryPts idx)
  )
)

(defun g378_pt_towards (from to d / vx vy ln k)
  (setq vx (- (car to) (car from)))
  (setq vy (- (cadr to) (cadr from)))
  (setq ln (sqrt (+ (* vx vx) (* vy vy))))
  (if (<= ln 1e-9)
    from
    (progn
      (setq k (/ d ln))
      (list (+ (car from) (* k vx)) (+ (cadr from) (* k vy)) 0.0)
    )
  )
)

(defun g377_valid_inter (p0 p1 a b bpt maxd / ip tb tp)
  (setq ip (g365_line_inter p0 p1 a b))
  (if ip
    (progn
      (setq tb (g365_seg_param a b ip))
      (setq tp (g365_seg_param p0 p1 ip))
      (if (and tb tp
               (>= tb -0.05) (<= tb 1.05)
               (>= tp -0.05) (<= tp 1.05)
               (<= (distance ip bpt) maxd))
        ip
        nil
      )
    )
    nil
  )
)

(defun g377_proj_on_seg (p a b / res)
  (setq res (g365_closest_on_seg p a b))
  (if res (nth 0 res) nil)
)

(defun g377_pick_attach (poly prevPt bpt nextPt maxd usePrev / p0 p1 ip)
  (setq p0 (nth 0 poly))
  (setq p1 (nth 1 poly))
  (if (and p0 p1)
    (progn
      (if usePrev
        (progn
          (setq ip (if prevPt (g377_valid_inter p0 p1 prevPt bpt bpt maxd) nil))
          (if (null ip) (setq ip (if prevPt (g377_proj_on_seg p0 prevPt bpt) nil)))
        )
        (progn
          (setq ip (if nextPt (g377_valid_inter p0 p1 bpt nextPt bpt maxd) nil))
          (if (null ip) (setq ip (if nextPt (g377_proj_on_seg p0 bpt nextPt) nil)))
        )
      )
      (if (and ip (> (distance ip bpt) maxd)) (setq ip nil))
      ip
    )
    nil
  )
)

(defun g377_bump_force_rec (boundaryPts idx step childId dist / bump)
  (setq bump (g372_bump_open_mouth_rec boundaryPts idx step childId dist))
  (if bump bump (g377_bump_vertex_cap boundaryPts idx step childId dist))
)

(defun g377_bump_force_half (boundaryPts idx step childId dist useIncoming / bump)
  (setq bump (g372_bump_open_mouth_half_rec boundaryPts idx step childId dist useIncoming))
  (if bump bump (g377_bump_vertex_cap boundaryPts idx step childId dist))
)

(defun g385_chamfer_fix (pts dist / n i out p0 p1 p2 p3 u01 u12 u23 l12 dot01_23 dot12_01 dot12_23 ip maxD)
  (setq n (length pts))
  (if (or (null pts) (< n 4))
    pts
    (progn
      (setq out nil)
      (setq out (g365_append_pt out (nth 0 pts)))
      (setq i 1)
      (while (< i n)
        (if (<= i (- n 3))
          (progn
            (setq p0 (nth (1- i) pts))
            (setq p1 (nth i pts))
            (setq p2 (nth (1+ i) pts))
            (setq p3 (nth (+ i 2) pts))

            (setq l12 (distance p1 p2))
            (setq u01 (g365_unit (- (car p1) (car p0)) (- (cadr p1) (cadr p0))))
            (setq u12 (g365_unit (- (car p2) (car p1)) (- (cadr p2) (cadr p1))))
            (setq u23 (g365_unit (- (car p3) (car p2)) (- (cadr p3) (cadr p2))))

            (setq dot01_23 (g365_abs (g365_dot (car u01) (cadr u01) (car u23) (cadr u23))))
            (setq dot12_01 (g365_abs (g365_dot (car u12) (cadr u12) (car u01) (cadr u01))))
            (setq dot12_23 (g365_abs (g365_dot (car u12) (cadr u12) (car u23) (cadr u23))))

            (setq maxD (* 8.0 dist))

            (if (and (> dist 0.0)
                     (<= l12 (* 4.0 dist))
                     (< dot01_23 0.35)
                     (< dot12_01 0.95)
                     (< dot12_23 0.95)
                     (<= (distance p1 p0) maxD)
                     (<= (distance p2 p3) maxD))
              (progn
                (setq ip (g365_line_inter p0 p1 p2 p3))
                (if (and ip (<= (distance ip p1) maxD) (<= (distance ip p2) maxD))
                  (progn
                    (setq out (g365_append_pt out ip))
                    (setq i (+ i 2))
                  )
                  (progn
                    (setq out (g365_append_pt out p1))
                    (setq i (1+ i))
                  )
                )
              )
              (progn
                (setq out (g365_append_pt out p1))
                (setq i (1+ i))
              )
            )
          )
          (progn
            (setq out (g365_append_pt out (nth i pts)))
            (setq i (1+ i))
          )
        )
      )
      out
    )
  )
)

(defun g385_simplify_colinear (pts dist / n i out pPrev pCur pNext u1 u2 dotv res d tol)
  (setq n (length pts))
  (if (or (null pts) (< n 3))
    pts
    (progn
      (setq tol (max 0.05 (* 0.02 dist)))
      (setq out nil)
      (setq out (g365_append_pt out (nth 0 pts)))
      (setq i 1)
      (while (< i (1- n))
        (setq pPrev (g365_last out))
        (setq pCur (nth i pts))
        (setq pNext (nth (1+ i) pts))

        (setq u1 (g365_unit (- (car pCur) (car pPrev)) (- (cadr pCur) (cadr pPrev))))
        (setq u2 (g365_unit (- (car pNext) (car pCur)) (- (cadr pNext) (cadr pCur))))
        (setq dotv (g365_abs (g365_dot (car u1) (cadr u1) (car u2) (cadr u2))))

        (setq res (g365_closest_on_seg pCur pPrev pNext))
        (setq d (if res (nth 2 res) 1e99))

        (if (and (> dotv 0.9995) (<= d tol))
          out
          (setq out (g365_append_pt out pCur))
        )

        (setq i (1+ i))
      )
      (setq out (g365_append_pt out (nth (1- n) pts)))
      out
    )
  )
)

(defun g385_postprocess_path (pts dist / p1 p2)
  (setq p1 (g385_chamfer_fix pts dist))
  (setq p2 (g385_simplify_colinear p1 dist))
  p2
)

(defun g418_drop_last (pts / out)
  (if (and pts (> (length pts) 0))
    (reverse (cdr (reverse pts)))
    pts
  )
)

(defun g419_entmake_open_poly (lay pts / n data e p)
  (setq n (length pts))
  (if (and n (> n 1))
    (progn
      (setq data (list
        (cons 0 "LWPOLYLINE")
        (cons 100 "AcDbEntity")
        (cons 8 lay)
        (cons 100 "AcDbPolyline")
        (cons 90 n)
        (cons 70 0)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g419_main_tangent (pts idx / n i0 i1 p0 p1 v)
  (setq n (length pts))
  (if (< n 2)
    (list 0.0 0.0)
    (progn
      (setq i0 (max 0 (1- idx)))
      (setq i1 (min (1- n) (1+ idx)))
      (setq p0 (nth i0 pts))
      (setq p1 (nth i1 pts))
      (setq v (list (- (car p1) (car p0)) (- (cadr p1) (cadr p0))))
      (g365_unit (car v) (cadr v))
    )
  )
)

(defun g419_best_cap_start_index (outPts pMain uMain dist / n i a b mid v u dotv len d score best bestI)
  (setq n (length outPts))
  (setq i 0 best 1e99 bestI 0)
  (while (< i n)
    (setq a (nth i outPts))
    (setq b (nth (rem (1+ i) n) outPts))
    (setq mid (list (/ (+ (car a) (car b)) 2.0) (/ (+ (cadr a) (cadr b)) 2.0) 0.0))
    (setq v (list (- (car b) (car a)) (- (cadr b) (cadr a))))
    (setq len (sqrt (+ (* (car v) (car v)) (* (cadr v) (cadr v)))))
    (setq u (if (> len 1e-9) (list (/ (car v) len) (/ (cadr v) len)) (list 0.0 0.0)))
    (setq dotv (g365_abs (g365_dot (car u) (cadr u) (car uMain) (cadr uMain))))
    (setq d (distance mid pMain))
    (setq score (+ d (* dotv (* 10.0 dist)) (g365_abs (- len (* 2.0 dist)))))
    (if (< score best)
      (progn (setq best score) (setq bestI i))
    )
    (setq i (1+ i))
  )
  (rem (1+ bestI) n)
)

(defun g418_rebuild_outline_seam (outline lay pick mainPts dist / outPts nearV iMain pMain uMain k pts2 newEnt)
  (if (and outline (entget outline))
    (progn
      (setq outPts (g365_get_pts outline))
      (if (and outPts (>= (length outPts) 3) (g376_is_closed outPts))
        (setq outPts (g418_drop_last outPts))
      )
      (if (and outPts (>= (length outPts) 3) pick mainPts dist)
        (progn
          (setq nearV (g417_nearest_vertex pick mainPts))
          (setq iMain (car nearV))
          (setq pMain (cadr nearV))
          (setq uMain (g419_main_tangent mainPts iMain))
          (setq k (g419_best_cap_start_index outPts pMain uMain dist))
          (setq pts2 (g417_rotate outPts k))
          (setq newEnt (g419_entmake_open_poly lay pts2))
          (if newEnt
            (progn
              (entdel outline)
              newEnt
            )
            outline
          )
        )
        outline
      )
    )
    outline
  )
)

(defun g387_dist_pt_seg (p a b / res)
  (setq res (g365_closest_on_seg p a b))
  (if res (nth 2 res) 1e99)
)

(defun g387_on_seg (a b p / u)
  (setq u (g365_seg_param a b p))
  (and u (>= u -0.001) (<= u 1.001))
)

(defun g387_attach_inter (poly a b bpt maxd / p0 p1 ip)
  (setq p0 (nth 0 poly) p1 (nth 1 poly))
  (setq ip (if (and p0 p1 a b) (g377_valid_inter p0 p1 a b bpt maxd) nil))
  ip
)

(defun g388_pen (pt dist)
  (if pt 0.0 dist)
)

(defun g388_best_snap (p a b c d tol / r1 r2 d1 d2)
  (setq r1 (if (and a b) (g365_closest_on_seg p a b) nil))
  (setq r2 (if (and c d) (g365_closest_on_seg p c d) nil))
  (setq d1 (if r1 (nth 2 r1) 1e99))
  (setq d2 (if r2 (nth 2 r2) 1e99))
  (cond
    ((and r1 (<= d1 tol) (<= d1 d2)) (nth 0 r1))
    ((and r2 (<= d2 tol)) (nth 0 r2))
    (t p)
  )
)

(defun g372_colorize_assigned (aci) nil)

(defun g405_safe_entdel (e)
  (if (and e (entget e))
    (vl-catch-all-apply 'entdel (list e))
  )
)

(defun g372_delete_assigned (keepEnt / scan pair ent delCnt skipCnt)
  (setq delCnt 0)
  (setq skipCnt 0)
  (setq scan g372_assigned)
  (while scan
    (setq pair (car scan))
    (setq ent (car pair))
    (if (and ent (/= ent keepEnt) (entget ent))
      (progn
        (if (vl-catch-all-error-p (vl-catch-all-apply 'entdel (list ent)))
          (setq skipCnt (1+ skipCnt))
          (setq delCnt (1+ delCnt))
        )
      )
    )
    (setq scan (cdr scan))
  )
  T
)

(defun g405_on_seg (a b p / u)
  (setq u (g365_seg_param a b p))
  (and u (>= u -0.001) (<= u 1.001))
)

(defun g405_closest_pt (p a b / r)
  (setq r (g365_closest_on_seg p a b))
  (if r (car r) p)
)

(defun g405_dist_pt_seg (p a b / r)
  (setq r (g365_closest_on_seg p a b))
  (if r (nth 2 r) 1e99)
)

(defun g405_clamp_leg (p a b bpt maxLen / cp)
  (setq cp (g405_closest_pt p a b))
  (if (> (distance cp bpt) maxLen)
    (g378_pt_towards bpt cp maxLen)
    cp
  )
)

(defun g405_attach_score (aS aE prevPt bpt nextPt dist / pen)
  (setq pen 0.0)
  (if (and prevPt (not (g405_on_seg prevPt bpt aS)))
    (setq pen (+ pen (* 50.0 dist)))
  )
  (if (and nextPt (not (g405_on_seg bpt nextPt aE)))
    (setq pen (+ pen (* 50.0 dist)))
  )
  (+ pen (distance aS bpt) (distance aE bpt))
)

(defun g406_pt_ok (p)
  (and (listp p)
       (numberp (car p))
       (numberp (cadr p)))
)

(defun g406_to3 (p)
  (if (g406_pt_ok p)
    (list (car p) (cadr p)
          (if (and (caddr p) (numberp (caddr p))) (caddr p) 0.0))
    nil
  )
)

(defun g406_mid (p q / p3 q3)
  (setq p3 (g406_to3 p))
  (setq q3 (g406_to3 q))
  (if (and p3 q3)
    (list (/ (+ (car p3) (car q3)) 2.0)
          (/ (+ (cadr p3) (cadr q3)) 2.0)
          0.0)
    nil
  )
)

(defun g406_get_v (pts i / isClosed)
  (setq isClosed (g376_is_closed pts))
  (if isClosed (g376_nth_wrap pts i) (g376_nth_safe pts i))
)

(defun g406_best_corner_idx (boundaryPts idx step seed / cand bestI bestD i p s3 d)
  (setq s3 (g406_to3 seed))
  (if (null s3)
    idx
    (progn
      (setq cand (list idx
                       (- idx step) (+ idx step)
                       (- idx (* 2 step)) (+ idx (* 2 step))))
      (setq bestI idx)
      (setq bestD 1e99)
      (foreach i cand
        (setq p (g406_get_v boundaryPts i))
        (if (g406_pt_ok p)
          (progn
            (setq d (distance s3 (g406_to3 p)))
            (if (< d bestD) (setq bestD d bestI i))
          )
        )
      )
      bestI
    )
  )
)

(defun g407_ptdist (p q / p3 q3)
  (setq p3 (g406_to3 p))
  (setq q3 (g406_to3 q))
  (if (and p3 q3) (distance p3 q3) 1e99)
)

(defun g408_min2 (a b) (if (< a b) a b))
(defun g408_min3 (a b c) (g408_min2 (g408_min2 a b) c))

(defun g408_swap2 (a b / t) (setq t a) (setq a b) (setq b t) (list a b))

(defun g408_fix_side_order (side aug0 / s0 se)
  (if (and side aug0 (> (length side) 1))
    (progn
      (setq s0 (car side))
      (setq se (g365_last side))
      (if (< (distance (g406_to3 se) (g406_to3 aug0))
             (distance (g406_to3 s0) (g406_to3 aug0)))
        (g365_rev side)
        side
      )
    )
    side
  )
)

(defun g409_p2 (p)
  (and (listp p) (numberp (car p)) (numberp (cadr p)))
)

(defun g409_to3 (p)
  (if (g409_p2 p)
    (list (car p) (cadr p) (if (numberp (caddr p)) (caddr p) 0.0))
    nil
  )
)

(defun g409_dist (a b / aa bb)
  (setq aa (g409_to3 a))
  (setq bb (g409_to3 b))
  (if (and aa bb) (distance aa bb) 1e99)
)

(defun g409_find_p1 (pts p0 / i p1)
  (setq i 1 p1 nil)
  (while (and (< i (length pts)) (null p1))
    (if (> (g409_dist (nth i pts) p0) 1e-6)
      (setq p1 (nth i pts))
    )
    (setq i (1+ i))
  )
  (if p1 p1 (nth 1 pts))
)

(defun g410_ptp (p)
  (and p (listp p) (numberp (car p)) (numberp (cadr p)))
)

(defun g410_find_p1_safe (pts p0 / p1)
  (setq p1 (g409_find_p1 pts p0))
  (if (g410_ptp p1)
    p1
    (if (and pts (> (length pts) 1) (g410_ptp (nth 1 pts)))
      (nth 1 pts)
      p0
    )
  )
)

(defun g411_min (a b) (if (< a b) a b))

(defun g411_orient_triplet_to_bpt (aug brL brR bpt / a0 aN)
  (setq a0 (car aug))
  (setq aN (g365_last aug))
  (if (and a0 aN bpt (> (distance a0 bpt) (distance aN bpt)))
    (list (g365_rev aug) (g365_rev brL) (g365_rev brR))
    (list aug brL brR)
  )
)

(defun g412_wrap_index (i n)
  (if (and n (> n 0))
    (rem (+ i (* n 1000)) n)
    i
  )
)

(defun g412_seek_leg_point (pts idx dir bpt minD isClosed / n j k cand)
  (setq n (length pts))
  (setq j 1)
  (setq cand nil)
  (while (and (null cand) (< j (min 12 n)))
    (setq k (+ idx (* dir j)))
    (if isClosed
      (setq k (g412_wrap_index k n))
      (if (or (< k 0) (>= k n)) (setq k nil))
    )
    (if k
      (progn
        (setq cand (nth k pts))
        (if (or (null cand) (<= (distance cand bpt) minD))
          (setq cand nil)
        )
      )
    )
    (setq j (1+ j))
  )
  (if cand cand (if isClosed (g376_nth_wrap pts (+ idx dir)) (g376_nth_safe pts (+ idx dir))))
)

(defun g413_inter_line (a b c d / x1 y1 x2 y2 x3 y3 x4 y4 den t1 t2 x y)
  (if (and a b c d)
    (progn
      (setq x1 (car a)  y1 (cadr a))
      (setq x2 (car b)  y2 (cadr b))
      (setq x3 (car c)  y3 (cadr c))
      (setq x4 (car d)  y4 (cadr d))
      (setq den (- (* (- x1 x2) (- y3 y4)) (* (- y1 y2) (- x3 x4))))
      (if (< (abs den) 1e-12)
        nil
        (progn
          (setq t1 (- (* x1 y2) (* y1 x2)))
          (setq t2 (- (* x3 y4) (* y3 x4)))
          (setq x (/ (- (* t1 (- x3 x4)) (* (- x1 x2) t2)) den))
          (setq y (/ (- (* t1 (- y3 y4)) (* (- y1 y2) t2)) den))
          (list x y)
        )
      )
    )
    nil
  )
)

(defun g413_attach_on_bound (a b c d dist / ip cp1 cp2 tol)
  (setq tol (* 0.6 dist))
  (setq ip (g413_inter_line a b c d))
  (if ip
    (progn
      (setq cp1 (g365_closest_on_seg ip a b))
      (setq cp2 (g365_closest_on_seg ip c d))
      (if (and cp1 cp2 (<= (nth 2 cp1) tol) (<= (nth 2 cp2) tol))
        ip
        nil
      )
    )
    nil
  )
)

(defun g377_bump_vertex_cap (boundaryPts idx step childId dist /
                                   childAug brL brR childBM bpt isClosed prevPt nextPt
                                   lenPrev lenNext minLen capD minD trip
                                   enter exit
                                   brL0 brR0 side1 side2 tag1 tag2
                                   attIn attOut
                                   n jj idxCur key brList tmp rec bump didBump kk2 farOther seq)

  (setq childAug (g372_node childId 'aug))
  (setq brL      (g372_node childId 'left))
  (setq brR      (g372_node childId 'right))
  (setq childBM  (g372_node childId 'branchMap))

  (setq isClosed (g376_is_closed boundaryPts))
  (setq bpt (g377_get_bpt boundaryPts idx))

  (if (or (null bpt) (null childAug) (< (length childAug) 2)
          (null brL) (null brR) (< (length brL) 2) (< (length brR) 2))
    nil
    (progn
      (setq minD (max (* 0.15 dist) 0.001))
      (setq prevPt (g412_seek_leg_point boundaryPts idx -1 bpt minD isClosed))
      (setq nextPt (g412_seek_leg_point boundaryPts idx  1 bpt minD isClosed))

      (setq trip (g411_orient_triplet_to_bpt childAug brL brR bpt))
      (setq childAug (nth 0 trip))
      (setq brL      (nth 1 trip))
      (setq brR      (nth 2 trip))

      (setq lenPrev (if prevPt (distance bpt prevPt) 0.0))
      (setq lenNext (if nextPt (distance bpt nextPt) 0.0))
      (cond
        ((and prevPt nextPt) (setq minLen (min lenPrev lenNext)))
        (prevPt             (setq minLen lenPrev))
        (nextPt             (setq minLen lenNext))
        (t                  (setq minLen 0.0))
      )

      (setq capD (min (* 0.7 dist) (* 0.45 minLen)))
      (if (< capD (* 0.05 dist)) (setq capD (* 0.05 dist)))

      (setq enter (if prevPt (g378_pt_towards bpt prevPt capD) bpt))
      (setq exit  (if nextPt (g378_pt_towards bpt nextPt capD) bpt))

      (setq brL0 (car brL))
      (setq brR0 (car brR))

      (if (and brL0 brR0 prevPt (< (distance brL0 prevPt) (distance brR0 prevPt)))
        (progn
          (setq side1 brL  tag1  1)
          (setq side2 brR  tag2 -1)
        )
        (progn
          (setq side1 brR  tag1 -1)
          (setq side2 brL  tag2  1)
        )
      )

      (setq attIn  (if prevPt (g413_attach_on_bound (nth 0 side1) (nth 1 side1) prevPt bpt dist) bpt))
      (setq attOut (if nextPt (g413_attach_on_bound (nth 0 side2) (nth 1 side2) bpt nextPt dist) bpt))
      (if (null attIn)  (setq attIn bpt))
      (if (null attOut) (setq attOut bpt))

      (setq side1 (cons attIn  (cdr side1)))
      (setq side2 (cons attOut (cdr side2)))

      (setq n (length childAug))
      (if (or (< n 2) (/= (length side1) n) (/= (length side2) n))
        nil
        (progn
          (setq seq nil)

          (setq seq (g365_append_pt seq enter))
          (if prevPt
            (progn
              (if (and (not (g387_on_seg prevPt bpt attIn)) (not (g365_closep attIn bpt)))
                (setq seq (g365_append_pt seq bpt))
              )
              (setq seq (g365_append_pt seq attIn))
            )
            (setq seq (g365_append_pt seq attIn))
          )

          (setq jj 1)
          (while (< jj n)
            (setq key (g365_ptkey (nth jj childAug)))
            (setq brList (if childBM (cdr (assoc key childBM)) nil))
            (setq didBump nil)

            (if (and brList (> jj 0) (< jj (1- n)))
              (progn
                (setq tmp brList)
                (while tmp
                  (setq rec (car tmp))
                  (if (= (car rec) tag1)
                    (progn
                      (setq bump (g377_bump_force_rec side1 jj 1 (cadr rec) dist))
                      (if bump
                        (progn
                          (setq kk2 0)
                          (while (< kk2 (length bump))
                            (setq seq (g365_append_pt seq (nth kk2 bump)))
                            (setq kk2 (1+ kk2))
                          )
                          (setq didBump 1)
                        )
                      )
                    )
                  )
                  (setq tmp (cdr tmp))
                )
              )
            )

            (if (not didBump)
              (setq seq (g365_append_pt seq (nth jj side1)))
            )
            (setq jj (1+ jj))
          )

          (setq farOther (nth (1- n) side2))
          (setq seq (g365_append_pt seq farOther))

          (setq idxCur (- n 2))
          (while (>= idxCur 0)
            (setq key (g365_ptkey (nth idxCur childAug)))
            (setq brList (if childBM (cdr (assoc key childBM)) nil))
            (setq didBump nil)

            (if (and brList (> idxCur 0) (< idxCur (1- n)))
              (progn
                (setq tmp brList)
                (while tmp
                  (setq rec (car tmp))
                  (if (= (car rec) tag2)
                    (progn
                      (setq bump (g377_bump_force_rec side2 idxCur -1 (cadr rec) dist))
                      (if bump
                        (progn
                          (setq kk2 0)
                          (while (< kk2 (length bump))
                            (setq seq (g365_append_pt seq (nth kk2 bump)))
                            (setq kk2 (1+ kk2))
                          )
                          (setq didBump 1)
                        )
                      )
                    )
                  )
                  (setq tmp (cdr tmp))
                )
              )
            )

            (if (not didBump)
              (setq seq (g365_append_pt seq (nth idxCur side2)))
            )
            (setq idxCur (1- idxCur))
          )

          (if nextPt
            (progn
              (if (and (not (g387_on_seg bpt nextPt attOut)) (not (g365_closep attOut bpt)))
                (setq seq (g365_append_pt seq bpt))
              )
              (setq seq (g365_append_pt seq exit))
            )
            (setq seq (g365_append_pt seq exit))
          )

          seq
        )
      )
    )
  )
)

(defun g415_entmake_closed_poly (lay pts / n data e p)
  (setq n (length pts))
  (if (and n (> n 2))
    (progn
      (setq data (list
        (cons 0 "LWPOLYLINE")
        (cons 100 "AcDbEntity")
        (cons 8 lay)
        (cons 100 "AcDbPolyline")
        (cons 90 n)
        (cons 70 1)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g418_flush_cmd (/ i)
  (setq i 0)
  (while (and (> (getvar "CMDACTIVE") 0) (< i 80))
    (vl-cmdf "")
    (setq i (1+ i))
  )
  (setq i 0)
  (while (and (> (getvar "CMDACTIVE") 0) (< i 10))
    (vl-cmdf "\003") 
    (setq i (1+ i))
  )
  (setq i 0)
  (while (and (> (getvar "CMDACTIVE") 0) (< i 10))
    (vl-cmdf "_.CANCEL")
    (setq i (1+ i))
  )
  T
)

(defun g415_ss_from_list (lst / ss)
  (setq ss (ssadd))
  (while lst
    (if (and (car lst) (entget (car lst)))
      (ssadd (car lst) ss)
    )
    (setq lst (cdr lst))
  )
  ss
)

(defun g415_collect_new_ents (afterEnt / e out)
  (setq out nil)
  (setq e (if afterEnt (entnext afterEnt) (entnext nil)))
  (while e
    (setq out (cons e out))
    (setq e (entnext e))
  )
  (reverse out)
)

(defun g415_poly_closed_p (e / ed flg)
  (setq ed (entget e))
  (setq flg (cdr (assoc 70 ed)))
  (and flg (= 1 (logand 1 flg)))
)

(defun g415_poly_area (e / o a)
  (vl-load-com)
  (setq o (vlax-ename->vla-object e))
  (setq a (vl-catch-all-apply 'vla-get-Area (list o)))
  (if (vl-catch-all-error-p a) 0.0 a)
)

(defun g415_pick_largest_closed_poly (cand / best bestA e a)
  (setq best nil bestA 0.0)
  (while cand
    (setq e (car cand))
    (if (and (entget e)
             (member (cdr (assoc 0 (entget e))) '("LWPOLYLINE" "POLYLINE"))
             (g415_poly_closed_p e))
      (progn
        (setq a (g415_poly_area e))
        (if (> a bestA)
          (progn (setq best e) (setq bestA a))
        )
      )
    )
    (setq cand (cdr cand))
  )
  best
)

(defun g415_pick_any_poly (cand / e typ)
  (setq e nil)
  (while (and cand (null e))
    (setq typ (cdr (assoc 0 (entget (car cand)))))
    (if (member typ '("LWPOLYLINE" "POLYLINE"))
      (setq e (car cand))
    )
    (setq cand (cdr cand))
  )
  e
)

(defun g415_force_close_poly (e / ed old70)
  (if (and e (entget e))
    (progn
      (setq ed (entget e))
      (setq old70 (cdr (assoc 70 ed)))
      (if (null old70) (setq old70 0))
      (if (= 0 (logand old70 1))
        (progn
          (setq ed (subst (cons 70 (boole 7 old70 1)) (assoc 70 ed) ed))
          (entmod ed)
          (entupd e)
        )
      )
    )
  )
  e
)

(defun g415_delete_ents (lst)
  (while lst
    (if (and (car lst) (entget (car lst)))
      (entdel (car lst))
    )
    (setq lst (cdr lst))
  )
  T
)

(defun g415_get_assigned_original_ents (allEnts / out scan e)
  (setq out nil)
  (setq scan allEnts)
  (while scan
    (setq e (car scan))
    (if (and e (g372_assigned_p e))
      (setq out (cons e out))
    )
    (setq scan (cdr scan))
  )
  (reverse out)
)

(defun g415_make_tube_poly_from_ent (ent dist lay / pts left right path)
  (setq pts (g365_get_pts ent))
  (if (and pts (>= (length pts) 2))
    (progn
      (setq left  (g365_offset_open_pts pts dist  1))
      (setq right (g365_offset_open_pts pts dist -1))
      (if (and left right (= (length left) (length pts)) (= (length right) (length pts)))
        (progn
          (setq path (append left (reverse right)))
          (g415_entmake_closed_poly lay path)
        )
        nil
      )
    )
    nil
  )
)

(defun g415_union_tubes_to_outline (tubePls lay / oldCm oldPe oldOsm oldCl beforeR regEnts ssReg beforeU uniEnts regU beforeX curves ssC beforeP newEnts cand best)
  (setq best nil)
  (if (null tubePls)
    nil
    (progn
      (setq oldCm (getvar "CMDECHO"))
      (setq oldPe (getvar "PEDITACCEPT"))
      (setq oldOsm (getvar "OSMODE"))
      (setq oldCl (getvar "CLAYER"))
      (setvar "CMDECHO" 0)
      (setvar "PEDITACCEPT" 1)
      (setvar "OSMODE" 0)

      (setq beforeR (entlast))
      (vl-cmdf "_.REGION" (g415_ss_from_list tubePls) "")
      (setq regEnts (g415_collect_new_ents beforeR))

      (if regEnts
        (progn
          (setq ssReg (g415_ss_from_list regEnts))
          (setq beforeU (entlast))
          (vl-cmdf "_.UNION" ssReg "")
          (setq uniEnts (g415_collect_new_ents beforeU))
          (if uniEnts
            (setq regU (car (last uniEnts)))
            (setq regU (entlast))
          )

          (if (and regU (entget regU))
            (progn
              (setq beforeX (entlast))
              (vl-cmdf "_.EXPLODE" regU)
              (setq curves (g415_collect_new_ents beforeX))

              (if curves
                (progn
                  (setq ssC (g415_ss_from_list curves))
                  (setq beforeP (entlast))
                  (setq oldPEDITACCEPT (getvar "PEDITACCEPT"))
                  (setvar "PEDITACCEPT" 1)
                  (vl-cmdf "_.PEDIT" "_M" ssC "" "_J" 0.0 "_C" "")
                  (setvar "PEDITACCEPT" oldPEDITACCEPT)
                  (g418_flush_cmd)
                  (setq newEnts (g415_collect_new_ents beforeP))
                  (setq cand (append curves newEnts))
                  (setq best (g415_pick_largest_closed_poly cand))
                  (if (null best)
                    (setq best (g415_pick_any_poly cand))
                  )
                  (if best
                    (progn
                      (g415_force_close_poly best)
                      (g415_delete_ents (vl-remove best cand))
                    )
                  )
                )
              )
            )
          )
        )
      )

      (g418_flush_cmd)
      (setvar "CMDECHO" oldCm)
      (setvar "PEDITACCEPT" oldPe)
      (setvar "OSMODE" oldOsm)
      (setvar "CLAYER" oldCl)

      best
    )
  )
)

(defun g417_take (lst n / out i)
  (setq out nil i 0)
  (while (and lst (< i n))
    (setq out (cons (car lst) out))
    (setq lst (cdr lst))
    (setq i (1+ i))
  )
  (reverse out)
)

(defun g417_nthcdr (n lst / i)
  (setq i 0)
  (while (and lst (< i n))
    (setq lst (cdr lst))
    (setq i (1+ i))
  )
  lst
)

(defun g417_rotate (lst k / a b)
  (if (or (null lst) (<= k 0))
    lst
    (progn
      (setq a (g417_nthcdr k lst))
      (setq b (g417_take lst k))
      (append a b)
    )
  )
)

(defun g417_set_nth (lst idx val / i out)
  (setq i 0 out nil)
  (while lst
    (setq out (cons (if (= i idx) val (car lst)) out))
    (setq lst (cdr lst))
    (setq i (1+ i))
  )
  (reverse out)
)

(defun g417_nearest_vertex (p pts / i bestI bestD d)
  (setq i 0 bestI 0 bestD 1e99)
  (while (< i (length pts))
    (setq d (distance p (nth i pts)))
    (if (< d bestD)
      (progn
        (setq bestD d)
        (setq bestI i)
      )
    )
    (setq i (1+ i))
  )
  (list bestI (nth bestI pts) bestD)
)

(defun g417_farthest_index (p pts / i bestI bestD d)
  (setq i 0 bestI 0 bestD -1.0)
  (while (< i (length pts))
    (setq d (distance p (nth i pts)))
    (if (> d bestD)
      (progn
        (setq bestD d)
        (setq bestI i)
      )
    )
    (setq i (1+ i))
  )
  bestI
)

(defun g417_lwpoly_parse (ed / pts bul sw ew curIdx pr code val)
  (setq pts nil bul nil sw nil ew nil curIdx -1)
  (while ed
    (setq pr (car ed))
    (setq code (car pr))
    (setq val (cdr pr))
    (cond
      ((= code 10)
        (setq pts (append pts (list (list (car val) (cadr val) 0.0))))
        (setq bul (append bul (list 0.0)))
        (setq sw  (append sw  (list nil)))
        (setq ew  (append ew  (list nil)))
        (setq curIdx (1- (length pts)))
      )
      ((and (>= curIdx 0) (= code 42))
        (setq bul (g417_set_nth bul curIdx val))
      )
      ((and (>= curIdx 0) (= code 40))
        (setq sw (g417_set_nth sw curIdx val))
      )
      ((and (>= curIdx 0) (= code 41))
        (setq ew (g417_set_nth ew curIdx val))
      )
    )
    (setq ed (cdr ed))
  )
  (list pts bul sw ew)
)

(defun g417_lwpoly_rebuild (pre pts bul sw ew / n i x y out)
  (setq n (length pts))
  (setq out nil)
  (while pre
    (if (= (car (car pre)) 90)
      (setq out (cons (cons 90 n) out))
      (setq out (cons (car pre) out))
    )
    (setq pre (cdr pre))
  )
  (setq out (reverse out))

  (setq i 0)
  (while (< i n)
    (setq x (car (nth i pts)))
    (setq y (cadr (nth i pts)))
    (setq out (append out (list (cons 10 (list x y)))))
    (if (nth i sw) (setq out (append out (list (cons 40 (nth i sw))))))
    (if (nth i ew) (setq out (append out (list (cons 41 (nth i ew))))))
    (if (and (nth i bul) (/= (nth i bul) 0.0))
      (setq out (append out (list (cons 42 (nth i bul)))))
    )
    (setq i (1+ i))
  )
  out
)

(defun g417_lwpoly_rotate_start (e k / ed pre rest parsed pts bul sw ew n pts2 bul2 sw2 ew2 newEd)
  (setq ed (entget e))
  (if (/= (cdr (assoc 0 ed)) "LWPOLYLINE")
    nil
    (progn
      (setq pre nil rest ed)
      (while (and rest (/= (car (car rest)) 10))
        (setq pre (append pre (list (car rest))))
        (setq rest (cdr rest))
      )
      (setq parsed (g417_lwpoly_parse ed))
      (setq pts (nth 0 parsed))
      (setq bul (nth 1 parsed))
      (setq sw  (nth 2 parsed))
      (setq ew  (nth 3 parsed))
      (setq n (length pts))
      (if (< n 3)
        nil
        (progn
          (setq k (rem k n))
          (if (< k 0) (setq k (+ k n)))
          (setq pts2 (g417_rotate pts k))
          (setq bul2 (g417_rotate bul k))
          (setq sw2  (g417_rotate sw k))
          (setq ew2  (g417_rotate ew k))
          (setq newEd (g417_lwpoly_rebuild pre pts2 bul2 sw2 ew2))
          (entmod newEd)
          (entupd e)
          T
        )
      )
    )
  )
)

(defun g417_move_outline_seam (outline pick mainPts / nearV outPts k)
  (if (and outline pick mainPts)
    (progn
      (if (= (cdr (assoc 0 (entget outline))) "LWPOLYLINE")
        (progn
          (setq nearV (g417_nearest_vertex pick mainPts))
          (setq outPts (g365_get_pts outline))
          (if (and outPts (>= (length outPts) 3))
            (progn
              (setq k (g417_farthest_index (cadr nearV) outPts))
              (g417_lwpoly_rotate_start outline k)
            )
          )
        )
      )
    )
  )
  T
)

(vl-load-com)

(defun DEGZ--ename (x)
  (cond
    ((= (type x) 'ENAME) x)
    ((= (type x) 'VLA-OBJECT) (vlax-vla-object->ename x))
    (t nil)
  )
)

(defun DEGZ--pt2d (p)
  (cond
    ((and (listp p) (>= (length p) 2)) (list (car p) (cadr p)))
    (t p)
  )
)

(defun DEGZ--pt3d (p)
  (setq p (DEGZ--pt2d p))
  (list (car p) (cadr p) 0.0)
)

(defun deg-safe-closest-point (crv pt / e r p2)
  (setq e (DEGZ--ename crv))
  (setq p2 (DEGZ--pt2d-safe pt nil))
  (if (or (not e) (not p2))
    p2
    (progn
      (setq r (vl-catch-all-apply 'vlax-curve-getClosestPointTo (list e (list (car p2) (cadr p2) 0.0))))
      (if (vl-catch-all-error-p r)
        p2
        (DEGZ--pt2d-safe r p2)
      )
    )
  )
)

(defun deg-safe-dist-at-point (crv pt / e cp r)
  (setq e  (DEGZ--ename crv))
  (if (not e)
    0.0
    (progn
      (setq cp (deg-safe-closest-point e pt))
      (if (not cp)
        0.0
        (progn
          (setq r  (vl-catch-all-apply 'vlax-curve-getDistAtPoint (list e (list (car cp) (cadr cp) 0.0))))
          (if (vl-catch-all-error-p r)
            0.0
            r
          )
        )
      )
    )
  )
)

(defun DEGZ--safe-props (e / ed pr)
  (setq e  (DEGZ--ename e))
  (setq ed (entget e))
  (setq pr (vl-remove nil (list (assoc 8 ed) (assoc 62 ed) (assoc 6 ed) (assoc 48 ed) (assoc 370 ed))))
  pr
)

(defun DEGZ--get-lwpts (e / ed pts x)
  (setq e  (DEGZ--ename e))
  (setq ed (entget e) pts '())
  (foreach x ed
    (if (= (car x) 10)
      (cond
        ((listp (cdr x)) (setq pts (append pts (list (DEGZ--pt2d (cdr x))))))
        ((and (listp x) (>= (length x) 3))
         (setq pts (append pts (list (list (cadr x) (caddr x))))))
      )
    )
  )
  pts
)

(defun DEGZ--entmakex-lwpoly (pts props closed70 / lst e)
  (if (null closed70) (setq closed70 0))
  (setq lst
    (append
      (list (cons 0 "LWPOLYLINE") (cons 100 "AcDbEntity"))
      props
      (list (cons 100 "AcDbPolyline") (cons 90 (length pts)) (cons 70 closed70))
      (apply 'append (mapcar '(lambda (p) (list (cons 10 (DEGZ--pt2d p)))) pts))
    )
  )
  (entmake lst)
  (setq e (entlast))
  e
)

(defun DEGZ--ensure-last (lst pt)
  (if (or (null lst) (> (distance (DEGZ--pt2d (last lst)) (DEGZ--pt2d pt)) 1e-6))
    (append lst (list (DEGZ--pt2d pt)))
    lst
  )
)

(defun DEGZ--unit (vx vy / l)
  (setq l (sqrt (+ (* vx vx) (* vy vy))))
  (if (> l 1e-12)
    (list (/ vx l) (/ vy l) l)
    (list 0.0 0.0 0.0)
  )
)


(defun DEGZ--perp-axis-from-curve (crv pt / obj par der dx dy)
  ;; ORTHO: curve tangent -> choose dominant axis, return perpendicular unit (rx ry)
  (setq obj (if (vlax-objectp crv) crv (vlax-ename->vla-object crv)))
  (setq par (vl-catch-all-apply 'vlax-curve-getParamAtPoint (list obj pt)))
  (if (vl-catch-all-error-p par)
    (progn
      (list 1.0 0.0)
    )
    (progn
      (setq der (vl-catch-all-apply 'vlax-curve-getFirstDeriv (list obj par)))
      (if (vl-catch-all-error-p der)
        (list 1.0 0.0)
        (progn
          (setq dx (car der) dy (cadr der))
          (if (>= (abs dx) (abs dy))
            (list 0.0 1.0)  ;; curve ~ horizontal -> perp is vertical
            (list 1.0 0.0)  ;; curve ~ vertical   -> perp is horizontal
          )
        )
      )
    )
  )
)

(defun DEGZ--curve-total (crv)
  (setq crv (DEGZ--ename crv))
  (if (not crv)
    0.0
    (vlax-curve-getDistAtParam crv (vlax-curve-getEndParam crv))
  )
)

(defun DEGZ--clamp (v a b)
  (cond ((< v a) a) ((> v b) b) (t v))
)

(defun DEGZ--direct-detour-order (blockSide a b ip ipRin / pa pb ia ib tmp sA sB)
  ;; Direkt/normal baglantida ana hat agzi, blok tarafindaki en yakin ucla eslessin.
  ;; Gecersiz nokta gelirse distance patlamasin; cagiran taraf baglantiyi atlar.
  (setq pa (if (and (listp a) (numberp (car a)) (numberp (cadr a))) (DEGZ--pt2d a) nil))
  (setq pb (if (and (listp b) (numberp (car b)) (numberp (cadr b))) (DEGZ--pt2d b) nil))
  (setq ia (if (and (listp ip) (numberp (car ip)) (numberp (cadr ip))) (DEGZ--pt2d ip) nil))
  (setq ib (if (and (listp ipRin) (numberp (car ipRin)) (numberp (cadr ipRin))) (DEGZ--pt2d ipRin) nil))
  (if (and pa pb ia ib)
    (progn
      (setq sA (+ (DEGZ--safe-distance pa ia) (DEGZ--safe-distance pb ib)))
      (setq sB (+ (DEGZ--safe-distance pa ib) (DEGZ--safe-distance pb ia)))
      (if (< sB sA)
        (progn
          (setq tmp ia)
          (setq ia ib)
          (setq ib tmp)
        )
      )
      (list pa pb ia ib)
    )
    nil
  )
)
(defun DEGZ--distpair10 (distMid dirSign maxDist half / d1 d2)
  ;; distMid etrafýnda ±half (toplam 2*half) olacak þekilde iki mesafe üretir.
  ;; Uçlarda (0 / maxDist) 10 birimi korumak için içeri kaydýrýr.
  (setq full (* 2.0 half))
  (setq d1 (- distMid (* half dirSign)))
  (setq d2 (+ distMid (* half dirSign)))

  ;; önce kaba clamp
  (setq d1 (DEGZ--clamp d1 0.0 maxDist))
  (setq d2 (DEGZ--clamp d2 0.0 maxDist))

  ;; eðer 10 birim bozulduysa, uca göre düzelt
  (if (< (abs (- d2 d1)) (- full 1e-3))
    (cond
      ;; baþlangýca çok yakýn
      ((< distMid half)
        (if (>= dirSign 0.0)
          (progn (setq d1 0.0) (setq d2 (DEGZ--clamp full 0.0 maxDist)))
          (progn (setq d2 0.0) (setq d1 (DEGZ--clamp full 0.0 maxDist)))
        )
      )
      ;; sona çok yakýn
      ((< (- maxDist distMid) half)
        (if (>= dirSign 0.0)
          (progn (setq d2 maxDist) (setq d1 (DEGZ--clamp (- maxDist full) 0.0 maxDist)))
          (progn (setq d1 maxDist) (setq d2 (DEGZ--clamp (- maxDist full) 0.0 maxDist)))
        )
      )
    )
  )

  (list d1 d2)
)

(defun DEGZ--closest-on-seg (a b p / ax ay bx by px py abx aby apx apy den tt cx cy dx dy)
  (setq a (DEGZ--pt2d a) b (DEGZ--pt2d b) p (DEGZ--pt2d p))
  (setq ax (car a) ay (cadr a))
  (setq bx (car b) by (cadr b))
  (setq px (car p) py (cadr p))
  (setq abx (- bx ax) aby (- by ay))
  (setq apx (- px ax) apy (- py ay))
  (setq den (+ (* abx abx) (* aby aby)))
  (if (< den 1e-12)
    (list a (+ (* apx apx) (* apy apy)))
    (progn
      (setq tt (/ (+ (* apx abx) (* apy aby)) den))
      (setq tt (DEGZ--clamp tt 0.0 1.0))
      (setq cx (+ ax (* tt abx)))
      (setq cy (+ ay (* tt aby)))
      (setq dx (- px cx))
      (setq dy (- py cy))
      (list (list cx cy) (+ (* dx dx) (* dy dy)))
    )
  )
)

(defun DEGZ--poly-closest-seg-index (pts p closed70 / n lim i a b res d2 bestI bestD)
  (setq pts (mapcar 'DEGZ--pt2d pts))
  (setq p (DEGZ--pt2d p))
  (setq n (length pts))
  (if (< n 2)
    0
    (progn
      (setq lim (if (/= (logand closed70 1) 0) n (1- n)))
      (setq i 0 bestI 0 bestD 1e99)
      (while (< i lim)
        (setq a (nth i pts))
        (setq b (nth (if (= i (1- n)) 0 (1+ i)) pts))
        (setq res (DEGZ--closest-on-seg a b p))
        (setq d2 (cadr res))
        (if (< d2 bestD)
          (progn (setq bestD d2) (setq bestI i))
        )
        (setq i (1+ i))
      )
      bestI
    )
  )
)

(defun DEGZ--poly-closest-on-seg (pts segIdx p closed70 / n a b res)
  (setq pts (mapcar 'DEGZ--pt2d pts))
  (setq p (DEGZ--pt2d p))
  (setq n (length pts))
  (if (< n 2)
    p
    (progn
      (setq a (nth segIdx pts))
      (setq b (nth (if (= segIdx (1- n)) 0 (1+ segIdx)) pts))
      (setq res (DEGZ--closest-on-seg a b p))
      (car res)
    )
  )
)

(defun DEGZ--cpE-side (crv cp join rx ry / e d tot pPlus pMin v1x v1y v2x v2y s1 s2 rPlus rMin)
  (setq e (DEGZ--ename crv))
  (setq cp (DEGZ--pt2d-safe cp nil))
  (if (or (not e) (not cp))
    cp
    (progn
      (setq d   (deg-safe-dist-at-point e cp))
      (setq tot (DEGZ--curve-total e))
      (setq rPlus (vl-catch-all-apply 'vlax-curve-getPointAtDist (list e (min tot (+ d join)))))
      (setq rMin  (vl-catch-all-apply 'vlax-curve-getPointAtDist (list e (max 0.0 (- d join)))))
      (setq pPlus (if (vl-catch-all-error-p rPlus) cp (DEGZ--pt2d-safe rPlus cp)))
      (setq pMin  (if (vl-catch-all-error-p rMin)  cp (DEGZ--pt2d-safe rMin  cp)))
      (if (and pPlus pMin)
        (progn
          (setq v1x (- (car pPlus) (car cp)))
          (setq v1y (- (cadr pPlus) (cadr cp)))
          (setq v2x (- (car pMin) (car cp)))
          (setq v2y (- (cadr pMin) (cadr cp)))
          (setq s1 (+ (* v1x rx) (* v1y ry)))
          (setq s2 (+ (* v2x rx) (* v2y ry)))
          (if (>= s1 s2) pPlus pMin)
        )
        cp
      )
    )
  )
)

(defun DEGZ--cpE-side-flag (crv cp join choosePlus / e d tot pPlus pMin rPlus rMin)
  (setq e (DEGZ--ename crv))
  (setq cp (DEGZ--pt2d-safe cp nil))
  (if (or (not e) (not cp))
    cp
    (progn
      (setq d   (deg-safe-dist-at-point e cp))
      (setq tot (DEGZ--curve-total e))
      (setq rPlus (vl-catch-all-apply 'vlax-curve-getPointAtDist (list e (min tot (+ d join)))))
      (setq rMin  (vl-catch-all-apply 'vlax-curve-getPointAtDist (list e (max 0.0 (- d join)))))
      (setq pPlus (if (vl-catch-all-error-p rPlus) cp (DEGZ--pt2d-safe rPlus cp)))
      (setq pMin  (if (vl-catch-all-error-p rMin)  cp (DEGZ--pt2d-safe rMin  cp)))
      (if choosePlus pPlus pMin)
    )
  )
)

(defun DEGZ--shorten-toward-cp (crv cp cpE short / e dcp dE tot dNew res)
  (setq e (DEGZ--ename crv))
  (setq cp  (DEGZ--pt2d-safe cp nil))
  (setq cpE (DEGZ--pt2d-safe cpE cp))
  (if (or (not e) (not cp) (not cpE))
    cpE
    (progn
      (setq dcp (deg-safe-dist-at-point e cp))
      (setq dE  (deg-safe-dist-at-point e cpE))
      (setq tot (DEGZ--curve-total e))
      (if (>= dE dcp)
        (setq dNew (max dcp (- dE short)))
        (setq dNew (min dcp (+ dE short)))
      )
      (setq res (vl-catch-all-apply 'vlax-curve-getPointAtDist (list e (DEGZ--clamp dNew 0.0 tot))))
      (if (vl-catch-all-error-p res)
        cpE
        (DEGZ--pt2d-safe res cpE)
      )
    )
  )
)

(defun DEGZ--insert-detour (crv attachA attachB midPts / e pts props pA pB tmp sIdx eIdx head tail k newPts firstPt lastPt keepScore revScore midNorm p)
  (setq e     (DEGZ--ename crv))
  (setq pts   (DEGZ--get-lwpts e))
  (setq props (DEGZ--safe-props e))

  (setq attachA (deg-safe-closest-point e attachA))
  (setq attachB (deg-safe-closest-point e attachB))

  (setq pA (vl-catch-all-apply 'vlax-curve-getParamAtPoint (list e (DEGZ--pt3d attachA))))
  (setq pB (vl-catch-all-apply 'vlax-curve-getParamAtPoint (list e (DEGZ--pt3d attachB))))
  (if (or (vl-catch-all-error-p pA) (vl-catch-all-error-p pB))
    crv
    (progn
      (if (> pA pB)
        (progn
          (setq tmp attachA attachA attachB attachB tmp)
          (setq tmp pA pA pB pB tmp)
        )
      )
      ;; midPts tek nokta ya da karisik liste gelebilir; sadece gercek noktalari kullan.
      (setq midNorm '())
      (cond
        ((null midPts)
          (setq midPts nil)
        )
        ((not (listp midPts))
          (setq midPts nil)
        )
        ((and (numberp (car midPts)) (numberp (cadr midPts)))
          (setq midPts (list (DEGZ--pt2d midPts)))
        )
        (T
          (foreach p midPts
            (if (and (listp p) (numberp (car p)) (numberp (cadr p)))
              (setq midNorm (append midNorm (list (DEGZ--pt2d p))))
            )
          )
          (setq midPts midNorm)
        )
      )

      ;; Polyline cizim yonu ters olsa bile agiz eslesmesi yakinliga gore kalsin.
      (if (and midPts (cdr midPts)
               (listp attachA) (numberp (car attachA)) (numberp (cadr attachA))
               (listp attachB) (numberp (car attachB)) (numberp (cadr attachB)))
        (progn
          (setq firstPt (DEGZ--pt2d (car midPts)))
          (setq lastPt  (DEGZ--pt2d (car (last midPts))))
          (setq keepScore (+ (distance (DEGZ--pt2d attachA) firstPt) (distance (DEGZ--pt2d attachB) lastPt)))
          (setq revScore  (+ (distance (DEGZ--pt2d attachA) lastPt)  (distance (DEGZ--pt2d attachB) firstPt)))
          (if (< revScore keepScore)
            (setq midPts (reverse midPts))
          )
        )
      )

      (setq sIdx (fix pA))
      (setq eIdx (fix pB))

      (setq head '() k 0)
      (while (<= k sIdx)
        (setq head (append head (list (nth k pts))))
        (setq k (1+ k))
      )
      (setq head (DEGZ--ensure-last head attachA))

      (setq tail '() k (1+ eIdx))
      (while (< k (length pts))
        (setq tail (append tail (list (nth k pts))))
        (setq k (1+ k))
      )

      (setq newPts (append head (mapcar 'DEGZ--pt2d midPts) (list attachB) tail))

      (entdel e)
      (DEGZ--entmakex-lwpoly newPts props 0)
    )
  )
)

(defun DEGZ--block-effective-name (en / vla nm ed)
  (setq en (DEGZ--ename en))
  (if (not en)
    nil
    (progn
      (setq ed (entget en))
      (setq nm (cdr (assoc 2 ed)))
      (if (and nm (= (substr nm 1 1) "*"))
        (progn
          (setq vla (vlax-ename->vla-object en))
          (if (vlax-property-available-p vla 'EffectiveName)
            (setq nm (vla-get-EffectiveName vla))
          )
        )
      )
      nm
    )
  )
)

(defun DEGZ--skip-block-p (blk / nm nmU)
  (setq nm  (DEGZ--block-effective-name blk))
  (setq nmU (strcase (if nm nm "")))
  (if (or (vl-string-search "FLASOR" nmU)
          (vl-string-search "FLAR"   nmU))
    T
    nil
  )
)

(defun DEGZ--floor (x)
  (if (>= x 0.0) (fix x) (1- (fix x)))
)

(defun DEGZ--cellkey (p cell / cx cy)
  (setq p (DEGZ--pt2d p))
  (setq cx (DEGZ--floor (/ (car p) cell)))
  (setq cy (DEGZ--floor (/ (cadr p) cell)))
  (list cx cy)
)

(defun DEGZ--cells-put (cells key val / rec)
  (if (setq rec (assoc key cells))
    (subst (cons key (cons val (cdr rec))) rec cells)
    (cons (list key val) cells)
  )
)

(defun DEGZ--uf-init (parents x)
  (if (assoc x parents) parents (cons (cons x x) parents))
)

(defun DEGZ--uf-find (parents x / p)
  (setq p (cdr (assoc x parents)))
  (if (null p) x
    (progn
      (while (and p (not (equal p x)))
        (setq x p)
        (setq p (cdr (assoc x parents)))
      )
      x
    )
  )
)

(defun DEGZ--uf-union (parents a b / ra rb rec)
  (setq ra (DEGZ--uf-find parents a))
  (setq rb (DEGZ--uf-find parents b))
  (if (not (equal ra rb))
    (progn
      (setq rec (assoc rb parents))
      (if rec
        (setq parents (subst (cons rb ra) rec parents))
        (setq parents (cons (cons rb ra) parents))
      )
    )
  )
  parents
)

(defun DEGZ--groups-build (parents data / groups blk rep r rec)
  (setq groups '())
  (foreach rec data
    (setq blk (car rec))
    (setq rep (DEGZ--uf-find parents blk))
    (if (setq r (assoc rep groups))
      (setq groups (subst (cons rep (cons rec (cdr r))) r groups))
      (setq groups (cons (list rep rec) groups))
    )
  )
  groups
)

(defun DEGZ--perp-axis-from-curve-safe (crv pt / tan tx ty)
  ;; ActiveX belge nesnesine ihtiyac duymadan yerel tegetten baskin dik ekseni al.
  ;; AutoCAD Core Console ve GStarCAD'de de ayni sonucu verir.
  (setq tan (DEGZ--canonical-tangent-at crv pt)
        tx (car tan)
        ty (cadr tan))
  (if (>= (abs tx) (abs ty))
    (list 0.0 1.0)
    (list 1.0 0.0))
)

(defun DEGZ--choosePlus-main (mainCrv ip cp join / vvx vvy uu dx dy rx ry rperp cpE d tot pPlus)
  (setq ip (DEGZ--pt2d ip))
  (setq cp (DEGZ--pt2d cp))

  (setq vvx (- (car ip) (car cp)))
  (setq vvy (- (cadr ip) (cadr cp)))
  (setq uu (DEGZ--unit vvx vvy))
  (setq dx (car uu) dy (cadr uu))

  (setq rperp (DEGZ--perp-axis-from-curve-safe mainCrv cp))
              (setq rx (car rperp))
              (setq ry (cadr rperp))

  (setq cpE (DEGZ--cpE-side mainCrv cp join rx ry))

  (setq d   (deg-safe-dist-at-point mainCrv cp))
  (setq tot (DEGZ--curve-total mainCrv))
  (setq pPlus (DEGZ--pt2d (vlax-curve-getPointAtDist (DEGZ--ename mainCrv) (min tot (+ d join)))))

  (if (<= (distance cpE pPlus) 1e-6) T nil)
)

(defun DEGZ--point-toward (a b dist / a2 b2 vx vy uu)
  (setq a2 (DEGZ--pt2d a))
  (setq b2 (DEGZ--pt2d b))
  (setq vx (- (car b2) (car a2)))
  (setq vy (- (cadr b2) (cadr a2)))
  (setq uu (DEGZ--unit vx vy))
  (if (> (caddr uu) 1e-12)
    (list (+ (car a2) (* (car uu) dist)) (+ (cadr a2) (* (cadr uu) dist)))
    a2
  )
)

(defun DEGZ--calc-L-corner (S B uPerp / S2 B2 c1 c2 d1 d2)
  ;; ORTHO KÖÞE: Baðlantýlar sadece 0/90/180/270 olacak þekilde,
  ;; S -> corner -> B iki eksenli (yatay/dikey) kýrýlým üretir.
  (setq S2 (DEGZ--pt2d S))
  (setq B2 (DEGZ--pt2d B))

  ;; Ýki olasý L köþe
  (setq c1 (list (car S2) (cadr B2))) ; önce dikey, sonra yatay
  (setq c2 (list (car B2) (cadr S2))) ; önce yatay, sonra dikey

  ;; S'den daha kýsa ilk bacaðý seç
  (setq d1 (distance S2 c1))
  (setq d2 (distance S2 c2))
  (if (<= d1 d2) c1 c2)
)


(defun DEGZ--ortho-first-axis (ip cp / dx dy)
  ;; T => once X, NIL => once Y
  (setq dx (abs (- (car ip) (car cp))))
  (setq dy (abs (- (cadr ip) (cadr cp))))
  (< dx dy)
)

(defun DEGZ--axis-horiz-at (crv cp / e prm der dx dy)
  ;; Ana hattin tangent yonune gore yatay mi (T) dikey mi (NIL)
  (setq e (DEGZ--ename crv))
  (if (not e)
    T
    (progn
      (setq prm (vl-catch-all-apply 'vlax-curve-getParamAtPoint (list e (DEGZ--pt3d cp))))
      (if (vl-catch-all-error-p prm)
        T
        (progn
          (setq der (vl-catch-all-apply 'vlax-curve-getFirstDeriv (list e prm)))
          (if (vl-catch-all-error-p der)
            T
            (progn
              (setq dx (abs (car der)))
              (setq dy (abs (cadr der)))
              (>= dx dy)
            )
          )
        )
      )
    )
  )
)

;; Ana hattin yonunu, cp noktasinin hemen ilerisinden/gerisinden (choosePlus) örnekleyerek bulur.
;; Köþe (vertex) üstünde derivative belirsiz kaldýðýnda, ilk kolun gerçekten ana hat hizasýnda
;; baþlamasý için kullanýlýr.
(defun DEGZ--axis-horiz-at2 (crv cp choosePlus / e prm dist maxDist dist2 p2 vx vy)
  (setq e (DEGZ--ename crv))
  (if (not e)
    T
    (progn
      (setq prm (vl-catch-all-apply 'vlax-curve-getParamAtPoint (list e (DEGZ--pt3d cp))))
      (if (vl-catch-all-error-p prm)
        (DEGZ--axis-horiz-at crv cp)
        (progn
          (setq dist    (vlax-curve-getDistAtParam e prm))
          (setq maxDist (vlax-curve-getDistAtParam e (vlax-curve-getEndParam e)))
          ;; 1.0 birimlik örnekleme, köþe noktalarýnda yönü netleþtirir
          (setq dist2 (if choosePlus (+ dist 1.0) (- dist 1.0)))
          (setq dist2 (DEGZ--clamp dist2 0.0 maxDist))
          (setq p2 (DEGZ--pt2d (vlax-curve-getPointAtDist e dist2)))
          (setq vx (- (car p2) (car cp)))
          (setq vy (- (cadr p2) (cadr cp)))
          (if (and (< (abs vx) 1e-6) (< (abs vy) 1e-6))
            (DEGZ--axis-horiz-at crv cp)
            (>= (abs vx) (abs vy))
          )
        )
      )
    )
  )
)

(defun DEGZ--perp-axis-from-curve (crv pt / prm deriv tx ty)
  ;; ORTHO için ana hattýn tangent yönüne göre (x/y) eksen-perp döndürür.
  ;; dönüþ: (rx ry) birim vektör (mutlak eksen), iþaret sideFact ile verilir.
  (setq prm (vlax-curve-getParamAtPoint (DEGZ--ename crv) (DEGZ--pt3d pt)))
  (setq deriv (vlax-curve-getFirstDeriv (DEGZ--ename crv) prm))
  (setq tx (car deriv) ty (cadr deriv))
  (if (> (abs tx) (abs ty))
    (list 0.0 1.0)   ;; tangent yatay => perp dikey
    (list 1.0 0.0)   ;; tangent dikey => perp yatay
  )
)

(defun DEGZ--calc-L-corner-mode (S B mode / S2 B2)
  ;; ORTHO KÖÞE (MODLU): mode = 'vfirst veya 'hfirst
  ;; vfirst: (Sx, By)  -> önce dikey, sonra yatay
  ;; hfirst: (Bx, Sy)  -> önce yatay, sonra dikey
  (setq S2 (DEGZ--pt2d S))
  (setq B2 (DEGZ--pt2d B))
  (if (= mode 'vfirst)
    (list (car S2) (cadr B2))
    (list (car B2) (cadr S2))
  )
)
(defun DEGZ--lmode-along-main (cpA cpB / a b dx dy)
  ;; ORTHO zorlanan yerlerde ilk bacak her zaman ana hat hizasinda olsun:
  ;; cpA->cpB vektoru ana hattin tangent eksenini temsil eder.
  ;; yatay => 'hfirst (ilk bacak yatay), dikey => 'vfirst (ilk bacak dikey)
  (setq a (DEGZ--pt2d cpA))
  (setq b (DEGZ--pt2d cpB))
  (setq dx (abs (- (car b) (car a))))
  (setq dy (abs (- (cadr b) (cadr a))))
  (if (>= dx dy) 'hfirst 'vfirst)
)

;; ORTHO zorlanan baglantilarda ana hat hizasini secmek icin:
;; cpCur noktasinda egri uzerinde iki yonde (once/sonra) kucuk bir ornek alinir.
;; Blok vektoru ile daha iyi hizalanan yon secilir; bu sayede cpCur bir vertex uzerindeyken
;; "yanlis segment" baz alinmaz (blok sag/ustte kalinca gorulen bozulma).
(defun DEGZ--lmode-along-main-at (crv cpCur ip / e cp b d len eps d1 d2 p1 p2 v1 v2 vt dot1 dot2 vx vy)
  (setq e (DEGZ--ename crv))
  (setq cp (DEGZ--pt2d cpCur))
  (setq b  (DEGZ--pt2d ip))
  (setq vt (list (- (car b) (car cp)) (- (cadr b) (cadr cp)) 0.0))

  ;; dist clamp
  (setq d   (vlax-curve-getDistAtPoint e cp))
  (setq len (vlax-curve-getDistAtParam e (vlax-curve-getEndParam e)))
  (setq eps 1.0)
  (setq d1 (max 0.0 (- d eps)))
  (setq d2 (min len (+ d eps)))
  (setq p1 (DEGZ--pt2d (vlax-curve-getPointAtDist e d1)))
  (setq p2 (DEGZ--pt2d (vlax-curve-getPointAtDist e d2)))

  ;; v1: p1->cp, v2: cp->p2
  (setq v1 (list (- (car cp) (car p1)) (- (cadr cp) (cadr p1)) 0.0))
  (setq v2 (list (- (car p2) (car cp)) (- (cadr p2) (cadr cp)) 0.0))

  (setq dot1 (abs (+ (* (car v1) (car vt)) (* (cadr v1) (cadr vt)))))
  (setq dot2 (abs (+ (* (car v2) (car vt)) (* (cadr v2) (cadr vt)))))

  (if (>= dot2 dot1)
    (progn (setq vx (car v2)) (setq vy (cadr v2)))
    (progn (setq vx (car v1)) (setq vy (cadr v1)))
  )

  (if (> (abs vx) (abs vy)) 'hfirst 'vfirst)
)

(defun DEGZ--canonical-tangent-at (crv pt / e prm der ln tx ty)
  ;; Polyline cizim yonunden bagimsiz yerel teget: +X, dikeyde +Y yonune sabitlenir.
  (setq e (DEGZ--ename crv))
  (if (not e)
    (list 1.0 0.0)
    (progn
      (setq prm
        (vl-catch-all-apply
          'vlax-curve-getParamAtPoint
          (list e (DEGZ--pt3d (deg-safe-closest-point e pt)))
        )
      )
      (if (vl-catch-all-error-p prm)
        (list 1.0 0.0)
        (progn
          (setq der (vl-catch-all-apply 'vlax-curve-getFirstDeriv (list e prm)))
          (if (or (vl-catch-all-error-p der) (not (listp der)))
            (list 1.0 0.0)
            (progn
              (setq ln (sqrt (+ (* (car der) (car der)) (* (cadr der) (cadr der)))))
              (if (<= ln 1e-12)
                (list 1.0 0.0)
                (progn
                  (setq tx (/ (car der) ln)
                        ty (/ (cadr der) ln))
                  (if (or (< tx -1e-10)
                          (and (<= (abs tx) 1e-10) (< ty 0.0)))
                    (setq tx (- tx) ty (- ty))
                  )
                  (list tx ty)
                )
              )
            )
          )
        )
      )
    )
  )
)

(defun DEGZ--local-side-factor (crv pt dx dy rx ry / tan tx ty nx ny dotT dotN refx refy)
  ;; Egik hatta WCS RIGHT/TOP esigi yerine ana hattin yerel eksenini kullan.
  ;; Baglanti ana hatta paralelse ofset +yerel normale, dikse -yerel tegete bakar.
  (setq tan (DEGZ--canonical-tangent-at crv pt)
        tx (car tan)
        ty (cadr tan)
        nx (- ty)
        ny tx
        dotT (+ (* dx tx) (* dy ty))
        dotN (+ (* dx nx) (* dy ny)))
  (if (>= (abs dotT) (abs dotN))
    (setq refx nx refy ny)
    (setq refx (- tx) refy (- ty))
  )
  (if (>= (+ (* rx refx) (* ry refy)) 0.0) 1.0 -1.0)
)

(defun DEGZ--APPLY (crv0 ss / crv i blk ip blk2 ip2
               ptsMain propsMain mainTmp mainClosed guideCrv
               joinCand short shift approach
               vvx vvy uu dx dy len rx ry ipRin
               nearLim mainFarLim mergeOff
               cell cells
               parents data
               groups
               forcedReps sideMap segMap
               anchorMap stemMap  remoteMap mergeMap
               dirMap dirRec udir mdx mdy p1 ipb p1b pJoin stemRec stemA stemB cpSec pStep pStepb
               g rep recs r bestRec bestIp bestD dNow segIdx choosePlus
               procData anchorRec remote
               forceMain isAnchor cpMain cpCur cpE cpEshort
               uTan uPerp corner1 corner2 paramCur distEnds
               pDown pDownRin uDirRemote anchorStemDir
               key cx cy ix iy rec item mergePt isTargetSide
               sX sY sideFact 
               ipAvg pMid paramMid deriv Tlen Tx Ty Lx Ly dotProd dirSign distMid distDown distDownRin maxDist
               pMerge pMergeRin pLeft pRight ipLeft ipRight pMainTop pMainBot ipTop ipBot yTop yBot pTopA pBotA pTopB pBotB pTopDrop pBotDrop scoreA scoreB outsideLeft fromTop sideMode shortIp longIp calcCrv)

  (vl-load-com)

  (setq joinCand 20.0)
  (setq short    10.0)
  (setq shift    10.0)
  (setq approach 10.0)

  (setq nearLim    100.0)
  (setq mainFarLim 200.0)
  (setq mergeOff   50.0)

  (setq crv0 (DEGZ--ename crv0))

  (if (not (and crv0 (entget crv0)))
    (progn (princ "\nDZ: Gecersiz polyline.") (princ))
    (if (not (and ss (= (type ss) 'PICKSET) (> (sslength ss) 0)))
      (progn (princ "\nDZ: Block secimi yok.") (princ))
      (progn

        (setq ptsMain   (DEGZ--get-lwpts crv0))
        (setq propsMain (DEGZ--safe-props crv0))
        (setq mainClosed (cdr (assoc 70 (entget crv0))))
        (if (null mainClosed) (setq mainClosed 0))
        (setq mainClosed (if (/= (logand mainClosed 1) 0) 1 0))
        (setq mainTmp   (DEGZ--entmakex-lwpoly ptsMain propsMain mainClosed))

        (setq cell    nearLim)
        (setq cells   '())
        (setq parents '())
        (setq data    '())

        (setq i 0)
        (while (< i (sslength ss))
          (setq blk (ssname ss i))
          (if (not (DEGZ--skip-block-p blk))
            (progn
              (setq ip (DEGZ--pt2d (cdr (assoc 10 (entget blk)))))

              (setq parents (DEGZ--uf-init parents blk))
              (setq data (append data (list (list blk ip))))

              (setq key (DEGZ--cellkey ip cell))
              (setq cx (car key) cy (cadr key))

              (setq ix -1)
              (while (<= ix 1)
                (setq iy -1)
                (while (<= iy 1)
                  (setq rec (assoc (list (+ cx ix) (+ cy iy)) cells))
                  (if rec
                    (foreach item (cdr rec)
                      (setq blk2 (car item))
                      (setq ip2  (cadr item))
                      (if (and blk2 ip2 (<= (distance ip ip2) nearLim))
                        (setq parents (DEGZ--uf-union parents blk blk2))
                      )
                    )
                  )
                  (setq iy (1+ iy))
                )
                (setq ix (1+ ix))
              )

              (setq cells (DEGZ--cells-put cells (list cx cy) (list blk ip)))
            )
          )
          (setq i (1+ i))
        )

        (setq groups (DEGZ--groups-build parents data))

        (setq forcedReps '())
        (setq sideMap    '())
        (setq segMap     '())
        (setq anchorMap  '())
        (setq stemMap    '())
        (setq remoteMap  '())
        (setq mergeMap   '())
        (setq dirMap     '())

        (foreach g groups
          (setq rep  (car g))
          (setq recs (cdr g))

          (setq bestRec nil)
          (setq bestD   1e99)
          (foreach r recs
            (setq ip (cadr r))
            (setq cpMain (deg-safe-closest-point mainTmp ip))
            (setq dNow (distance (DEGZ--pt2d ip) (DEGZ--pt2d cpMain)))
            (if (< dNow bestD)
              (progn (setq bestD dNow) (setq bestRec r))
            )
          )
          (if (null bestRec) (setq bestRec (car recs)))
          (setq bestIp (cadr bestRec))
          (setq anchorMap (cons (cons rep bestRec) anchorMap))

          (setq cpMain (deg-safe-closest-point mainTmp bestIp))
          (setq stemMap (cons (cons rep (list (DEGZ--pt2d bestIp) (DEGZ--pt2d cpMain))) stemMap))
          (setq choosePlus (DEGZ--choosePlus-main mainTmp bestIp cpMain joinCand))
          (setq sideMap (cons (cons rep choosePlus) sideMap))
          (setq segIdx (DEGZ--poly-closest-seg-index ptsMain bestIp mainClosed))
          (setq segMap (cons (cons rep segIdx) segMap))

          (if (> (length recs) 1)
            (progn
              (if (> bestD mainFarLim)
                (progn
                  (setq remoteMap (cons (cons rep T) remoteMap))
                  (setq mergePt (DEGZ--point-toward bestIp cpMain mergeOff))
                  (setq mergeMap (cons (cons rep mergePt) mergeMap))

                  (setq udir (DEGZ--unit (- (car bestIp) (car cpMain)) (- (cadr bestIp) (cadr cpMain))))
                  (setq dirMap (cons (cons rep (list (car udir) (cadr udir))) dirMap))
                )
                (progn
                  (setq remoteMap (cons (cons rep nil) remoteMap))
                  (setq forcedReps (cons rep forcedReps))
                )
              )
            )
            (setq remoteMap (cons (cons rep nil) remoteMap))
          )
        )

        (setq procData '())
        (foreach g groups
          (setq rep  (car g))
          (setq recs (cdr g))
          (setq remote (cdr (assoc rep remoteMap)))
          (if (and remote (> (length recs) 1))
            (progn
              (setq anchorRec (cdr (assoc rep anchorMap)))
              (setq procData (append procData (list anchorRec)))
              (foreach r recs
                (if (not (equal (car r) (car anchorRec)))
                  (setq procData (append procData (list r)))
                )
              )
            )
            (setq procData (append procData recs))
          )
        )

        (setq crv crv0)

        (foreach rec procData
          (setq blk (car rec))
          (setq ip  (cadr rec))

          (setq rep (DEGZ--uf-find parents blk))
          (setq choosePlus (cdr (assoc rep sideMap)))
          (if (null choosePlus) (setq choosePlus T))
          (setq remote (cdr (assoc rep remoteMap)))

          (setq anchorRec (cdr (assoc rep anchorMap)))
          (setq isAnchor (and remote anchorRec (equal blk (car anchorRec))))
          (setq forceMain (if (member rep forcedReps) T nil))

          (cond
            (forceMain
              (progn
                (setq segIdx (cdr (assoc rep segMap)))
                (if (null segIdx) (setq segIdx 0))
                (setq cpMain (DEGZ--poly-closest-on-seg ptsMain segIdx ip mainClosed))
              )
            )
            (remote
              (if isAnchor
                (progn
                  (setq segIdx (cdr (assoc rep segMap)))
                  (if (null segIdx) (setq segIdx 0))
                  (setq cpMain (DEGZ--poly-closest-on-seg ptsMain segIdx ip mainClosed))
                )
                (progn
                  (setq cpMain (deg-safe-closest-point mainTmp ip))
                )
              )
            )
            (T (setq cpMain (deg-safe-closest-point mainTmp ip)))
          )

          (setq cpCur (deg-safe-closest-point crv cpMain))

          (setq ip     (DEGZ--pt2d ip))
          (setq cpMain (DEGZ--pt2d cpMain))
          (setq cpCur  (DEGZ--pt2d cpCur))

          (setq vvx (- (car ip) (car cpMain)))
          (setq vvy (- (cadr ip) (cadr cpMain)))
          
          (setq orthoForced (and (> (abs vvx) 1e-6) (> (abs vvy) 1e-6)))
(setq shiftBlk (if orthoForced 10.0 shift))

;; ORTHO zorlamasi (diag) durumunda dx/dy eksenini sabitle:
;; - Bloktan ana hatta en kisa eksen (X veya Y) secilir.
;; - Böylece shiftBlk=10.0 gercekten 10 olarak kalir (capraz unit ile bozulmaz).
(if orthoForced
  (progn
    (setq firstX (>= (abs vvx) (abs vvy)))
    (setq dx (if firstX (if (>= vvx 0.0) 1.0 -1.0) 0.0))
    (setq dy (if firstX 0.0 (if (>= vvy 0.0) 1.0 -1.0)))
    (setq len 100.0)
  )
  (progn
    (setq uu (DEGZ--unit vvx vvy))
    (setq dx (car uu) dy (cadr uu) len (caddr uu))
  )
)

          (if (and remote (not isAnchor))
            (progn
              (setq uDirRemote (cdr (assoc rep dirMap)))
              (setq dx (car uDirRemote))
              (setq dy (cadr uDirRemote))
              (setq len 100.0)
            )
          )

          (if (> len 1e-9)
            (progn
              (setq rx dy)
              (setq ry (- dx))

              ;; =========================================================
              ;; 1. BLOK BACAK YONU VE TARAF KONTROLU (HERKES ICIN)
              ;; =========================================================
              (setq isTargetSide (or (> dy 1e-4) (< dx -1e-4)))
              (setq sideFact (if isTargetSide -1.0 1.0))

              ;; Sol/Ust taraf ise bacaklari ters yone cevir
              (setq ipRin
                (list
                  (+ (car ip) (* rx shiftBlk sideFact))
                  (+ (cadr ip) (* ry shiftBlk sideFact))
                )
              )
              (setq ipRin
                 (list 
                   (- (car ipRin) (* dx approach))
                   (- (cadr ipRin) (* dy approach))
                 )
              )
              
              ;; cpE noktasini da tarafa gore duzelt (Referans icin)
              (setq rx (* rx sideFact))
              (setq ry (* ry sideFact))

              ;; Remote + anchor + sol/ust ise ANA HAT UZERINDEKI CIKIS VERTEX'INI OBUR TARAFA AL
              ;; (blok bacagi/yonu degismez, sadece ana hatta degdigi taraf degisir)
              (if (and remote isAnchor isTargetSide)
                (setq choosePlus (if choosePlus nil T))
              )

              (if (or forceMain remote)
                (setq cpE (DEGZ--cpE-side-flag crv cpCur joinCand choosePlus))
                (setq cpE (DEGZ--cpE-side      crv cpCur joinCand rx ry))
              )
              (setq cpCur (DEGZ--pt2d-safe cpCur cpMain))
              (setq cpE   (DEGZ--pt2d-safe cpE cpCur))
              (if (and cpCur cpE)
                (setq cpEshort (DEGZ--shorten-toward-cp crv cpCur cpE (min short (* (distance cpCur cpE) 0.45))))
                (setq cpEshort cpCur)
              )
              (setq cpEshort (DEGZ--pt2d-safe cpEshort cpCur))

              (if (and cpCur cpEshort (> (distance cpCur cpEshort) 1e-4))
                (progn
                  
                  (if (and remote (not isAnchor))
                     ;; =====================================================
                     ;; DURUM A: UZAK BLOKLAR (REMOTE) -> L-SHAPE / MERGE
                     ;; =====================================================
                     ;; * Bu bloklar komsu hattina baglanmali (Merge).
                     ;; * Hesaplamalar 'crv' (islenmis hat) uzerinde yapilmali.
                     (progn
                       ;; pMerge: ip'den mergeOff kadar asagi
                       (setq pMerge
                        (list
                          (+ (car ip) (* (- dx) mergeOff))
                          (+ (cadr ip) (* (- dy) mergeOff))
                        )
                       )
                       ;; pMergeRin: ipRin hizasinda
                       (setq pMergeRin
                        (list
                          (+ (car pMerge) (- (car ipRin) (car ip)))
                          (+ (cadr pMerge) (- (cadr ipRin) (cadr ip)))
                        )
                       )
                       
                       ;; Ana hat uzerindeki noktalar (Mevcut 'crv' uzerinden alinir)
                       (setq cpCur    (deg-safe-closest-point crv pMerge))
                       (setq cpEshort (deg-safe-closest-point crv pMergeRin))
                       
                       ;; Baglanti: pMerge noktalarini kullan (L Sekli)
                       ;; ACI ZORLANAN (ORTHO) DURUMDA:
                       ;; Ilk kolu her zaman "ana hat hizasinda" baslatmak icin, cpCur noktasinda
                       ;; egri uzerinde iki yonde orneklenir ve bloða dogru daha iyi hizalanan
                       ;; segmentin ekseni secilir (vertex ustu sapmalari engeller).
                       (if orthoForced
                         (setq lmode (DEGZ--lmode-along-main-at crv cpCur ip))
                         (progn
                           (setq firstX (DEGZ--ortho-first-axis ip cpCur))
                           (setq lmode (if firstX 'hfirst 'vfirst))
                         )
                       )

                       (setq corner1 (DEGZ--calc-L-corner-mode cpCur    ip   lmode))
                       (setq corner2 (DEGZ--calc-L-corner-mode cpEshort ipRin lmode))

                       (setq crv (DEGZ--insert-detour crv cpCur cpEshort (list corner1 ip ipRin corner2)))
                     )
                     
                     ;; =====================================================
                     ;; DURUM B: YAKIN BLOKLAR (DIRECT CONNECT)
                     ;; =====================================================
                     ;; * Bu bloklar DIREKT ana hatta baglanmali.
                     ;; * Komsunun bacagina YAPISMAMALI.
                     ;; * Bu yuzden referans olarak 'mainTmp' (Temiz Hat) kullanilmali.
                     (progn
                        (if (and remote isAnchor)
                            ;; Anchor ozel durumu (Pahli Baglanti)
                            (progn
                              (setq distEnds (distance cpCur cpEshort))
                              (setq uTan (list (/ (- (car cpEshort) (car cpCur)) distEnds)
                                               (/ (- (cadr cpEshort) (cadr cpCur)) distEnds)))
                              (setq uPerp (list (- (cadr uTan)) (car uTan)))
                              (setq corner1 (DEGZ--calc-L-corner cpCur ip uPerp))
                              (setq corner2 (DEGZ--calc-L-corner cpEshort ipRin uPerp))
                              (setq crv (DEGZ--insert-detour crv cpCur cpEshort (list corner1 ip ipRin corner2)))
                            )
                            
                            ;; STANDART DIREKT BAGLANTI (VEKTOREL HIZALAMA)
                            (progn
                                ;; *** ONEMLI: Hesaplamalarda 'mainTmp' (Temiz Hat) kullan! ***
                                (setq calcCrv mainTmp) 
                                
                                ;; A. Orta noktayi bul
                                (setq ipAvg (list (/ (+ (car ip) (car ipRin)) 2.0) (/ (+ (cadr ip) (cadr ipRin)) 2.0)))
                                (setq pMid (deg-safe-closest-point calcCrv ipAvg))
                                
                                ;; B. Hattin yonunu bul (Temiz hat uzerinden)
                                (setq paramMid (vlax-curve-getParamAtPoint (DEGZ--ename calcCrv) (DEGZ--pt3d pMid)))
                                (setq deriv (vlax-curve-getFirstDeriv (DEGZ--ename calcCrv) paramMid))
                                (setq Tlen (distance '(0 0 0) deriv))
                                (if (< Tlen 1e-9)
                                   (progn (setq Tx rx) (setq Ty ry))
                                   (progn (setq Tx (/ (car deriv) Tlen)) (setq Ty (/ (cadr deriv) Tlen)))
                                )

                                ;; C. Hizalama Yonu
                                (setq Lx (- (car ipRin) (car ip)))
                                (setq Ly (- (cadr ipRin) (cadr ip)))
                                (setq dotProd (+ (* Tx Lx) (* Ty Ly)))
                                (setq dirSign (if (>= dotProd 0) 1.0 -1.0))

                                ;; Remote + anchor + target side: reverse direction so the short piece is taken from the other side
                                (if (and remote isAnchor isTargetSide)
                                  (setq dirSign (- dirSign))
                                )
                                
                                ;; D. Sabit 10 birim aralik (Merkezden +/- 5.0)
                                (setq distMid (vlax-curve-getDistAtParam (DEGZ--ename calcCrv) paramMid))
                                (setq maxDist (DEGZ--curve-total calcCrv))
                                
                                (setq distPair (DEGZ--distpair10 distMid dirSign maxDist (/ shift 4.0)))
                                (setq distDown (car distPair))
                                (setq distDownRin (cadr distPair))
                                
                                ;; Noktalari Temiz Hat uzerinden al (Komsunun bacagina carpmaz)
                                (setq pDown    (DEGZ--pt2d (vlax-curve-getPointAtDist (DEGZ--ename calcCrv) distDown)))
                                (setq pDownRin (DEGZ--pt2d (vlax-curve-getPointAtDist (DEGZ--ename calcCrv) distDownRin)))

                                ;; Detour ekleme noktalarini guncel 'crv' uzerinde bul
                                ;; pDown temiz hat uzerinde oldugu icin, 'crv' uzerinde de govdeye denk gelir.
                                (setq cpCur    (deg-safe-closest-point crv pDown))
                                (setq cpEshort (deg-safe-closest-point crv pDownRin))
                                
                                ;; DIREKT BAGLANTI LISTESI
                                ;; ORTHO modunu ana hattin yonune gore sabitle (iki uc ayni mod kullanir)
                                (if orthoForced
                                (setq lmode (DEGZ--lmode-along-main-at crv cpCur ip))
                                (progn
                                  (setq firstX (DEGZ--ortho-first-axis ip cpCur))
                                  (setq lmode (if firstX 'hfirst 'vfirst))
                                )
                              )
                       ;; ORTHO zorlanan ve blok ana hattin ustunde/solunda ise
                       ;; kisa kolun blok tarafinda kalmasi icin mode'u corner->ip mesafesine gore sec
                       (if (and orthoForced isTargetSide)
                         (progn
                           (setq dxA (abs (- (car ip) (car cpCur))))
                           (setq dyA (abs (- (cadr ip) (cadr cpCur))))
                           ;; vfirst => corner->ip yatay (dx), hfirst => corner->ip dikey (dy)
                           (setq lmode (if (< dxA dyA) 'vfirst 'hfirst))
                         )
                       )
(setq corner1 (DEGZ--calc-L-corner-mode cpCur    ip   lmode))
                                (setq corner2 (DEGZ--calc-L-corner-mode cpEshort ipRin lmode))
                                (setq crv (DEGZ--insert-detour crv cpCur cpEshort (list corner1 ip ipRin corner2)))
                            )
                        )
                     )
                  )
                )
              )
            )
          )
        )

        (if mainTmp (entdel mainTmp))
      )
    )
  )
  (princ)
)

(defun DEGDR--RUN (mainEnt pick dist / mainPts tol ss allEnts rootId assignedEnts lay mainCol tubePls scan e pl outline)
  (setq mainPts (g365_get_pts mainEnt))
  (if (or (null mainPts) (< (length mainPts) 2))
    (progn (princ "\nAna hat okunamadi / cok kisa.") nil)
    (progn
      (setq tol (DEG:CFG-TOL-NUM-OR 'DR_TREE_TOL 0.1))
      (if (<= dist 0.0)
        (progn (princ "\nGecersiz mesafe.") nil)
        (progn
          (setq lay (cdr (assoc 8 (entget mainEnt))))
          (setq mainCol (g365_effective_color mainEnt))
          ;; Iskelete dahil olacak nesneler, secilen ana hat ile AYNI layer'da olmalidir.
          (if (and lay (/= lay ""))
            (setq ss (ssget "X" (list (cons 0 "LWPOLYLINE,POLYLINE,LINE") (cons 8 lay))))
            (setq ss (ssget "X" '((0 . "LWPOLYLINE,POLYLINE,LINE"))))
          )
          (if (null ss)
            (progn (princ "\nHic nesne bulunamadi.") nil)
            (progn
              (setq allEnts (g372_ss_to_list ss))
              ;; Iskelete dahil olacak nesneler, secilen ana hat ile AYNI renkte olmalidir.
              (setq allEnts
                (vl-remove nil
                  (mapcar
                    '(lambda (en)
                       (if (= (g365_effective_color en) mainCol) en nil)
                     )
                    allEnts
                  )
                )
              )
              (setq rootId (g372_build_tree mainEnt mainPts allEnts tol))
              (setq assignedEnts (g415_get_assigned_original_ents allEnts))
              
              (setq tubePls nil)
              (setq scan assignedEnts)
              (while scan
                (setq e (car scan))
                (setq pl (g415_make_tube_poly_from_ent e dist lay))
                (if pl (setq tubePls (cons pl tubePls)))
                (setq scan (cdr scan))
              )
              (setq tubePls (reverse tubePls))
              (setq outline (g415_union_tubes_to_outline tubePls lay))

              (if outline
                (progn
                  (setq outline (g418_rebuild_outline_seam outline lay pick mainPts dist))
                  (if outline (g365_copy_color mainEnt outline))
                  (g415_delete_ents assignedEnts)
                  (g418_flush_cmd)
                  outline
                )
                nil
              )
            )
          )
        )
      )
    )
  )
)

(defun DZ_ORIG ()
  (prompt "\nDZ bu sürümden kaldýrýldý.")
  (princ)
)




(defun deg-fire-flasher-filter (plLayer blkName blkLayer / L B BL)
  (setq L  (strcase plLayer)
        B  (strcase blkName)
        BL (strcase blkLayer))
  (cond
    ((DEGN-DN--match-list-p B (DEGN-DN--cfg-list-or-codes 'DN_FILTER_IGNORE_BLOCKS '(N1 K2 N2))) nil)

    ((DEGN-DN--match-list-p L (DEGN-DN--cfg-list-or-codes 'DN_FILTER_FIRE_LAYER_PATTERNS '(K11 K10 K9)))
     (not (DEGN-DN--match-list-p B (DEGN-DN--cfg-list-or-codes 'DN_FILTER_FIRE_BLOCK_EXCLUDES '(K13 K14 K15))))
    )

    ((DEGN-DN--match-list-p L (DEGN-DN--cfg-list-or-codes 'DN_FILTER_CO_LAYER_PATTERNS '(K8)))
     (DEGN-DN--match-list-p B (DEGN-DN--cfg-list-or-codes 'DN_FILTER_CO_BLOCKS '(K7)))
    )

    ((DEGN-DN--match-list-p L (DEGN-DN--cfg-list-or-codes 'DN_FILTER_FLASOR_LAYERS '(K1)))
     (DEGN-DN--match-list-p B (DEGN-DN--cfg-list-or-codes 'DN_FILTER_FLASOR_BLOCKS '(K12)))
    )

    ((DEGN-DN--match-list-p L (DEGN-DN--cfg-list-or-codes 'DN_FILTER_SOUND_LAYER_PATTERNS '(K13 K14 K15)))
     (DEGN-DN--match-list-p B (DEGN-DN--cfg-list-or-codes 'DN_FILTER_SOUND_BLOCK_PATTERNS '(K13 K14 K15)))
    )

    (T T)
  )
)


(defun degp--alist-add (al k v / a)
  (setq a (assoc k al))
  (if a
    (subst (cons k (+ (cdr a) v)) a al)
    (cons (cons k v) al)
  )
)

(defun degp--sortlayers (al)
  (vl-sort al
    (function (lambda (a b) (< (strcase (car a)) (strcase (car b))))))
)

(defun degp--ename (x)
  (cond
    ((= (type x) 'ENAME) x)
    ((= (type x) 'VLA-OBJECT) (vlax-vla-object->ename x))
    (T nil)
  )
)

(defun degp--mline-length (e / ed flags item points previous total)
  (setq ed    (entget e)
        flags (if (assoc 71 ed) (cdr (assoc 71 ed)) 0)
        total 0.0)
  (foreach item ed
    (if (= (car item) 11)
      (setq points (append points (list (cdr item))))))
  (foreach item points
    (if previous (setq total (+ total (distance previous item))))
    (setq previous item))
  (if (and (> (length points) 2) (= (logand flags 2) 2))
    (setq total (+ total (distance (car (last points)) (car points)))))
  total
)

(defun degp--length (x / e ed typ obj len endParam)
  (setq e (degp--ename x))
  (if (null e)
    0.0
    (progn
      (setq ed  (entget e)
            typ (if ed (cdr (assoc 0 ed)) ""))
      (if (= typ "MLINE")
        (setq len (degp--mline-length e))
        (progn
          ;; Tum sonlu curve tiplerinde once ortak curve API'sini kullan.
          (setq endParam
            (vl-catch-all-apply 'vlax-curve-getEndParam (list e)))
          (if (not (vl-catch-all-error-p endParam))
            (setq len
              (vl-catch-all-apply
                'vlax-curve-getDistAtParam
                (list e endParam))))
          ;; CAD'e ozel bir curve tipi yalniz Length sunuyorsa onu da dene.
          (if (or (vl-catch-all-error-p len) (not (numberp len)))
            (progn
              (setq obj
                (vl-catch-all-apply 'vlax-ename->vla-object (list e)))
              (if (and obj (not (vl-catch-all-error-p obj)))
                (setq len
                  (vl-catch-all-apply 'vla-get-Length (list obj))))))))
      (if (and (numberp len) (> len 0.0)) len 0.0)
    )
  )
)

(defun degp--numstr (s / txt)
  (cond
    ((numberp s)
      (float s)
    )
    ((and (= (type s) 'STR)
          (/= (setq txt (vl-string-trim " \t\r\n" s)) ""))
      (atof (vl-string-subst "." "," txt))
    )
    (T nil)
  )
)

(defun DEGP--length-report (ss / i e ed lay len sums msg vals it qty qtyNum)
  (if (null ss)
    (progn (DEG:WIN-MESSAGE "Secim yok veya uygun obje yok.") (princ))
    (progn
      (setq sums '() i 0)
      (while (< i (sslength ss))
        (setq e   (ssname ss i)
              ed  (entget e)
              lay (cdr (assoc 8 ed))
              len (degp--length e))
        (if (> len 0.0)
          (setq sums (degp--alist-add sums lay len))
        )
        (setq i (1+ i))
      )

      (if (null sums)
        (DEG:WIN-MESSAGE "Secimde uzunlugu > 0 olan desteklenen bir cizgi/egri bulunamadi.")
        (progn
          (setq sums (degp--sortlayers sums))
          (setq vals (DEGDO--dp-e-values-alist))
          (setq msg "")
          (foreach it sums
            (setq lay    (car it)
                  len    (cdr it)
                  qty    (DEGDO--dp-e-value-get vals lay)
                  qtyNum (degp--numstr qty))
            (if qtyNum
              (setq msg
                (strcat msg
                        lay " : " (DEG:DP-LEN-STR len) " metre x " qty
                        " = " (DEG:DP-LEN-STR (* len qtyNum)) " metre\n"))
              (setq msg
                (strcat msg
                        lay " : " (DEG:DP-LEN-STR len) " metre\n"))
            )
          )
          (DEG:WIN-MESSAGE msg)
        )
      )
      (princ)
    )
  )
)

(defun DEGP--layer-total-pairs (rows / order sums row lay v rec out)
  (setq order '()
        sums  '())
  (foreach row rows
    (setq lay (nth 1 row)
          v   (nth 5 row))
    (if (and lay (/= lay "") (numberp v))
      (progn
        (if (not (assoc lay sums))
          (setq order (append order (list lay))))
        (setq rec (assoc lay sums))
        (if rec
          (setq sums (subst (cons lay (+ (cdr rec) v)) rec sums))
          (setq sums (append sums (list (cons lay v)))))
      )
    )
  )
  (setq out '())
  (foreach lay order
    (setq rec (assoc lay sums))
    (if rec
      (setq out (append out (list rec))))
  )
  out
)

(defun DEGP--popup-results-by-layer (sortedList title / msg cnt i row total v unitLab pair)
  (setq cnt (length sortedList))
  (setq total 0.0)
  (foreach row sortedList
    (setq v (nth 5 row))
    (if (numberp v) (setq total (+ total v)))
  )
  (setq unitLab (if *degLastIsCCTV* " (m)" (strcat " " (DEG:LEN-UNIT-LABEL))))
  (setq msg (strcat title "\nSatir: " (itoa cnt) "\n\n"))
  (setq i 0)
  (foreach row sortedList
    (if (< i 25)
      (progn
        (setq msg
          (strcat msg
                  (if (nth 0 row) (nth 0 row) "") " | "
                  (if (nth 1 row) (nth 1 row) "") " | "
                  (if (nth 5 row) (strcat (DEG:DP-LEN-STR (nth 5 row)) unitLab) (strcat "0" unitLab))
                  "\n"
          )
        )
        (setq i (1+ i))
      )
    )
  )
  (if (> cnt 25)
    (setq msg (strcat msg "\n... (" (itoa (- cnt 25)) " satir daha)\n"))
    (setq msg (strcat msg "\n"))
  )
  (setq msg (strcat msg "==============================\n"))
  (foreach pair (DEGP--layer-total-pairs sortedList)
    (setq msg
      (strcat msg
              (car pair) " TOPLAM: " (DEG:DP-LEN-STR (cdr pair)) unitLab "\n"))
  )
  (setq msg
    (strcat msg
            "------------------------------\n"
            "GENEL TOPLAM: " (DEG:DP-LEN-STR total) unitLab "\n"
            "==============================\n"
    )
  )
  (DEG:WIN-MESSAGE msg)
)

(defun DEGP--data-layer-name-p (lay / u)
  (setq u (norm-layer lay))
  (and (/= u "")
       (or (member u (DEGP--data-line-layers))
           (member u (DEGP--data-comb-layers))
           (DEG:LAYER-IN-CODES? u '(C1 C2 C3 C4))
           (wcmatch u (DEG:VAL 'C9))))
)

(defun DEGP--kombine-line-layers ()
  (DEG:VALS '(D1 D2))
)

(defun DEGP--kombine-comb-layers ()
  (DEG:VALS '(D3 D4))
)

(defun DEGP--kombine-layer-name-p (lay / u)
  (setq u (norm-layer lay))
  (and (/= u "")
       (or (member u (DEGP--kombine-line-layers))
           (member u (DEGP--kombine-comb-layers))))
)

(defun DEGP--lighting-name-pattern-p (lay / u)
  (setq u (norm-layer lay))
  (and (/= u "")
       (wcmatch u "*AYDINLATMA*,*LIGHTING*"))
)

(defun DEGP--dp-lighting-line-layers ()
  (DEGP--merge-layer-lists
    (DEG:VALS '(A1 A2 A4 A7))
    (append
      (DEG:CFG-LIST 'DP_LIGHTING_LINE_LAYERS)
      (DEG:CFG-LIST 'DG_KIT_LAYER)
      (DEG:CFG-LIST 'DG_ANAHTAR_LAYER)
      (DEG:DG-EXTRA-LAYERS)))
)

(defun DEGP--dp-lighting-comb-layers ()
  (DEGP--merge-layer-lists
    (DEG:VALS '(A3 A5))
    (DEG:CFG-LIST 'DP_LIGHTING_COMB_LAYERS))
)

(defun DEGP--lighting-base-layers ()
  (DEGP--merge-layer-lists
    (DEGP--dp-lighting-line-layers)
    (DEGP--dp-lighting-comb-layers))
)

(defun DEGP--lighting-comb-like-layer-p (lay / u)
  (setq u (norm-layer lay))
  (or (member u (DEG:VALS '(A3 A5)))
      (wcmatch u "*KOMBINE*,*COMBINE*,*MULTI*"))
)

(defun DEGP--scope-lighting-layers (/ out ss i ent ed lay baseLayers)
  (setq out nil
        baseLayers (DEGP--lighting-base-layers)
        ss (if (and (boundp '*degDGScopePolySS*) *degDGScopePolySS*)
             *degDGScopePolySS*
             nil))
  (if ss
    (progn
      (setq i 0)
      (while (< i (sslength ss))
        (setq ent (ssname ss i)
              ed  (if ent (entget ent))
              lay (if ed (norm-layer (cdr (assoc 8 ed))) ""))
        (if (and (/= lay "")
                 (or (member lay baseLayers)
                     (DEGP--lighting-name-pattern-p lay)))
          (setq out (DEGP--layer-list-add-unique out lay)))
        (setq i (1+ i)))))
  out
)

(defun DEGP--lighting-line-layers (/ out lay selected)
  (setq out nil)
  (foreach lay (append (DEGP--lighting-base-layers)
                       (DEGP--scope-lighting-layers))
    (if (not (DEGP--lighting-comb-like-layer-p lay))
      (setq out (DEGP--layer-list-add-unique out lay))))
  (setq selected
    (if (and (boundp '*DEGP_DP_LIGHTING_SELECTED_LAYER*)
             *DEGP_DP_LIGHTING_SELECTED_LAYER*)
      (norm-layer *DEGP_DP_LIGHTING_SELECTED_LAYER*)
      ""))
  (if (and (/= selected "")
           (not (DEGP--lighting-comb-like-layer-p selected)))
    (setq out (DEGP--layer-list-add-unique out selected)))
  out
)

(defun DEGP--lighting-comb-layers (/ out lay selected)
  (setq out nil)
  (foreach lay (append (DEGP--lighting-base-layers)
                       (DEGP--scope-lighting-layers))
    (if (DEGP--lighting-comb-like-layer-p lay)
      (setq out (DEGP--layer-list-add-unique out lay))))
  (setq selected
    (if (and (boundp '*DEGP_DP_LIGHTING_SELECTED_LAYER*)
             *DEGP_DP_LIGHTING_SELECTED_LAYER*)
      (norm-layer *DEGP_DP_LIGHTING_SELECTED_LAYER*)
      ""))
  (if (and (/= selected "")
           (DEGP--lighting-comb-like-layer-p selected))
    (setq out (DEGP--layer-list-add-unique out selected)))
  out
)

(defun DEGP--lighting-layer-name-p (lay / u)
  (setq u (norm-layer lay))
  (and (/= u "")
       (or (member u (DEGP--lighting-base-layers))
           (DEGP--lighting-name-pattern-p u)))
)

(defun DEGP--dp-lighting-mode-p ()
  (and (boundp '*DEGP_DP_LIGHTING_MODE*)
       *DEGP_DP_LIGHTING_MODE*)
)

(defun DEGP--reset-data-run-state (/)
  (setq *degk-dispatch-sel* nil)
  (deg-reset-session)
  (deg-clear-deg-done-xdata)
  (setq DEGN-DEGA--CONNS nil)
  (setq DEGN-DEGA--BLCONNS nil)
  (setq DEGN-DEGA--POLYNODESMAP nil)
  (setq DEGN-DEGA--DATA-ONLY nil)
  (setq *DEGP_DP_DATA_MODE* nil)
  (setq *DEGP_DP_DATA_SELECTED_LAYER* nil)
  (setq *DEGP_DP_LIGHTING_MODE* nil)
  (setq *DEGP_DP_LIGHTING_SELECTED_LAYER* nil)
  (princ)
)

(defun DEGP--data-report-single (sel / ent pickPt ed typ obj refPt selectedLayer scopeSel scopePolySS scopeBlkSS sortedList codeSnap oldDpDataMode)
  (setq ent    (car sel)
        pickPt (cadr sel)
        ed     (if ent (entget ent))
        typ    (cdr (assoc 0 ed)))
  (if (and ent typ
           (wcmatch typ "LWPOLYLINE,POLYLINE")
           (DEGP--data-layer-name-p (cdr (assoc 8 ed))))
    (progn
      (DEGP--reset-data-run-state)
      (setq selectedLayer (norm-layer (cdr (assoc 8 ed))))
      (setq *DEGP_DP_DATA_SELECTED_LAYER* selectedLayer)
      (princ "\nDP DATA: Alan secin (polyline ve blocklar): ")
      (setq scopeSel (ssget '((0 . "LWPOLYLINE,POLYLINE,INSERT"))))
      (if (not scopeSel)
        (progn
          (DEGP--reset-data-run-state)
          (princ "\n\nDP DATA iptal: alan secilmedi.")
          T
        )
        (progn
          (setq scopePolySS (DEG:SS-FILTER-BY-TYPE scopeSel "LWPOLYLINE,POLYLINE"))
          (setq scopeBlkSS  (DEG:SS-FILTER-BY-TYPE scopeSel "INSERT"))
          (if (<= (DEG:SS-LEN scopePolySS) 0) (setq scopePolySS nil))
          (if (<= (DEG:SS-LEN scopeBlkSS) 0)  (setq scopeBlkSS  nil))
          (if (not scopePolySS) (setq scopePolySS (ssadd)))
          (if (and ent (not (DEG:SS-CONTAINS-ENAME? scopePolySS ent)))
            (ssadd ent scopePolySS)
          )
          (setq obj   (vlax-ename->vla-object ent))
          (setq refPt (deg-safe-closest-point obj pickPt))
          (if (not refPt)
            (setq refPt (deg-nearest-vertex obj pickPt))
          )
          (setq *degDGScopePolySS* scopePolySS)
          (setq *degDGScopeBlkSS*  scopeBlkSS)
          (setq *degForceRefObj* obj)
          (setq *degForceRefPt*  refPt)
          (setq oldDpDataMode (if (boundp '*DEGP_DP_DATA_MODE*) *DEGP_DP_DATA_MODE* nil))
          (setq *DEGP_DP_DATA_MODE* T)
          (setq codeSnap (DEGP--data-code-snapshot))
          (DEGP--apply-data-code-overrides)
          (setq sortedList (vl-catch-all-apply 'deg-build-data (list nil refPt)))
          (DEGP--restore-data-code-snapshot codeSnap)
          (setq *DEGP_DP_DATA_MODE* oldDpDataMode)
          (setq *degForceRefObj* nil)
          (setq *degForceRefPt*  nil)
          (setq *degDGScopePolySS* nil)
          (setq *degDGScopeBlkSS*  nil)
          (if (vl-catch-all-error-p sortedList)
            (progn
              (princ (strcat "\nDP DATA hata: " (vl-catch-all-error-message sortedList)))
              (setq sortedList nil)
            )
          )
          (if sortedList
            (DEGP--popup-results-by-layer (deg-filter-out-kombine-rows sortedList) "DP - DATA Sonuclari")
            (DEG:WIN-MESSAGE "DP - DATA\nBu referans icin veri bulunamadi."))
          (DEGP--reset-data-run-state)
          T
        )
      )
    )
  )
)

(defun DEGP--lighting-report-single (sel / ent pickPt ed typ obj refPt selectedLayer scopeSel scopePolySS scopeBlkSS sortedList)
  (setq ent    (car sel)
        pickPt (cadr sel)
        ed     (if ent (entget ent))
        typ    (cdr (assoc 0 ed)))
  (if (and ent typ
           (wcmatch typ "LWPOLYLINE,POLYLINE")
           (DEGP--lighting-layer-name-p (cdr (assoc 8 ed))))
    (progn
      (DEGP--reset-data-run-state)
      (setq selectedLayer (norm-layer (cdr (assoc 8 ed))))
      (setq *DEGP_DP_LIGHTING_MODE* T)
      (setq *DEGP_DP_LIGHTING_SELECTED_LAYER* selectedLayer)
      (princ "\nDP AYDINLATMA: Alan secin (polyline ve blocklar): ")
      (setq scopeSel (ssget '((0 . "LWPOLYLINE,POLYLINE,INSERT"))))
      (if (not scopeSel)
        (progn
          (DEGP--reset-data-run-state)
          (princ "\n\nDP AYDINLATMA iptal: alan secilmedi.")
          T
        )
        (progn
          (setq scopePolySS (DEG:SS-FILTER-BY-TYPE scopeSel "LWPOLYLINE,POLYLINE"))
          (setq scopeBlkSS  (DEG:SS-FILTER-BY-TYPE scopeSel "INSERT"))
          (if (<= (DEG:SS-LEN scopePolySS) 0) (setq scopePolySS nil))
          (if (<= (DEG:SS-LEN scopeBlkSS) 0)  (setq scopeBlkSS  nil))
          (if (not scopePolySS) (setq scopePolySS (ssadd)))
          (if (and ent (not (DEG:SS-CONTAINS-ENAME? scopePolySS ent)))
            (ssadd ent scopePolySS)
          )
          (setq obj   (vlax-ename->vla-object ent)
                refPt (deg-safe-closest-point obj pickPt))
          (if (not refPt)
            (setq refPt (deg-nearest-vertex obj pickPt)))
          (setq *degDGScopePolySS* scopePolySS)
          (setq *degDGScopeBlkSS*  scopeBlkSS)
          (setq *degForceRefObj* obj)
          (setq *degForceRefPt*  refPt)
          ;; Veri motoru bazý aydýnlatma/KNX yollarýnda gerçek bir VLA nesnesi
          ;; bekler; týklama koordinatý *degForceRefPt* üzerinden korunur.
          (setq sortedList (vl-catch-all-apply 'deg-build-data (list nil obj)))
          (setq *degForceRefObj* nil)
          (setq *degForceRefPt*  nil)
          (setq *degDGScopePolySS* nil)
          (setq *degDGScopeBlkSS*  nil)
          (if (vl-catch-all-error-p sortedList)
            (progn
              (princ (strcat "\nDP AYDINLATMA hata: " (vl-catch-all-error-message sortedList)))
              (setq sortedList nil)
            )
          )
          (if sortedList
            (DEGP--popup-results-by-layer sortedList "DP - AYDINLATMA Sonuclari")
            (DEG:WIN-MESSAGE "DP - AYDINLATMA\nBu referans icin veri bulunamadi."))
          (DEGP--reset-data-run-state)
          T
        )
      )
    )
  )
)

(defun DEGP--kombine-report-single (sel / ent pickPt ed typ obj refPt scopeSel scopePolySS scopeBlkSS sortedList)
  (setq ent    (car sel)
        pickPt (cadr sel)
        ed     (if ent (entget ent))
        typ    (cdr (assoc 0 ed)))
  (if (and ent typ
           (wcmatch typ "LWPOLYLINE,POLYLINE")
           (DEGP--kombine-layer-name-p (cdr (assoc 8 ed))))
    (progn
      (DEGP--reset-data-run-state)
      (princ "\nDP KOMBINE: Alan secin (polyline ve blocklar): ")
      (setq scopeSel (ssget '((0 . "LWPOLYLINE,POLYLINE,INSERT"))))
      (if (not scopeSel)
        (progn
          (DEGP--reset-data-run-state)
          (princ "\n\nDP KOMBINE iptal: alan secilmedi.")
          T
        )
        (progn
          (setq scopePolySS (DEG:SS-FILTER-BY-TYPE scopeSel "LWPOLYLINE,POLYLINE"))
          (setq scopeBlkSS  (DEG:SS-FILTER-BY-TYPE scopeSel "INSERT"))
          (if (<= (DEG:SS-LEN scopePolySS) 0) (setq scopePolySS nil))
          (if (<= (DEG:SS-LEN scopeBlkSS) 0)  (setq scopeBlkSS  nil))
          (if (not scopePolySS) (setq scopePolySS (ssadd)))
          (if (and ent (not (DEG:SS-CONTAINS-ENAME? scopePolySS ent)))
            (ssadd ent scopePolySS)
          )
          (setq obj   (vlax-ename->vla-object ent)
                refPt (deg-nearest-vertex obj pickPt))
          (setq *degDGScopePolySS* scopePolySS)
          (setq *degDGScopeBlkSS*  scopeBlkSS)
          (setq *degForceRefObj* obj)
          (setq *degForceRefPt*  refPt)
          (setq sortedList (vl-catch-all-apply 'deg-build-data (list nil refPt)))
          (setq *degForceRefObj* nil)
          (setq *degForceRefPt*  nil)
          (setq *degDGScopePolySS* nil)
          (setq *degDGScopeBlkSS*  nil)
          (if (vl-catch-all-error-p sortedList)
            (progn
              (princ (strcat "\nDP KOMBINE hata: " (vl-catch-all-error-message sortedList)))
              (setq sortedList nil)
            )
          )
          (if sortedList
            (DEGP--popup-results-by-layer (deg-filter-out-kombine-rows sortedList) "DP - KOMBINE Sonuclari")
            (DEG:WIN-MESSAGE "DP - KOMBINE\nBu referans icin veri bulunamadi."))
          (DEGP--reset-data-run-state)
          T
        )
      )
    )
  )
)

(defun DEGP--run-data-single (sel)
  (DEGP--data-report-single sel)
)

(defun DEGP--dispatch-single (sel / ent pickPt ed typ)
  (setq ent    (car sel)
        pickPt (cadr sel)
        ed     (if ent (entget ent))
        typ    (cdr (assoc 0 ed)))
  (if (and ent typ (wcmatch typ "LWPOLYLINE,POLYLINE"))
    (cond
      ((DEGP--data-report-single sel) T)
      ((DEGP--lighting-report-single sel) T)
      ((DEGP--kombine-report-single sel) T)
      (T nil)
    )
  )
)

(defun DP_ORIG (/ sel ss e pt)
  (vl-load-com)

  (setq sel (entsel "\nDP: Cizgi/egri sec (Polyline=AYDINLATMA/DATA/KOMBINE), Enter = uzunluk secimi: "))
  (cond
    ((and sel (DEGP--dispatch-single sel))
      (princ)
    )
    (sel
      (setq ss (ssadd (car sel)))
      (DEGP--length-report ss)
    )
    (T
      (prompt "\nDP: Uzunluk icin LINE/POLYLINE/SPLINE/ARC/CIRCLE/ELLIPSE/HELIX/MLINE sec: ")
      (setq ss
        (ssget
          '((0 . "LINE,LWPOLYLINE,POLYLINE,SPLINE,ARC,CIRCLE,ELLIPSE,HELIX,MLINE"))))
      (if (and ss
               (= (sslength ss) 1)
               (setq e (ssname ss 0))
               (wcmatch (cdr (assoc 0 (entget e))) "LWPOLYLINE,POLYLINE"))
        (progn
          (setq pt (vlax-curve-getStartPoint e))
          (cond
            ((DEGP--data-report-single (list e pt))
              (princ)
            )
            ((DEGP--lighting-report-single (list e pt))
              (princ)
            )
            ((DEGP--kombine-report-single (list e pt))
              (princ)
            )
            (T
              (DEGP--length-report ss)
            )
          )
        )
        (DEGP--length-report ss)
      )
    )
  )
)

(princ)



(vl-load-com)

(defun deg-reset-session ( / )
  (setq
    *deg-dallar*            nil
    *deg-visited*           nil
    *deg-done*              nil
    *deg-blk-visited*       nil
    *deg-block-cache*       nil
    *DEG-BLOCK-WRITTEN*     nil
    *degRefChainEnts*       nil
    *degn-last-poly*        nil
    *degn-last-idx*         nil
  )
  (princ)
)

(defun deg-clear-deg-done-xdata ( / ss i e ed newed x3)
  (if (setq ss (ssget "X" '((0 . "LWPOLYLINE,POLYLINE"))))
    (progn
      (setq i 0)
      (while (< i (sslength ss))
        (setq e  (ssname ss i))
        (setq ed (entget e '("*")))
        (setq newed nil)
        (foreach x3 ed
          (if (and (= (car x3) -3)
                   (listp (cadr x3))
                   (= (car (cadr x3)) (DEG:VAL 'R1)))
            (setq newed newed) ; skip this xdata chunk
            (setq newed (append newed (list x3)))
          )
        )
        (if (and newed (/= (length newed) (length ed)))
          (progn (entmod newed) (entupd e))
        )
        (setq i (1+ i))
      )
    )
  )
  (princ)
)


(defun degk--as-ename (e)
  (cond
    ((= (type e) 'ENAME) e)
    ((= (type e) 'VLA-OBJECT) (vlax-vla-object->ename e))
    (T nil)
  )
)

(defun degk--nearest-vertex (plEnt pickPt / ed v best bestd p d)
  (setq plEnt (degk--as-ename plEnt))
  (if (null plEnt)
    pickPt
    (progn
      (setq best nil bestd 1e99)
      (setq ed (entget plEnt))
      (foreach v ed
        (if (= (car v) 10)
          (progn
            (setq p (list (car (cdr v)) (cadr (cdr v)) 0.0))
            (setq d (distance p pickPt))
            (if (< d bestd) (setq bestd d best p))
          )
        )
      )
      (if best best pickPt)
    )
  )
)

(defun degk--last-number-in-text (s / i len ch code cur lastNum)
  (setq s (if (= (type s) 'STR) s ""))
  (setq i 1 len (strlen s) cur nil lastNum nil)
  (while (<= i len)
    (setq ch (substr s i 1)
          code (ascii ch))
    (if (and (>= code 48) (<= code 57))
      (setq cur (+ (* (if cur cur 0) 10) (- code 48)))
      (if cur
        (setq lastNum cur cur nil)
      )
    )
    (setq i (1+ i))
  )
  (if cur cur lastNum)
)

(defun degk--sira-min-number (s / parts part n best)
  (setq parts (degk--split-commas (if (= (type s) 'STR) s "")))
  (foreach part parts
    (setq n (degk--last-number-in-text part))
    (if (and n (or (null best) (< n best)))
      (setq best n)
    )
  )
  best
)



(vl-load-com)


(defun DEGV:_regapp (app /)
  (if (not (tblsearch "APPID" app))
    (regapp app)
  )
  app
)

(defun DEGV:_mark-created (e /)
  e
)

(defun DEGV:_is-created (e /)
  nil
)


(defun DEGV:_set-chain-polylines-white (chain / polyE obj)
  (foreach polyE chain
    (if (and polyE (setq obj (vl-catch-all-apply 'vlax-ename->vla-object (list polyE))))
      (if (not (vl-catch-all-error-p obj))
        (if (vlax-property-available-p obj 'Color)
          nil
        )
      )
    )
  )
)
(defun DEGK--keyword-layer-p (lay code / u hit key)
  (setq u (strcase (if lay lay "")))
  (foreach key (DEG:VAL-LIST code)
    (if (and (/= key "") (vl-string-search (strcase key) u))
      (setq hit T)
    )
  )
  hit
)

(defun DEGK--data-layer-name-p (lay / u)
  (setq u (strcase (if lay lay "")))
  (or (DEG:LAYER-IN-CODES? u '(C1 C2 C3 C4))
      (wcmatch u (DEG:VAL 'C9))
      (DEGK--keyword-layer-p u 'C10))
)

(defun DEGV:_is-data-layer (e / o lyr)
  (if (and e (= (type e) 'ENAME))
    (progn
      (setq o (vl-catch-all-apply 'vlax-ename->vla-object (list e)))
      (if (vl-catch-all-error-p o)
        nil
        (progn
          (setq lyr (strcase (vla-get-Layer o)))
          (DEGK--data-layer-name-p lyr)
        )
      )
    )
    nil
  )
)

(defun DEGV:_filter-chain-data (lst / out e)
  (setq out nil)
  (foreach e lst
    (if (DEGV:_is-data-layer e)
      (setq out (cons e out))
    )
  )
  (reverse out)
)

(defun DEGV:_tel-tv-layer-name-p (lay / u)
  (setq u (strcase (if lay lay "")))
  (or (DEG:LAYER-IN-CODES? u '(E1 E2 E3 E5 F1 F2 F3 F4))
      (wcmatch u (DEG:VAL 'E4))
      (wcmatch u (DEG:VAL 'F5)))
)

(defun DEGV:_data-tel-tv-layer-name-p (lay / u)
  (setq u (strcase (if lay lay "")))
  (or (DEGK--data-layer-name-p u)
      (DEGV:_tel-tv-layer-name-p u))
)

(defun DEGV:_is-data-tel-tv-layer (e / o lyr)
  (if (and e (= (type e) 'ENAME))
    (progn
      (setq o (vl-catch-all-apply 'vlax-ename->vla-object (list e)))
      (if (vl-catch-all-error-p o)
        nil
        (progn
          (setq lyr (strcase (vla-get-Layer o)))
          (DEGV:_data-tel-tv-layer-name-p lyr)
        )
      )
    )
    nil
  )
)

(defun DEGV:_filter-chain-data-tel-tv (lst / out e)
  (setq out nil)
  (foreach e lst
    (if (DEGV:_is-data-tel-tv-layer e)
      (setq out (cons e out))
    )
  )
  (reverse out)
)

(defun DEGV:_chain-unique (lst / out hs e h)
  (setq out nil hs nil)
  (foreach e lst
    (if (and e (= (type e) 'ENAME))
      (progn
        (setq h (DEGV:_ename-handle e))
        (if (and h (not (member h hs)))
          (progn
            (setq hs (cons h hs))
            (setq out (cons e out))
          )
        )
      )
    )
  )
  (reverse out)
)

(defun DEGV:_chain-merge-unique (a b)
  (DEGV:_chain-unique (append a b))
)
(defun DEGV:_POLY-TOUCHES-ANY_SELECTED-BLOCK? (pl blkList)
  nil
)



(defun DEGV:_contains-ci (s sub)
  (if (and s sub)
    (not (null (vl-string-search (strcase sub) (strcase s))))
    nil
  )
)

(defun DEGV:_blk-effective-name-safe (b / nm)
  (setq nm nil)
  (if (and b (= (type b) 'VLA-OBJECT))
    (progn
      (setq nm (vl-catch-all-apply 'vla-get-EffectiveName (list b)))
      (if (vl-catch-all-error-p nm) (setq nm nil))
      (if (null nm)
        (progn
          (setq nm (vl-catch-all-apply 'vla-get-Name (list b)))
          (if (vl-catch-all-error-p nm) (setq nm nil))
        )
      )
    )
  )
  (if nm (strcase nm) "")
)


(defun DEGV:_data-shift-block-name-p (nm / pattern hit)
  (setq nm (strcase (if nm nm ""))
        hit nil)
  (foreach pattern (DEG:CFG-LIST-GET 'DKX_DATA_SHIFT_BLOCKS)
    (if (and (/= pattern "")
             (or (wcmatch nm pattern)
                 (vl-string-search pattern nm)))
      (setq hit T)
    )
  )
  hit
)

(defun DEGV:_data-shift-y ()
  (DEG:CFG-DK-NUM-OR 'DKX_DATA_SHIFT_Y 5.25)
)

(defun DEGV:_is-klemens-terminal (bo / nm)
  (setq nm (DEGV:_blk-effective-name-safe bo))
  (DEGV:_data-shift-block-name-p nm)
)

(defun DEGV:_move-klemens-terminal (blkList / acad doc lays b bo layName layObj wasLocked shiftY)
  (setq acad (vlax-get-acad-object)
        doc  (vla-get-ActiveDocument acad)
        lays (vla-get-Layers doc)
        shiftY (DEGV:_data-shift-y)
  )

  (foreach b blkList
    (setq bo b)
    (if (and bo (= (type bo) 'ENAME))
      (setq bo (vlax-ename->vla-object bo))
    )
    (if (and (vlax-objectp bo)
             (= (strcase (vla-get-ObjectName bo)) "ACDBBLOCKREFERENCE"))
      (progn
        (if (and (> (abs shiftY) 1e-9)
                 (DEGV:_is-klemens-terminal bo))
          (progn
            (setq layName (vla-get-Layer bo))
            (setq layObj nil
                  wasLocked nil
            )
            (if (and layName (/= layName ""))
              (progn
                (setq layObj (vl-catch-all-apply 'vla-item (list lays layName)))
                (if (not (vl-catch-all-error-p layObj))
                  (progn
                    (setq wasLocked (vla-get-Lock layObj))
                    (if (= wasLocked :vlax-true)
                      (vla-put-Lock layObj :vlax-false)
                    )
                  )
                  (setq layObj nil)
                )
              )
            )

            (vl-catch-all-apply 'vla-Move
              (list bo
                    (vlax-3d-point '(0 0 0))
                    (vlax-3d-point (list 0.0 shiftY 0.0)))
            )

            (if (and layObj wasLocked (= wasLocked :vlax-true))
              (vla-put-Lock layObj :vlax-true)
            )
          )
        )
      )
    )
  )
  (princ)
)

(defun DEGV:_move-klemens-terminal-global ( / ss i en o lst)
  (setq lst '())
  (setq ss (ssget "X" '((0 . "INSERT"))))
  (if ss
    (progn
      (setq i 0)
      (while (< i (sslength ss))
        (setq en (ssname ss i))
        (if en (setq lst (cons en lst)))
        (setq i (1+ i))
      )
    )
  )
  (DEGV:_move-klemens-terminal lst)
  (princ)
)




(defun DEGV:_collect-blockrefs-from-ss (ss / i e o lst)
  (setq lst nil)
  (if ss
    (progn
      (setq i 0)
      (while (< i (sslength ss))
        (setq e (ssname ss i))
        (if e
          (progn
            (setq o (vlax-ename->vla-object e))
            (if (and (= (type o) 'VLA-OBJECT)
                     (= (strcase (vla-get-ObjectName o)) "ACDBBLOCKREFERENCE"))
              (setq lst (cons o lst))
            )
          )
        )
        (setq i (1+ i))
      )
    )
  )
  lst
)

(defun DEGV:_make-scale-positive (blk / sx sy sz)
  (if (and blk
           (= (vla-get-ObjectName blk) "AcDbBlockReference")
           (vlax-property-available-p blk 'XScaleFactor))
    (progn
      (setq sx (vla-get-XScaleFactor blk))
      (setq sy (vla-get-YScaleFactor blk))
      (setq sz (vla-get-ZScaleFactor blk))
      (vla-put-XScaleFactor blk (abs sx))
      (vla-put-YScaleFactor blk (abs sy))
      (vla-put-ZScaleFactor blk (abs sz))
    )
  )
  blk
)



(defun DEGV:_add-under-polyline-filleted (ms x y lyr vlen leadSign / sc r bulge sa pl d lx ly fy fyEnd)
  (setq sc (DEG:PLAN-UNIT-SCALE))
  (if (null vlen) (setq vlen (* 100.0 sc)))
  (setq r     (* 10.0 sc)
        bulge -0.41421356
        d     (* (/ 14.1421 1.41421356) sc)
        fy    (+ (- y vlen) r)
        fyEnd (- fy r)
  )

  (if leadSign
    (progn
      (setq lx (+ x (* leadSign d)))
      (setq ly (+ y d))
      (setq sa (vlax-make-safearray vlax-vbDouble '(0 . 7)))
      (mapcar 'vlax-safearray-put-element
              (list sa sa sa sa sa sa sa sa)
              '(0 1 2 3 4 5 6 7)
              (list
                lx ly
                x  y
                x  fy
                (- x r) fyEnd))
      (setq pl (vla-AddLightWeightPolyline ms (vlax-make-variant sa)))
      (vla-put-Layer pl lyr)
      (DEGV:_mark-created (vlax-vla-object->ename pl))
      (vla-SetBulge pl 2 bulge)
    )
    (progn
      (setq sa (vlax-make-safearray vlax-vbDouble '(0 . 5)))
      (mapcar 'vlax-safearray-put-element
              (list sa sa sa sa sa sa)
              '(0 1 2 3 4 5)
              (list
                x y
                x fy
                (- x r) fyEnd))
      (setq pl (vla-AddLightWeightPolyline ms (vlax-make-variant sa)))
      (vla-put-Layer pl lyr)
      (DEGV:_mark-created (vlax-vla-object->ename pl))
      (vla-SetBulge pl 1 bulge)
    )
  )
  pl
)

(defun DEGV:_add-under-polyline-last (ms x y lyr vlen hlen leadSign / sc step r bulge sa pl d lx ly fy fyEnd xEnd)
  (setq sc (DEG:PLAN-UNIT-SCALE)
        step (* 10.0 sc))
  (if (null vlen) (setq vlen (* 100.0 sc)))
  (if (null hlen) (setq hlen (* 150.0 sc)))
  (setq r     0.0
        bulge 0.0
        d     (* (/ 14.1421 1.41421356) sc)
        fy    (+ (- y vlen) step)
        fyEnd (- fy step)
        xEnd  (- x (abs hlen))
  )

  (if leadSign
    (progn
      (setq lx (+ x (* leadSign d)))
      (setq ly (+ y d))
      (setq sa (vlax-make-safearray vlax-vbDouble '(0 . 7)))
      (mapcar 'vlax-safearray-put-element
              (list sa sa sa sa sa sa sa sa)
              '(0 1 2 3 4 5 6 7)
              (list
                lx ly
                x  y
                x  fyEnd
                xEnd fyEnd))
      (setq pl (vla-AddLightWeightPolyline ms (vlax-make-variant sa)))
      (vla-put-Layer pl lyr)
      (DEGV:_mark-created (vlax-vla-object->ename pl))
    )
    (progn
      (setq sa (vlax-make-safearray vlax-vbDouble '(0 . 5)))
      (mapcar 'vlax-safearray-put-element
              (list sa sa sa sa sa sa)
              '(0 1 2 3 4 5)
              (list
                x y
                x fyEnd
                xEnd fyEnd))
      (setq pl (vla-AddLightWeightPolyline ms (vlax-make-variant sa)))
      (vla-put-Layer pl lyr)
      (DEGV:_mark-created (vlax-vla-object->ename pl))
    )
  )
  pl
)
(defun DEGV:_layer-is-data-str (lyr refL / u r)
  (setq u (strcase (if lyr lyr "")))
  (setq r (strcase (if refL refL "")))
  (or (= u r)
      (wcmatch u (DEG:VAL 'C9)))
)

(defun DEGV:_add-under-polyline-last-filleted (ms x y lyr vlen hlen leadSign / sc r bulge sa pl d lx ly fy fyEnd xEnd)
  (setq sc (DEG:PLAN-UNIT-SCALE))
  (if (null vlen) (setq vlen (* 100.0 sc)))
  (if (null hlen) (setq hlen (* 150.0 sc)))
  (setq r     (* 10.0 sc)
        bulge -0.41421356
        d     (* (/ 14.41421 1.1421356) sc)
        fy    (+ (- y vlen) r)
        fyEnd (- fy r)
        xEnd  (- x (abs hlen))
  )

  (if leadSign
    (progn
      (setq lx (+ x (* leadSign d)))
      (setq ly (+ y d))
      (setq sa (vlax-make-safearray vlax-vbDouble '(0 . 9)))
      (mapcar 'vlax-safearray-put-element
              (list sa sa sa sa sa sa sa sa sa sa)
              '(0 1 2 3 4 5 6 7 8 9)
              (list
                lx ly
                x  y
                x  fy
                (- x r) fyEnd
                xEnd fyEnd))
      (setq pl (vla-AddLightWeightPolyline ms (vlax-make-variant sa)))
      (vla-put-Layer pl lyr)
      (DEGV:_mark-created (vlax-vla-object->ename pl))
      (vla-SetBulge pl 2 bulge)
    )
    (progn
      (setq sa (vlax-make-safearray vlax-vbDouble '(0 . 7)))
      (mapcar 'vlax-safearray-put-element
              (list sa sa sa sa sa sa sa sa)
              '(0 1 2 3 4 5 6 7)
              (list
                x y
                x fy
                (- x r) fyEnd
                xEnd fyEnd))
      (setq pl (vla-AddLightWeightPolyline ms (vlax-make-variant sa)))
      (vla-put-Layer pl lyr)
      (DEGV:_mark-created (vlax-vla-object->ename pl))
      (vla-SetBulge pl 1 bulge)
    )
  )
  pl
)

(defun DEGV:_add-2pt-lwpoly (ms p1 p2 lyr / e x1 y1 x2 y2)
  (if (and p1 p2)
    (progn
      (setq x1 (car p1) y1 (cadr p1)
            x2 (car p2) y2 (cadr p2))
      (setq e
        (entmakex
          (list
            (cons 0 "LWPOLYLINE")
            (cons 100 "AcDbEntity")
            (cons 8 (if lyr lyr "0"))
            (cons 100 "AcDbPolyline")
            (cons 90 2)
            (cons 70 0)
            (cons 10 (list x1 y1))
            (cons 10 (list x2 y2))
          )
        )
      )
      (DEGV:_mark-created e)
      e
    )
  )
)


(defun DEGV:_nearest-vertex (plE pickPt / ed v best bestd p d)
  (setq best nil bestd 1e99)
  (setq ed (entget plE))
  (foreach v ed
    (if (= (car v) 10)
      (progn
        (setq p (list (car (cdr v)) (cadr (cdr v)) 0.0))
        (setq d (distance p pickPt))
        (if (< d bestd) (setq bestd d best p))
      )
    )
  )
  (if best best pickPt)
)

(defun DEGV:_get-pl-startpt (plE pickPt / sp ep vPick totalLen pDist)
  (setq sp (vlax-curve-getStartPoint plE))
  (setq ep (vlax-curve-getEndPoint   plE))
  (setq vPick (DEGV:_nearest-vertex plE pickPt))
  (setq totalLen (vlax-curve-getDistAtParam plE (vlax-curve-getEndParam plE)))
  (setq pDist (deg-safe-dist-at-point plE (deg-safe-closest-point plE vPick)))
  (if (<= pDist (- totalLen pDist))
    sp
    ep
  )
)

(defun DEGV:_v2l (v / r)
  (cond
    ((null v) nil)
    (t
      (setq r (vl-catch-all-apply 'vlax-variant-value (list v)))
      (if (vl-catch-all-error-p r)
        (vlax-safearray->list v)
        (vlax-safearray->list r)
      )
    )
  )
)

(defun DEGV:_ensure-layer (doc layName / lays layObj)
  (if (null (tblsearch "LAYER" layName))
    (progn
      (setq lays (vla-get-Layers doc))
      (setq layObj (vla-Add lays layName))
    )
  )
  layName
)

(defun DEGV:_attval (blk key / atts lst a tval)
  (setq tval "")
  (if (and blk key)
    (progn
      (if (vlax-method-applicable-p blk 'GetAttributes)
        (progn
          (setq atts (vlax-invoke blk 'GetAttributes))
          (setq lst (cond
                      ((= (type atts) 'VARIANT)  (vlax-safearray->list (vlax-variant-value atts)))
                      ((= (type atts) 'SAFEARRAY) (vlax-safearray->list atts))
                      (T nil)
                    )
          )
          (foreach a lst
            (if (or
                  (= (strcase (vla-get-TagString a)) (strcase key))
                  (and (vlax-property-available-p a 'PromptString)
                       (= (strcase (vla-get-PromptString a)) (strcase key)))
                )
              (setq tval (vla-get-TextString a))
            )
          )
        )
      )
    )
  )
  tval
)




(defun DEGV:_attclear (blk tag / a)
  (if (and blk tag (vlax-method-applicable-p blk 'GetAttributes))
    (foreach a (vlax-safearray->list (vlax-variant-value (vla-GetAttributes blk)))
      (if (= (strcase (vla-get-TagString a)) (strcase tag))
        (vla-put-TextString a "")
      )
    )
  )
  (princ)
)


(defun DEGV:_sirano-int-from-ename (blkE / e d tag val n)
  (setq tag "SIRA_NO")
  (setq val "")
  (if blkE
    (progn
      (setq e (entnext blkE))
      (while (and e (setq d (entget e)) (not (= (cdr (assoc 0 d)) "SEQEND")))
        (if (= (cdr (assoc 0 d)) "ATTRIB")
          (if (= (strcase (cdr (assoc 2 d))) tag)
            (setq val (cdr (assoc 1 d)))
          )
        )
        (setq e (entnext e))
      )
    )
  )
  (setq n (degk--sira-min-number val))
  (if n n 2147483647)
)

(defun DEGV:_sort-blocks-by-sirano-int (ss / lst i e)
  (setq lst nil)
  (if ss
    (progn
      (setq i 0)
      (while (< i (sslength ss))
        (setq e (ssname ss i))
        (setq lst (cons (list (DEGV:_sirano-int-from-ename e) e) lst))
        (setq i (1+ i))
      )
    )
  )
  (setq lst (vl-sort lst '(lambda (a b) (< (car a) (car b)))))
  (mapcar 'cadr lst)
)

(defun DEGV:_bbox (vlaObj / mn mx)
  (if (and vlaObj (vlax-method-applicable-p vlaObj 'GetBoundingBox))
    (progn
      (vla-GetBoundingBox vlaObj 'mn 'mx)
      (list (DEGV:_v2l mn) (DEGV:_v2l mx))
    )
  )
)

(defun DEGV:_pt (x y) (list x y 0.0))

(defun DEGV:_dist2d (p q)
  (sqrt
    (+ (expt (- (car p) (car q)) 2.0)
       (expt (- (cadr p) (cadr q)) 2.0))
  )
)

(defun DEGV:_bbox-sample-pts (mn mx / x1 y1 x2 y2 xc yc)
  (setq x1 (car mn)  y1 (cadr mn))
  (setq x2 (car mx)  y2 (cadr mx))
  (setq xc (/ (+ x1 x2) 2.0))
  (setq yc (/ (+ y1 y2) 2.0))
  (list
    (DEGV:_pt x1 y1) (DEGV:_pt x2 y1) (DEGV:_pt x2 y2) (DEGV:_pt x1 y2)
    (DEGV:_pt xc y1) (DEGV:_pt x2 yc) (DEGV:_pt xc y2) (DEGV:_pt x1 yc)
    (DEGV:_pt xc yc)
  )
)

(defun DEGV:_min-dist-pts-to-curve (e pts / i p cp d mind)
  (setq mind 1e99)
  (setq i 0)
  (while (< i (length pts))
    (setq p (nth i pts))
    (setq cp (vlax-curve-getclosestpointto e p))
    (if cp
      (progn
        (setq d (DEGV:_dist2d p cp))
        (if (< d mind) (setq mind d))
      )
    )
    (setq i (1+ i))
  )
  mind
)

(defun DEGV:_ename-handle (e)
  (cdr (assoc 5 (entget e)))
)

(defun DEGV:_handle-in-list (h hlist)
  (if (member h hlist) T nil)
)

(defun DEGV:_append-unique-by-handle (hChain chain addList / e h)
  (foreach e addList
    (if (and e (= (type e) 'ENAME))
      (progn
        (setq h (DEGV:_ename-handle e))
        (if (and h (not (DEGV:_handle-in-list h hChain)))
          (progn
            (setq hChain (cons h hChain))
            (setq chain  (cons e chain))
          )
        )
      )
    )
  )
  (list hChain chain)
)

(defun DEGV:_ss-union (a b / out i)
  (setq out (ssadd))
  (if a
    (progn
      (setq i 0)
      (while (< i (sslength a))
        (ssadd (ssname a i) out)
        (setq i (1+ i))
      )
    )
  )
  (if b
    (progn
      (setq i 0)
      (while (< i (sslength b))
        (ssadd (ssname b i) out)
        (setq i (1+ i))
      )
    )
  )
  out
)

(defun DEGV:_ss-add-unique (ss e / i hit he hs cur)
  (if (and ss e (= (type e) 'ENAME))
    (progn
      (setq he (DEGV:_ename-handle e))
      (setq i 0 hit nil)
      (while (and (< i (sslength ss)) (not hit))
        (setq cur (ssname ss i))
        (setq hs (DEGV:_ename-handle cur))
        (if (or (equal e cur) (and he hs (= he hs)))
          (setq hit T)
        )
        (setq i (1+ i))
      )
      (if (not hit) (ssadd e ss))
    )
  )
  ss
)

(defun DEGV:_ss-unique (ss / out i)
  (setq out (ssadd))
  (if ss
    (progn
      (setq i 0)
      (while (< i (sslength ss))
        (setq out (DEGV:_ss-add-unique out (ssname ss i)))
        (setq i (1+ i))
      )
    )
  )
  out
)
(defun DEGV:_filter-out-doseme-blocks (ss / out i e bname)
  (setq out (ssadd))
  (if ss
    (progn
      (setq i 0)
      (while (< i (sslength ss))
        (setq e (ssname ss i))
        (setq bname (strcase (cdr (assoc 2 (entget e)))))
        (if (/= bname (DEG:VAL 'M1))
          (ssadd e out)
        )
        (setq i (1+ i))
      )
    )
  )
  out
)


(defun DEGV:_block-has-attrib-tag? (blkE tag / e d)
  (setq tag (strcase tag))
  (setq e (entnext blkE))
  (while (and e
              (setq d (entget e))
              (not (= (cdr (assoc 0 d)) "SEQEND")))
    (if (= (cdr (assoc 0 d)) "ATTRIB")
      (if (= (strcase (cdr (assoc 2 d))) tag)
        (progn (setq e nil) (setq d 'FOUND))
      )
    )
    (if e (setq e (entnext e)))
  )
  (if (= d 'FOUND) T nil)
)

(defun DEGV:_filter-blocks-with-sira-no (ss / out i e)
  (setq out (ssadd))
  (if ss
    (progn
      (setq i 0)
      (while (< i (sslength ss))
        (setq e (ssname ss i))
        (if (DEGV:_block-has-attrib-tag? e "SIRA_NO")
          (ssadd e out)
        )
        (setq i (1+ i))
      )
    )
  )
  out
)


(defun deg-layer0-ename-p (e / lay)
  (setq lay (cdr (assoc 8 (entget e))))
  (and lay (= (strcase lay) "0"))
)

(defun deg-layerE-str-p (lay)
  (and lay (wcmatch (strcase lay) "E_*"))
)

(defun deg-layerE-ename-p (e / lay)
  (setq lay (cdr (assoc 8 (entget e))))
  (deg-layerE-str-p lay)
)


(defun DEGV:_touch-block-to-poly? (blkObj polyE tol / ip cp d)
  (setq ip (DEGV:_v2l (vla-get-InsertionPoint blkObj)))
  (if (and ip polyE)
    (progn
      (setq cp (vlax-curve-getclosestpointto polyE ip))
      (if cp
        (progn
          (setq d (DEGV:_dist2d ip cp))
          (if (<= d tol) T nil)
        )
        nil
      )
    )
    nil
  )
)


(defun DEGV:_blocks-touching-chain (chain tol / res src e lay blkObj polyE hit)
  (setq res (ssadd))
  (if DEGN-DEGA--SCOPE-ACTIVE
    (setq src DEGN-DEGA--SCOPE-BLOCKS)
    (setq src (DEGN-DEGA--scope-ss-to-list (ssget "X" '((0 . "INSERT")))))
  )
  (foreach e src
    (if (and e (= (type e) 'ENAME) (DEGN-DEGA--scope-block-p e))
      (progn
        (setq lay (cdr (assoc 8 (entget e))))
        (if (/= (strcase (if lay lay "")) (DEG:VAL 'O2))
          (progn
            (setq blkObj (vlax-ename->vla-object e))
            (setq hit nil)
            (foreach polyE chain
              (if (and (not hit)
                       polyE
                       (= (type polyE) 'ENAME)
                       (DEGN-DEGA--scope-poly-p polyE)
                       (DEGV:_touch-block-to-poly? blkObj polyE tol))
                (setq hit T)
              )
            )
            (if hit (ssadd e res))
          )
        )
      )
    )
  )
  res
)
(defun DEGV:_poly-touches-any-selected-block? (polyE ssBlocks tol / i blkE blkObj ok)
  (setq ok nil)
  (if (and ssBlocks (> (sslength ssBlocks) 0))
    (progn
      (setq i 0)
      (while (and (< i (sslength ssBlocks)) (not ok))
        (setq blkE (ssname ssBlocks i))
        (setq blkObj (vlax-ename->vla-object blkE))
        (if (DEGV:_touch-block-to-poly? blkObj polyE tol)
          (setq ok T)
        )
        (setq i (1+ i))
      )
    )
  )
  ok
)


(defun DEGV:_touching-polyline-layers-for-block-global (blkObj chain tolTouch / out ip touchedE polyE o lyr mnw mxw ssCand i e)
  (setq touchedE nil)
  (setq out nil)

  (if (not blkObj)
    nil
    (progn
      (setq ip (DEGV:_v2l (vla-get-InsertionPoint blkObj)))

      (foreach polyE chain
        (if (and polyE (= (type polyE) 'ENAME)
             (deg-layerE-ename-p polyE)
             (not (deg-layer0-ename-p polyE)))
          (if (DEGV:_touch-block-to-poly? blkObj polyE tolTouch)
            (if (not (member polyE touchedE))
              (setq touchedE (cons polyE touchedE))
            )
          )
        )
      )

      (if ip
        (progn
          (setq mnw (list (- (car ip) tolTouch) (- (cadr ip) tolTouch) 0.0))
          (setq mxw (list (+ (car ip) tolTouch) (+ (cadr ip) tolTouch) 0.0))
          (setq ssCand (ssget "_C" mnw mxw '((0 . "LWPOLYLINE,POLYLINE"))))
          (if ssCand
            (progn
              (setq i 0)
              (while (< i (sslength ssCand))
                (setq e (ssname ssCand i))
                (if (and e (not (DEGN-DEGA--scope-poly-p e))) (setq e nil))
                (if (and e (= (strcase (cdr (assoc 8 (entget e)))) (DEG:VAL 'O2))) (setq e nil))
                (if (and e (= (strcase (cdr (assoc 8 (entget e)))) "0")) (setq e nil))
                (if e
                  (if (and (not (member e chain))
                           (DEGV:_touch-block-to-poly? blkObj e tolTouch))
                    (progn
                      (setq o (vl-catch-all-apply 'vlax-ename->vla-object (list e)))
                      (if (not (vl-catch-all-error-p o))
                        (progn
                          (setq lyr (vla-get-Layer o))
                          (if (and lyr (deg-layerE-str-p lyr))
                            (if (not (member e touchedE))
                              (setq touchedE (cons e touchedE))
                            )
                          ))
                      )
                    )
                  )
                )
                (setq i (1+ i))
              )
            )
          )
        )
      )

      (foreach e (reverse touchedE)
        (setq o (vl-catch-all-apply 'vlax-ename->vla-object (list e)))
        (if (not (vl-catch-all-error-p o))
          (progn
            (setq lyr (vla-get-Layer o))
            (if (and lyr (deg-layerE-str-p lyr) (/= (strcase lyr) "0")) (setq out (cons lyr out)))
          )
        )
      )

      (reverse out)
    )
  )

)
    
  




(defun DEGV:_touching-polylines-for-block-global (blkObj chain tolTouch / ip mnw mxw ssCand i e ok out o lyr)
  (setq out nil)
  (setq ip (DEGV:_v2l (vla-get-InsertionPoint blkObj)))
  (if (not ip)
    nil
    (progn
      (setq mnw (list (- (car ip) tolTouch) (- (cadr ip) tolTouch) 0.0))
      (setq mxw (list (+ (car ip) tolTouch) (+ (cadr ip) tolTouch) 0.0))
      (setq ssCand (ssget "_C" mnw mxw '((0 . "LWPOLYLINE,POLYLINE"))))
      (if (not ssCand)
        nil
        (progn
          (setq i 0)
          (while (< i (sslength ssCand))
                (setq e (ssname ssCand i))
                (if (and e (not (DEGN-DEGA--scope-poly-p e))) (setq e nil))
                (if (and e (= (strcase (cdr (assoc 8 (entget e)))) (DEG:VAL 'O2))) (setq e nil))
                (if (and e (= (strcase (cdr (assoc 8 (entget e)))) "0")) (setq e nil))
            (if (and e (not (deg-layerE-ename-p e))) (setq e nil))
            (if e
              (progn
                (setq ok (DEGV:_touch-block-to-poly? blkObj e tolTouch))
                (if ok
                  (progn
                    (setq o (vl-catch-all-apply 'vlax-ename->vla-object (list e)))
                    (if (not (vl-catch-all-error-p o))
                      (progn
                        (setq lyr (vla-get-Layer o))
                        (if (and lyr (deg-layerE-str-p lyr) (/= (strcase lyr) "0"))
                          (if (not (member e out))
                            (setq out (cons e out))
                          )
                        )
                      )
                    )
                  )
                )
              )
            )
            (setq i (1+ i))
          )
          (reverse out)
        )
      )
    )
  )
)

(defun DEGV:_touching-polylines-for-block-anylayer (blkObj tolTouch / out ip mnw mxw ssCand i e ok)
  (setq out nil)
  (if (not blkObj)
    nil
    (progn
      (setq ip (deg-get-inspt blkObj))
      (setq mnw (list (- (car ip) tolTouch) (- (cadr ip) tolTouch) 0.0))
      (setq mxw (list (+ (car ip) tolTouch) (+ (cadr ip) tolTouch) 0.0))
      (setq ssCand (ssget "_C" mnw mxw '((0 . "LWPOLYLINE,POLYLINE"))))
      (if (not ssCand)
        nil
        (progn
          (setq i 0)
          (while (< i (sslength ssCand))
                (setq e (ssname ssCand i))
                (if (and e (not (DEGN-DEGA--scope-poly-p e))) (setq e nil))
                (if (and e (= (strcase (cdr (assoc 8 (entget e)))) (DEG:VAL 'O2))) (setq e nil))
                (if (and e (= (strcase (cdr (assoc 8 (entget e)))) "0")) (setq e nil))
            (if (and e (not (deg-layerE-ename-p e))) (setq e nil))
            (if e
              (progn
                (setq ok (DEGV:_touch-block-to-poly? blkObj e tolTouch))
                (if ok
                  (if (not (member e out))
                    (setq out (cons e out))
                  )
                )
              )
            )
            (setq i (1+ i))
          )
          (reverse out)
        )
      )
    )
  )
)

(defun DEGV:_mark-nonchain-touched-polys-red (blkObj chain tolTouch / lst e o)
  (setq lst (DEGV:_touching-polylines-for-block-anylayer blkObj tolTouch))
  (if (and lst (> (length lst) 1))
    (foreach e lst
      (if (and e (not (member e chain)))
        (progn
          (setq o (vl-catch-all-apply 'vlax-ename->vla-object (list e)))
          (if (not (vl-catch-all-error-p o))
            (if (vlax-property-available-p o 'Color)
              nil
            )
          )
        )
      )
    )
  )
  lst
)

(defun DEGV:_touching-polylines-in-chain-for-block (blkObj chain tolTouch / out polyE)
  (setq out (ssadd))
  (foreach polyE chain
    (if (and polyE (= (type polyE) 'ENAME)
             (deg-layerE-ename-p polyE)
             (not (deg-layer0-ename-p polyE))
             (member (cdr (assoc 0 (entget polyE))) '("LWPOLYLINE" "POLYLINE")))
      (if (DEGV:_touch-block-to-poly? blkObj polyE tolTouch)
        (ssadd polyE out)
      )
    )
  )
  out
)

(defun DEGV:_touching-polyline-layers-for-block (blkObj chain tolTouch / ss i e o lyr out)
  (setq out nil)
  (setq ss (DEGV:_touching-polylines-in-chain-for-block blkObj chain tolTouch))
  (if ss
    (progn
      (setq i 0)
      (while (< i (sslength ss))
        (setq e (ssname ss i))
        (if e
          (progn
            (setq o (vl-catch-all-apply 'vlax-ename->vla-object (list e)))
            (if (not (vl-catch-all-error-p o))
              (progn
                (setq lyr (vla-get-Layer o))
                (if (and lyr (/= (strcase lyr) "0") (not (member lyr out)))
                  (setq out (cons lyr out))
                )
              )
            )
          )
        )
        (setq i (1+ i))
      )
    )
  )
  (reverse out)
)



(defun DEGV:_nearest-touching-polyline-layer (blkObj chain tolTouch / ip bestE bestD polyE cp d)
  (setq ip (DEGV:_v2l (vla-get-InsertionPoint blkObj)))
  (setq bestE nil)
  (setq bestD 1e99)
  (if ip
    (foreach polyE chain
      (if (and polyE (= (type polyE) 'ENAME)
               (member (cdr (assoc 0 (entget polyE))) '("LWPOLYLINE" "POLYLINE")))
        (progn
          (setq cp (vlax-curve-getclosestpointto polyE ip))
          (if cp
            (progn
              (setq d (DEGV:_dist2d ip cp))
              (if (and (<= d tolTouch) (< d bestD))
                (progn (setq bestD d) (setq bestE polyE))
              )
            )
          )
        )
      )
    )
  )
  (if bestE
    (vla-get-Layer (vlax-ename->vla-object bestE))
    nil
  )
)

(defun DEGV:_doseme_expand_filtered (chain ssBlocksNoDoseme tolTouch / hChain polyE ssDoseme i blkE blkObj
                                         touchedByChain ipd mnw mxw ssCand j candE
                                         newSeeds added pack)

  (setq hChain nil)
  (foreach polyE chain
    (if (and polyE (= (type polyE) 'ENAME)
             (not (deg-layer0-ename-p polyE)))
      (setq hChain (cons (DEGV:_ename-handle polyE) hChain))
    )
  )

  (if DEGN-DEGA--SCOPE-ACTIVE
    (setq ssDoseme (DEGN-DEGA--scope-ss-from-list (DEGN-DEGA--e_dosemeye_blocks)))
    (setq ssDoseme (ssget "X" (list (cons 0 "INSERT") (cons 2 (DEG:VAL 'M1)))))
  )
  (if (not ssDoseme)
    chain
    (progn
      (setq i 0)
      (while (< i (sslength ssDoseme))
        (setq blkE   (ssname ssDoseme i))
        (setq blkObj (vlax-ename->vla-object blkE))

        (setq touchedByChain nil)
        (foreach polyE chain
          (if (and (not touchedByChain)
                   (member (cdr (assoc 0 (entget polyE))) '("LWPOLYLINE" "POLYLINE")))
            (if (DEGV:_touch-block-to-poly? blkObj polyE tolTouch)
              (setq touchedByChain T)
            )
          )
        )

        (if touchedByChain
          (progn
            (setq ipd (DEGV:_v2l (vla-get-InsertionPoint blkObj)))
            (if ipd
              (progn
                (setq mnw (list (- (car ipd) tolTouch) (- (cadr ipd) tolTouch) 0.0))
                (setq mxw (list (+ (car ipd) tolTouch) (+ (cadr ipd) tolTouch) 0.0))

                (setq ssCand (ssget "_C" mnw mxw '((0 . "LWPOLYLINE,POLYLINE"))))
                (if ssCand
                  (progn
                    (setq newSeeds nil)
                    (setq j 0)
                    (while (< j (sslength ssCand))
                      (setq candE (ssname ssCand j))
                      (if (and candE (not (DEGN-DEGA--scope-poly-p candE))) (setq candE nil))

                      (if (and candE (DEGV:_touch-block-to-poly? blkObj candE tolTouch))
                        (progn
                          (if (DEGV:_poly-touches-any-selected-block? candE ssBlocksNoDoseme tolTouch)
                            (setq newSeeds (cons candE newSeeds))
                          )
                        )
                      )

                      (setq j (1+ j))
                    )

                    (foreach candE newSeeds
                      (if (and candE (= (type candE) 'ENAME))
                        (if (not (DEGV:_handle-in-list (DEGV:_ename-handle candE) hChain))
                          (progn
                            (setq added (DEGN-DEGA--chain candE))
            (setq added (DEGV:_filter-chain-data added))
                            (if added
                              (progn
                                (setq pack (DEGV:_append-unique-by-handle hChain chain added))
                                (setq hChain (car pack))
                                (setq chain  (cadr pack))
                              )
                            )
                          )
                        )
                      )
                    )
                  )
                )
              )
            )
          )
        )

        (setq i (1+ i))
      )
      chain
    )
  )
)

  



(defun DEGV:RUN ( / pasteCount refEnt refObj refLayer firstStart lastBottom firstSet pastedBlks ent obj plLayer
    refStartPt
    tolTouch areaSS oldErr
    chain signalChain ends blocks blocksND
    ip baseX baseY
    i blkE blkObj lyr
    ms doc cpObj cpE
    tgt disp
    _idx _cnt _dx _x
    ssNew
    blksSorted lyrList prevBottom plObj _lyr _y _leadSign _vlen _sira _ipV _ip _tpt _tx
    dkkItem dkkObj
  )
  (vl-load-com)
  (setq oldErr *error*)
  (defun *error* (msg)
    (DEGN-DEGA--scope-reset)
    (setq *error* oldErr)
    (if (and msg (not (wcmatch (strcase msg) "*BREAK*,*CANCEL*,*QUIT*")))
      (princ (strcat "\nDEGV hata: " msg))
    )
    (princ)
  )


(defun DEGV:_regapp (app /)
  (if (not (tblsearch "APPID" app))
    (regapp app)
  )
  app
)

(defun DEGV:_mark-created (e /)
  (if (and e (= (type e) 'ENAME))
    (progn
      (DEGV:_regapp "DEGV")
      (entmod (append (entget e) (list (list -3 (list "DEGV" (cons 1000 "CREATED"))))))
      (entupd e)
    )
  )
  e
)

(defun DEGV:_is-created (e / x)
  (if (and e (= (type e) 'ENAME))
    (progn
      (setq x (assoc -3 (entget e '("DEGV"))))
      (and x (vl-string-search "CREATED" (vl-prin1-to-string x)))
    )
    nil
  )
)

  (setq tolTouch (DEG:CFG-TOL-NUM-OR 'DN_BLOCK_TOL 1.0))
  (setq *degk-attsync-names* nil)
  (setq firstSet nil firstStart nil lastBottom nil prevBottom nil blksSorted nil lyrList nil)

  (if (and (boundp '*degk-dispatch-sel*) *degk-dispatch-sel*)
    (progn (setq sel *degk-dispatch-sel*) (setq *degk-dispatch-sel* nil))
    (setq sel (entsel "\nDEGV: Polyline seç: ")))
  (if (not sel) (progn (princ) (exit)))
  (setq ent (car sel))
  (setq pickPt (cadr sel))
(setq obj (vlax-ename->vla-object ent))
  (setq refEnt ent)
  (setq refObj obj)
  (setq refLayer (vla-get-Layer refObj))

  (setq refStartPt (DEGV:_get-pl-startpt ent pickPt))

  (setq plLayer (strcase (vla-get-Layer obj)))
  (if (not (DEGK--data-layer-name-p plLayer))
    (progn (princ "\n\nDEGV: Seçilen polyline DATA layerýnda deðil.") (princ) (exit))
  )

  (princ "\nDK DATA: Alan icindeki block ve polyline'lari secin: ")
  (setq areaSS (ssget '((0 . "INSERT,LWPOLYLINE,POLYLINE"))))
  (if (not areaSS)
    (progn
      (DEGN-DEGA--scope-reset)
      (setq *error* oldErr)
      (princ)
      (exit)
    )
  )
  (DEGN-DEGA--scope-set-from-ss areaSS ent)

  (setq signalChain (DEGN-DEGA--chain ent))
  (setq chain (DEGV:_filter-chain-data signalChain))
  (setq signalChain (DEGV:_filter-chain-data-tel-tv signalChain))
  (if (not chain) (progn (princ "\n\nDEGV: Chain bulunamadý.") (princ) (exit)))
  (if (not signalChain) (setq signalChain chain))

  (setq ends   (DEGN-DEGA--chain-ends signalChain DEGN-DEGA--TOL))
  (setq blocks (DEGN-DEGA--blocks-near ends DEGN-DEGA--TOLBLOCK))
  (setq blocks (DEGV:_ss-union blocks (DEGV:_blocks-touching-chain signalChain tolTouch)))
  (setq blocksND (DEGV:_filter-blocks-with-sira-no (DEGV:_filter-out-doseme-blocks blocks)))
  (setq blocksND (DEGV:_ss-unique (DEG:SS-REMOVE-IGNORED-BLOCKS blocksND)))

  (setq chain (DEGV:_doseme_expand_filtered chain blocksND tolTouch))
  (setq signalChain (DEGV:_chain-merge-unique signalChain chain))


  (DEGV:_set-chain-polylines-white chain)
  (setq ends     (DEGN-DEGA--chain-ends signalChain DEGN-DEGA--TOL))
  (setq blocks   (DEGN-DEGA--blocks-near ends DEGN-DEGA--TOLBLOCK))
  (setq blocks (DEGV:_ss-union blocks (DEGV:_blocks-touching-chain signalChain tolTouch)))
  (setq blocksND (DEGV:_filter-blocks-with-sira-no (DEGV:_filter-out-doseme-blocks blocks)))
  (setq blocksND (DEGV:_ss-unique (DEG:SS-REMOVE-IGNORED-BLOCKS blocksND)))

  (if (or (null blocksND) (= (sslength blocksND) 0))
    (progn (princ "\n\nDEGV: (Doseme hariç) block bulunamadý.") (princ) (exit))
  )

  (setq ip (getpoint "\nYapýþtýrma baþlangýç noktasý: "))
  (if (not ip) (progn (princ) (exit)))
  (setq baseX (car ip) baseY (cadr ip))

  (setq doc (vla-get-ActiveDocument (vlax-get-acad-object)))
  (setq ms  (vla-get-ModelSpace doc))

  (setq pastedBlks nil)
  (setq ssNew (ssadd))

  (setq blksSorted (DEGV:_sort-blocks-by-sirano-int blocksND))

  (if (degkk--active-p)
    (setq blksSorted (degkk--prepare-items blksSorted))
  )

  (setq pasteCount (length blksSorted))

  (setq i 0)
  (foreach blkE blksSorted
    (setq blkObj (vlax-ename->vla-object blkE))
    (degk--attsync-add blkObj)
    (setq lyrList (DEGV:_touching-polyline-layers-for-block-global blkObj (vl-remove nil (mapcar 'degk--as-ename signalChain)) tolTouch))
    (if (degkk--active-p)
      (foreach dkkItem (degkk--group-items blkObj)
        (setq dkkObj (degkk--as-object dkkItem))
        (if dkkObj
          (setq lyrList
            (append
              lyrList
              (DEGV:_touching-polyline-layers-for-block-global
                dkkObj
                (vl-remove nil (mapcar 'degk--as-ename signalChain))
                tolTouch)))
        )
      )
    )
    (setq lyrList (degkk--unique-strings lyrList))
    (setq lyrList (vl-remove-if-not 'deg-layerE-str-p lyrList))
    (if (or (null lyrList) (= (length lyrList) 0))
      (setq lyrList nil)
    )
    (DEGV:_mark-nonchain-touched-polys-red blkObj signalChain tolTouch)

    (setq cpObj (vla-Copy blkObj))

    (DEGV:_make-scale-positive cpObj)
    (degk--ensure-layer (DEG:VAL 'O2))
    (vla-put-Layer cpObj (DEG:VAL 'O2))


    (setq pastedBlks (cons (DEG:ENAME cpObj) pastedBlks))
    (setq cpE   (vlax-vla-object->ename cpObj))

    (if (= (vla-get-ObjectName cpObj) "AcDbBlockReference")
      (vla-put-Rotation cpObj 0.0)
    )

    (ssadd cpE ssNew)

    (setq tgt (list (+ baseX (* i (DEG:CFG-DK-NUM-OR 'DKX_COPY_SPACING 140.0))) baseY 0.0))
    (if (not firstSet)
      (progn
        (setq firstStart (list (- (car tgt) (DEG:CFG-DK-NUM-OR 'DKX_FIRSTSTART_X 110.0)) (- (cadr tgt) (DEG:CFG-DK-NUM-OR 'DKX_FIRSTSTART_Y 100.0))))
        (setq firstSet T)
      )
    )
    (setq prevBottom lastBottom)
    (setq lastBottom (list (- (car tgt) (DEG:CFG-DK-NUM-OR 'DKX_LASTBOTTOM_X 10.0)) (- (cadr tgt) (DEG:CFG-DK-NUM-OR 'DKX_LASTBOTTOM_Y 100.0))))


    (setq disp
      (mapcar '-
        tgt
        (DEGV:_v2l (vla-get-InsertionPoint blkObj))
      )
    )
    (vla-Move cpObj (vlax-3d-point '(0 0 0)) (vlax-3d-point disp))
    (degk--reset-insert-attrs cpE)
    (if (degkk--active-p)
      (degk--set-att cpObj "ADET" (strcat "x" (itoa (degkk--item-count blkObj))))
    )
    (ssadd cpE ssNew)

    (DEGV:_ensure-layer doc "e_kolon_numarasi")

    (setq _sira "")
    (if (and cpObj (vlax-method-applicable-p cpObj 'GetAttributes))
      (foreach a (vlax-safearray->list (vlax-variant-value (vla-GetAttributes cpObj)))
        (if (= (strcase (vla-get-TagString a)) "SIRA_NO")
          (setq _sira (vla-get-TextString a))
        )
      )
    )
    (if (= _sira "") (setq _sira (DEGV:_attval cpObj "SIRA_NO")))
    (if (= _sira "") (setq _sira "<NO_SIRA_NO>"))

    (setq _ipV (deg-get-inspt cpObj))
    (setq _ip  (cond
                 ((= (type _ipV) 'VARIANT)  (vlax-safearray->list (vlax-variant-value _ipV)))
                 ((= (type _ipV) 'SAFEARRAY)(vlax-safearray->list _ipV))
                 (T (list (car tgt) (cadr tgt) 0.0))
               )
    )
    (setq _tpt (list (car _ip) (+ (cadr _ip) (DEG:CFG-DK-NUM-OR 'DKX_TEXT_OFFSET_Y 70.0)) (if (caddr _ip) (caddr _ip) 0.0)))

    (if (not (degkk--active-p))
      (progn
        (setq _tx  (vla-AddText ms _sira (vlax-3d-point _tpt) (DEG:CFG-DK-NUM-OR 'DKX_TEXT_HEIGHT 25.0)))
        (vla-put-Layer _tx "e_kolon_numarasi")
        (vla-put-Rotation _tx (/ pi 2.0))
        (vla-put-Alignment _tx acAlignmentMiddleLeft)
        (vla-put-TextAlignmentPoint _tx (vlax-3d-point _tpt))
        (ssadd (vlax-vla-object->ename _tx) ssNew)
      )
    )

    (DEGV:_attclear cpObj "SIRA_NO")
(setq _cnt (length lyrList))
(setq _idx 0)
(foreach _lyr lyrList
  (if (or (null _lyr) (= _lyr ""))
    (setq _lyr (if refLayer refLayer (getvar "CLAYER")))
  )
  (DEGV:_ensure-layer doc _lyr)

  (setq _dx 0.0)
  (cond
    ((= _cnt 3)
      (cond
        ((= _idx 1) (setq _dx (- (DEG:CFG-DK-NUM-OR 'DKX_MULTI_DX 10.0))))
        ((= _idx 2) (setq _dx  (DEG:CFG-DK-NUM-OR 'DKX_MULTI_DX 10.0)))
      )
    )
    ((= _cnt 2)
      (if (= _idx 1) (setq _dx (DEG:CFG-DK-NUM-OR 'DKX_MULTI_DX 10.0)))
    )
  )

  (setq _x (+ (car tgt) _dx))
  (setq _y (cadr tgt))
  (setq _leadSign nil)
  (if (> _idx 0)
    (setq _leadSign (if (< _dx 0.0) 1.0 -1.0))
  )
  (if (> _idx 0) (setq _y (- _y (DEG:CFG-DK-NUM-OR 'DKX_MULTI_DROP_Y 10.0))))
  (setq _vlen (if (> _idx 0) (DEG:CFG-DK-NUM-OR 'DKX_VLEN_SECONDARY 90.0) (DEG:CFG-DK-NUM-OR 'DKX_VLEN_MAIN 100.0))) ;; 2. ve 3. polyline 10 birim kýsa
  (setq _hlen (DEG:CFG-DK-NUM-OR 'DKX_HLEN_DEFAULT 150.0))
  (if (and (= i (1- pasteCount))
           (= _cnt 2)
           (= _idx 1)
           (not (DEGV:_layer-is-data-str _lyr refLayer)))
    (setq _hlen (DEG:CFG-DK-NUM-OR 'DKX_HLEN_LAST2 20.0))
  )
  (if (and (= i (1- pasteCount))
           (= _cnt 3))
    (progn
      (if (and (= _idx 1)
               (not (DEGV:_layer-is-data-str _lyr refLayer)))
        (setq _hlen (DEG:CFG-DK-NUM-OR 'DKX_HLEN_LAST3_LEFT 10.0))
      )
      (if (and (= _idx 2)
               (not (DEGV:_layer-is-data-str _lyr refLayer)))
        (setq _hlen (DEG:CFG-DK-NUM-OR 'DKX_HLEN_LAST3_RIGHT 20.0))
      )
    )
  )

  (if (= i (1- pasteCount))
    (cond
      ((and (= _cnt 3) (= _idx 1) (not (DEGV:_layer-is-data-str _lyr refLayer)))
        (setq plObj (DEGV:_add-under-polyline-last-filleted ms _x _y _lyr _vlen _hlen _leadSign))
      )
      ((and (or (= _cnt 2) (= _cnt 3))
            (DEGV:_layer-is-data-str _lyr refLayer))
        (setq plObj (DEGV:_add-under-polyline-last-filleted ms _x _y _lyr _vlen _hlen _leadSign))
      )
      (T
        (setq plObj (DEGV:_add-under-polyline-last ms _x _y _lyr _vlen _hlen _leadSign))
      )
    )
    (setq plObj (DEGV:_add-under-polyline-filleted ms _x _y _lyr _vlen _leadSign))
  )

(ssadd (vlax-vla-object->ename plObj) ssNew)
  (setq _idx (1+ _idx))
)
(setq i (1+ i))
  )

  (if (and firstSet firstStart prevBottom refLayer (deg-layerE-str-p refLayer) (/= (strcase refLayer) "0"))
    (DEGV:_add-2pt-lwpoly ms firstStart prevBottom refLayer)
  )

  (sssetfirst nil ssNew)

  (vl-catch-all-apply 'DEGV:_move-klemens-terminal (list pastedBlks))
  (degk--attsync-run)
  (DEGN-DEGA--scope-reset)
  (setq *error* oldErr)
  (princ)
)

(princ)


(defun DEGV:_set-chain-polylines-white (chain /)
  nil
)

(defun DEGV:_mark-nonchain-touched-polys-red (blkObj chain tolTouch / lst)
  (setq lst (DEGV:_touching-polylines-for-block-anylayer blkObj tolTouch))
  lst
)




(vl-load-com)


(defun DEGQ:_regapp (app /)
  (if (not (tblsearch "APPID" app))
    (regapp app)
  )
  app
)

(defun DEGQ:_mark-created (e /)
  e
)

(defun DEGQ:_is-created (e /)
  nil
)


(defun DEGQ:_set-chain-polylines-white (chain / polyE obj)
  (foreach polyE chain
    (if (and polyE (setq obj (vl-catch-all-apply 'vlax-ename->vla-object (list polyE))))
      (if (not (vl-catch-all-error-p obj))
        (if (vlax-property-available-p obj 'Color)
          nil
        )
      )
    )
  )
)
(defun DEGQ:_cctv-layer-name-p (layer / layU key)
  (if layer
    (progn
      (setq layU (strcase layer)
            key  (DEG:VAL 'D6))
      (or (DEG:LAYER-IN-CODES? layU '(D1 D2 D3 D4))
          (wcmatch layU (DEG:VAL 'D5))
          (and key
               (/= (vl-string-trim " \t\r\n" key) "")
               (vl-string-search (strcase key) layU))
      )
    )
  )
)

(defun DEGQ:_is-cctv-layer (e / o lyr)
  (if (and e (= (type e) 'ENAME))
    (progn
      (setq o (vl-catch-all-apply 'vlax-ename->vla-object (list e)))
      (if (vl-catch-all-error-p o)
        nil
        (progn
          (setq lyr (vla-get-Layer o))
          (DEGQ:_cctv-layer-name-p lyr)
        )
      )
    )
    nil
  )
)

(defun DEGQ:_filter-chain-cctv (lst / out e)
  (setq out nil)
  (foreach e lst
    (if (DEGQ:_is-cctv-layer e)
      (setq out (cons e out))
    )
  )
  (reverse out)
)

(defun DEGQ:_POLY-TOUCHES-ANY_SELECTED-BLOCK? (pl blkList)
  nil
)



(defun DEGQ:_contains-ci (s sub)
  (if (and s sub)
    (not (null (vl-string-search (strcase sub) (strcase s))))
    nil
  )
)

(defun DEGQ:_blk-effective-name-safe (b / nm)
  (setq nm nil)
  (if (and b (= (type b) 'VLA-OBJECT))
    (progn
      (setq nm (vl-catch-all-apply 'vla-get-EffectiveName (list b)))
      (if (vl-catch-all-error-p nm) (setq nm nil))
      (if (null nm)
        (progn
          (setq nm (vl-catch-all-apply 'vla-get-Name (list b)))
          (if (vl-catch-all-error-p nm) (setq nm nil))
        )
      )
    )
  )
  (if nm (strcase nm) "")
)


(defun DEGQ:_is-klemens-terminal (bo / nm)
  (setq nm (DEGQ:_blk-effective-name-safe bo))
  (or (DEGQ:_contains-ci nm (DEG:VAL 'L1))
      (DEGQ:_contains-ci nm (DEG:VAL 'L2)))
)

(defun DEGQ:_move-klemens-terminal (blkList / acad doc lays b bo nm layName layObj wasLocked)
  (setq acad (vlax-get-acad-object)
        doc  (vla-get-ActiveDocument acad)
        lays (vla-get-Layers doc)
  )

  (foreach b blkList
    (setq bo b)
    (if (and bo (= (type bo) 'ENAME))
      (setq bo (vlax-ename->vla-object bo))
    )
    (if (and (vlax-objectp bo)
             (= (strcase (vla-get-ObjectName bo)) "ACDBBLOCKREFERENCE"))
      (progn
        (setq nm (DEGQ:_blk-effective-name-safe bo))
        (if (or (DEGQ:_contains-ci nm (DEG:VAL 'L1))
                (DEGQ:_contains-ci nm (DEG:VAL 'L2)))
          (progn
            (setq layName (vla-get-Layer bo))
            (setq layObj nil
                  wasLocked nil
            )
            (if (and layName (/= layName ""))
              (progn
                (setq layObj (vl-catch-all-apply 'vla-item (list lays layName)))
                (if (not (vl-catch-all-error-p layObj))
                  (progn
                    (setq wasLocked (vla-get-Lock layObj))
                    (if (= wasLocked :vlax-true)
                      (vla-put-Lock layObj :vlax-false)
                    )
                  )
                  (setq layObj nil)
                )
              )
            )

            (vl-catch-all-apply 'vla-Move
              (list bo (vlax-3d-point '(0 0 0)) (vlax-3d-point '(0 5.25 0)))
            )

            (if (and layObj wasLocked (= wasLocked :vlax-true))
              (vla-put-Lock layObj :vlax-true)
            )
          )
        )
      )
    )
  )
  (princ)
)

(defun DEGQ:_move-klemens-terminal-global ( / ss i en o lst)
  (setq lst '())
  (setq ss (ssget "X" '((0 . "INSERT"))))
  (if ss
    (progn
      (setq i 0)
      (while (< i (sslength ss))
        (setq en (ssname ss i))
        (if en (setq lst (cons en lst)))
        (setq i (1+ i))
      )
    )
  )
  (DEGQ:_move-klemens-terminal lst)
  (princ)
)




(defun DEGQ:_collect-blockrefs-from-ss (ss / i e o lst)
  (setq lst nil)
  (if ss
    (progn
      (setq i 0)
      (while (< i (sslength ss))
        (setq e (ssname ss i))
        (if e
          (progn
            (setq o (vlax-ename->vla-object e))
            (if (and (= (type o) 'VLA-OBJECT)
                     (= (strcase (vla-get-ObjectName o)) "ACDBBLOCKREFERENCE"))
              (setq lst (cons o lst))
            )
          )
        )
        (setq i (1+ i))
      )
    )
  )
  lst
)

(defun DEGQ:_make-scale-positive (blk / sx sy sz)
  (if (and blk
           (= (vla-get-ObjectName blk) "AcDbBlockReference")
           (vlax-property-available-p blk 'XScaleFactor))
    (progn
      (setq sx (vla-get-XScaleFactor blk))
      (setq sy (vla-get-YScaleFactor blk))
      (setq sz (vla-get-ZScaleFactor blk))
      (vla-put-XScaleFactor blk (abs sx))
      (vla-put-YScaleFactor blk (abs sy))
      (vla-put-ZScaleFactor blk (abs sz))
    )
  )
  blk
)



(defun DEGQ:_add-under-polyline-filleted (ms x y lyr vlen leadSign / sc r bulge sa pl d lx ly fy fyEnd)
  (setq sc (DEG:PLAN-UNIT-SCALE))
  (if (null vlen) (setq vlen (* 100.0 sc)))
  (setq r     (* 10.0 sc)
        bulge -0.41421356
        d     (* (/ 14.1421 1.41421356) sc)
        fy    (+ (- y vlen) r)
        fyEnd (- fy r)
  )

  (if leadSign
    (progn
      (setq lx (+ x (* leadSign d)))
      (setq ly (+ y d))
      (setq sa (vlax-make-safearray vlax-vbDouble '(0 . 7)))
      (mapcar 'vlax-safearray-put-element
              (list sa sa sa sa sa sa sa sa)
              '(0 1 2 3 4 5 6 7)
              (list
                lx ly
                x  y
                x  fy
                (- x r) fyEnd))
      (setq pl (vla-AddLightWeightPolyline ms (vlax-make-variant sa)))
      (vla-put-Layer pl lyr)
      (DEGQ:_mark-created (vlax-vla-object->ename pl))
      (vla-SetBulge pl 2 bulge)
    )
    (progn
      (setq sa (vlax-make-safearray vlax-vbDouble '(0 . 5)))
      (mapcar 'vlax-safearray-put-element
              (list sa sa sa sa sa sa)
              '(0 1 2 3 4 5)
              (list
                x y
                x fy
                (- x r) fyEnd))
      (setq pl (vla-AddLightWeightPolyline ms (vlax-make-variant sa)))
      (vla-put-Layer pl lyr)
      (DEGQ:_mark-created (vlax-vla-object->ename pl))
      (vla-SetBulge pl 1 bulge)
    )
  )
  pl
)


(defun DEGQ:_add-under-polyline-filleted-hlen (ms x y lyr vlen hlen leadSign / sc r bulge sa pl d lx ly fy fyEnd xEnd)
  (setq sc (DEG:PLAN-UNIT-SCALE))
  (if (null vlen) (setq vlen (* 100.0 sc)))
  (if (null hlen) (setq hlen (* 150.0 sc)))
  (setq r     (* 10.0 sc)
        bulge -0.41421356
        d     (* (/ 14.1421 1.41421356) sc)
        fy    (+ (- y vlen) r)
        fyEnd (- fy r)
        xEnd  (- x (abs hlen))
  )
  (if (<= (abs hlen) r) (setq xEnd (- x (+ r sc))))

  (if leadSign
    (progn
      (setq lx (+ x (* leadSign d)))
      (setq ly (+ y d))
      (setq sa (vlax-make-safearray vlax-vbDouble '(0 . 9)))
      (mapcar 'vlax-safearray-put-element
              (list sa sa sa sa sa sa sa sa sa sa)
              '(0 1 2 3 4 5 6 7 8 9)
              (list
                lx ly
                x  y
                x  fy
                (- x r) fyEnd
                xEnd fyEnd))
      (setq pl (vla-AddLightWeightPolyline ms (vlax-make-variant sa)))
      (vla-put-Layer pl lyr)
      (DEGQ:_mark-created (vlax-vla-object->ename pl))
      (vla-SetBulge pl 2 bulge)
    )
    (progn
      (setq sa (vlax-make-safearray vlax-vbDouble '(0 . 7)))
      (mapcar 'vlax-safearray-put-element
              (list sa sa sa sa sa sa sa sa)
              '(0 1 2 3 4 5 6 7)
              (list
                x y
                x fy
                (- x r) fyEnd
                xEnd fyEnd))
      (setq pl (vla-AddLightWeightPolyline ms (vlax-make-variant sa)))
      (vla-put-Layer pl lyr)
      (DEGQ:_mark-created (vlax-vla-object->ename pl))
      (vla-SetBulge pl 1 bulge)
    )
  )
  pl
)


(defun DEGQ:_add-under-polyline-last (ms x y lyr vlen hlen leadSign / sc step r bulge sa pl d lx ly fy fyEnd xEnd)
  (setq sc (DEG:PLAN-UNIT-SCALE)
        step (* 10.0 sc))
  (if (null vlen) (setq vlen (* 100.0 sc)))
  (if (null hlen) (setq hlen (* 150.0 sc)))
  (setq r     0.0
        bulge 0.0
        d     (* (/ 14.1421 1.41421356) sc)
        fy    (+ (- y vlen) step)
        fyEnd (- fy step)
        xEnd  (- x (abs hlen))
  )

  (if leadSign
    (progn
      (setq lx (+ x (* leadSign d)))
      (setq ly (+ y d))
      (setq sa (vlax-make-safearray vlax-vbDouble '(0 . 7)))
      (mapcar 'vlax-safearray-put-element
              (list sa sa sa sa sa sa sa sa)
              '(0 1 2 3 4 5 6 7)
              (list
                lx ly
                x  y
                x  fyEnd
                xEnd fyEnd))
      (setq pl (vla-AddLightWeightPolyline ms (vlax-make-variant sa)))
      (vla-put-Layer pl lyr)
      (DEGQ:_mark-created (vlax-vla-object->ename pl))
    )
    (progn
      (setq sa (vlax-make-safearray vlax-vbDouble '(0 . 5)))
      (mapcar 'vlax-safearray-put-element
              (list sa sa sa sa sa sa)
              '(0 1 2 3 4 5)
              (list
                x y
                x fyEnd
                xEnd fyEnd))
      (setq pl (vla-AddLightWeightPolyline ms (vlax-make-variant sa)))
      (vla-put-Layer pl lyr)
      (DEGQ:_mark-created (vlax-vla-object->ename pl))
    )
  )
  pl
)

(defun DEGQ:_add-2pt-lwpoly (ms p1 p2 lyr / e x1 y1 x2 y2)
  (if (and p1 p2)
    (progn
      (setq x1 (car p1) y1 (cadr p1)
            x2 (car p2) y2 (cadr p2))
      (setq e
        (entmakex
          (list
            (cons 0 "LWPOLYLINE")
            (cons 100 "AcDbEntity")
            (cons 8 (if lyr lyr "0"))
            (cons 100 "AcDbPolyline")
            (cons 90 2)
            (cons 70 0)
            (cons 10 (list x1 y1))
            (cons 10 (list x2 y2))
          )
        )
      )
      (DEGQ:_mark-created e)
      e
    )
  )
)


(defun DEGQ:_nearest-vertex (plE pickPt / ed v best bestd p d)
  (setq best nil bestd 1e99)
  (setq ed (entget plE))
  (foreach v ed
    (if (= (car v) 10)
      (progn
        (setq p (list (car (cdr v)) (cadr (cdr v)) 0.0))
        (setq d (distance p pickPt))
        (if (< d bestd) (setq bestd d best p))
      )
    )
  )
  (if best best pickPt)
)

(defun DEGQ:_get-pl-startpt (plE pickPt / sp ep vPick totalLen pDist)
  (setq sp (vlax-curve-getStartPoint plE))
  (setq ep (vlax-curve-getEndPoint   plE))
  (setq vPick (DEGQ:_nearest-vertex plE pickPt))
  (setq totalLen (vlax-curve-getDistAtParam plE (vlax-curve-getEndParam plE)))
  (setq pDist (deg-safe-dist-at-point plE (deg-safe-closest-point plE vPick)))
  (if (<= pDist (- totalLen pDist))
    sp
    ep
  )
)

(defun DEGQ:_v2l (v / r)
  (cond
    ((null v) nil)
    (t
      (setq r (vl-catch-all-apply 'vlax-variant-value (list v)))
      (if (vl-catch-all-error-p r)
        (vlax-safearray->list v)
        (vlax-safearray->list r)
      )
    )
  )
)

(defun DEGQ:_ensure-layer (doc layName / lays layObj)
  (if (null (tblsearch "LAYER" layName))
    (progn
      (setq lays (vla-get-Layers doc))
      (setq layObj (vla-Add lays layName))
    )
  )
  layName
)

(defun DEGQ:_attval (blk key / atts lst a tval)
  (setq tval "")
  (if (and blk key)
    (progn
      (if (vlax-method-applicable-p blk 'GetAttributes)
        (progn
          (setq atts (vlax-invoke blk 'GetAttributes))
          (setq lst (cond
                      ((= (type atts) 'VARIANT)  (vlax-safearray->list (vlax-variant-value atts)))
                      ((= (type atts) 'SAFEARRAY) (vlax-safearray->list atts))
                      (T nil)
                    )
          )
          (foreach a lst
            (if (or
                  (= (strcase (vla-get-TagString a)) (strcase key))
                  (and (vlax-property-available-p a 'PromptString)
                       (= (strcase (vla-get-PromptString a)) (strcase key)))
                )
              (setq tval (vla-get-TextString a))
            )
          )
        )
      )
    )
  )
  tval
)




(defun DEGQ:_attclear (blk tag / a)
  (if (and blk tag (vlax-method-applicable-p blk 'GetAttributes))
    (foreach a (vlax-safearray->list (vlax-variant-value (vla-GetAttributes blk)))
      (if (= (strcase (vla-get-TagString a)) (strcase tag))
        (vla-put-TextString a "")
      )
    )
  )
  (princ)
)


(defun DEGQ:_sirano-int-from-ename (blkE / e d tag val n)
  (setq tag "SIRA_NO")
  (setq val "")
  (if blkE
    (progn
      (setq e (entnext blkE))
      (while (and e (setq d (entget e)) (not (= (cdr (assoc 0 d)) "SEQEND")))
        (if (= (cdr (assoc 0 d)) "ATTRIB")
          (if (= (strcase (cdr (assoc 2 d))) tag)
            (setq val (cdr (assoc 1 d)))
          )
        )
        (setq e (entnext e))
      )
    )
  )
  (setq n (degk--sira-min-number val))
  (if n n 2147483647)
)

(defun DEGQ:_sort-blocks-by-sirano-int (ss / lst i e)
  (setq lst nil)
  (if ss
    (progn
      (setq i 0)
      (while (< i (sslength ss))
        (setq e (ssname ss i))
        (setq lst (cons (list (DEGQ:_sirano-int-from-ename e) e) lst))
        (setq i (1+ i))
      )
    )
  )
  (setq lst (vl-sort lst '(lambda (a b) (< (car a) (car b)))))
  (mapcar 'cadr lst)
)

(defun DEGQ:_bbox (vlaObj / mn mx)
  (if (and vlaObj (vlax-method-applicable-p vlaObj 'GetBoundingBox))
    (progn
      (vla-GetBoundingBox vlaObj 'mn 'mx)
      (list (DEGQ:_v2l mn) (DEGQ:_v2l mx))
    )
  )
)

(defun DEGQ:_pt (x y) (list x y 0.0))

(defun DEGQ:_dist2d (p q)
  (sqrt
    (+ (expt (- (car p) (car q)) 2.0)
       (expt (- (cadr p) (cadr q)) 2.0))
  )
)

(defun DEGQ:_bbox-sample-pts (mn mx / x1 y1 x2 y2 xc yc)
  (setq x1 (car mn)  y1 (cadr mn))
  (setq x2 (car mx)  y2 (cadr mx))
  (setq xc (/ (+ x1 x2) 2.0))
  (setq yc (/ (+ y1 y2) 2.0))
  (list
    (DEGQ:_pt x1 y1) (DEGQ:_pt x2 y1) (DEGQ:_pt x2 y2) (DEGQ:_pt x1 y2)
    (DEGQ:_pt xc y1) (DEGQ:_pt x2 yc) (DEGQ:_pt xc y2) (DEGQ:_pt x1 yc)
    (DEGQ:_pt xc yc)
  )
)

(defun DEGQ:_min-dist-pts-to-curve (e pts / i p cp d mind)
  (setq mind 1e99)
  (setq i 0)
  (while (< i (length pts))
    (setq p (nth i pts))
    (setq cp (vlax-curve-getclosestpointto e p))
    (if cp
      (progn
        (setq d (DEGQ:_dist2d p cp))
        (if (< d mind) (setq mind d))
      )
    )
    (setq i (1+ i))
  )
  mind
)

(defun DEGQ:_ename-handle (e)
  (cdr (assoc 5 (entget e)))
)

(defun DEGQ:_handle-in-list (h hlist)
  (if (member h hlist) T nil)
)

(defun DEGQ:_append-unique-by-handle (hChain chain addList / e h)
  (foreach e addList
    (if (and e (= (type e) 'ENAME))
      (progn
        (setq h (DEGQ:_ename-handle e))
        (if (and h (not (DEGQ:_handle-in-list h hChain)))
          (progn
            (setq hChain (cons h hChain))
            (setq chain  (cons e chain))
          )
        )
      )
    )
  )
  (list hChain chain)
)

(defun DEGQ:_ss-union (a b / out i)
  (setq out (ssadd))
  (if a
    (progn
      (setq i 0)
      (while (< i (sslength a))
        (ssadd (ssname a i) out)
        (setq i (1+ i))
      )
    )
  )
  (if b
    (progn
      (setq i 0)
      (while (< i (sslength b))
        (ssadd (ssname b i) out)
        (setq i (1+ i))
      )
    )
  )
  out
)

(defun DEGQ:_filter-out-doseme-blocks (ss / out i e bname)
  (setq out (ssadd))
  (if ss
    (progn
      (setq i 0)
      (while (< i (sslength ss))
        (setq e (ssname ss i))
        (setq bname (strcase (cdr (assoc 2 (entget e)))))
        (if (/= bname (DEG:VAL 'M1))
          (ssadd e out)
        )
        (setq i (1+ i))
      )
    )
  )
  out
)


(defun DEGQ:_block-has-attrib-tag? (blkE tag / e d)
  (setq tag (strcase tag))
  (setq e (entnext blkE))
  (while (and e
              (setq d (entget e))
              (not (= (cdr (assoc 0 d)) "SEQEND")))
    (if (= (cdr (assoc 0 d)) "ATTRIB")
      (if (= (strcase (cdr (assoc 2 d))) tag)
        (progn (setq e nil) (setq d 'FOUND))
      )
    )
    (if e (setq e (entnext e)))
  )
  (if (= d 'FOUND) T nil)
)

(defun DEGQ:_filter-blocks-with-sira-no (ss / out i e)
  (setq out (ssadd))
  (if ss
    (progn
      (setq i 0)
      (while (< i (sslength ss))
        (setq e (ssname ss i))
        (if (DEGQ:_block-has-attrib-tag? e "SIRA_NO")
          (ssadd e out)
        )
        (setq i (1+ i))
      )
    )
  )
  out
)

(defun DEGQ:_touch-block-to-poly? (blkObj polyE tol / ip cp d)
  (setq ip (DEGQ:_v2l (vla-get-InsertionPoint blkObj)))
  (if (and ip polyE)
    (progn
      (setq cp (vlax-curve-getclosestpointto polyE ip))
      (if cp
        (progn
          (setq d (DEGQ:_dist2d ip cp))
          (if (<= d tol) T nil)
        )
        nil
      )
    )
    nil
  )
)

(defun DEGQ:_poly-touches-any-selected-block? (polyE ssBlocks tol / i blkE blkObj ok)
  (setq ok nil)
  (if (and ssBlocks (> (sslength ssBlocks) 0))
    (progn
      (setq i 0)
      (while (and (< i (sslength ssBlocks)) (not ok))
        (setq blkE (ssname ssBlocks i))
        (setq blkObj (vlax-ename->vla-object blkE))
        (if (DEGQ:_touch-block-to-poly? blkObj polyE tol)
          (setq ok T)
        )
        (setq i (1+ i))
      )
    )
  )
  ok
)


(defun DEGQ:_touching-polyline-layers-for-block-global (blkObj chain tolTouch / out ip touchedE polyE o lyr mnw mxw ssCand i e)
  (setq touchedE nil)
  (setq out nil)

  (if (not blkObj)
    nil
    (progn
      (setq ip (DEGQ:_v2l (vla-get-InsertionPoint blkObj)))

      (foreach polyE chain
        (if (and polyE (= (type polyE) 'ENAME)
             (not (deg-layer0-ename-p polyE)))
          (if (DEGQ:_touch-block-to-poly? blkObj polyE tolTouch)
            (if (not (member polyE touchedE))
              (setq touchedE (cons polyE touchedE))
            )
          )
        )
      )

      (if ip
        (progn
          (setq mnw (list (- (car ip) tolTouch) (- (cadr ip) tolTouch) 0.0))
          (setq mxw (list (+ (car ip) tolTouch) (+ (cadr ip) tolTouch) 0.0))
          (setq ssCand (ssget "_C" mnw mxw '((0 . "LWPOLYLINE,POLYLINE"))))
          (if ssCand
            (progn
              (setq i 0)
              (while (< i (sslength ssCand))
                (setq e (ssname ssCand i))
                (if (= (strcase (cdr (assoc 8 (entget e)))) (DEG:VAL 'O2)) (setq e nil))
                (if (= (strcase (cdr (assoc 8 (entget e)))) "0") (setq e nil))
                (if e
                  (if (and (not (member e chain))
                           (DEGQ:_touch-block-to-poly? blkObj e tolTouch))
                    (progn
                      (setq o (vl-catch-all-apply 'vlax-ename->vla-object (list e)))
                      (if (not (vl-catch-all-error-p o))
                        (progn
                          (setq lyr (vla-get-Layer o))
                          (if (and lyr)
                            (if (not (member e touchedE))
                              (setq touchedE (cons e touchedE))
                            )
                          ))
                      )
                    )
                  )
                )
                (setq i (1+ i))
              )
            )
          )
        )
      )

      (foreach e (reverse touchedE)
        (setq o (vl-catch-all-apply 'vlax-ename->vla-object (list e)))
        (if (not (vl-catch-all-error-p o))
          (progn
            (setq lyr (vla-get-Layer o))
            (if (and lyr (/= (strcase lyr) "0")) (setq out (cons lyr out)))
          )
        )
      )

      (reverse out)
    )
  )
)

    
  




(defun DEGQ:_touching-polylines-for-block-global (blkObj chain tolTouch / ip mnw mxw ssCand i e ok out o lyr)
  (setq out nil)
  (setq ip (DEGQ:_v2l (vla-get-InsertionPoint blkObj)))
  (if (not ip)
    nil
    (progn
      (setq mnw (list (- (car ip) tolTouch) (- (cadr ip) tolTouch) 0.0))
      (setq mxw (list (+ (car ip) tolTouch) (+ (cadr ip) tolTouch) 0.0))
      (setq ssCand (ssget "_C" mnw mxw '((0 . "LWPOLYLINE,POLYLINE"))))
      (if (not ssCand)
        nil
        (progn
          (setq i 0)
          (while (< i (sslength ssCand))
            (setq e (ssname ssCand i))
            (if (= (strcase (cdr (assoc 8 (entget e)))) (DEG:VAL 'O2)) (setq e nil))
                (if (= (strcase (cdr (assoc 8 (entget e)))) "0") (setq e nil))
            (if (and e (not (deg-layerE-ename-p e))) (setq e nil))
            (if e
              (progn
                (setq ok (DEGQ:_touch-block-to-poly? blkObj e tolTouch))
                (if ok
                  (progn
                    (setq o (vl-catch-all-apply 'vlax-ename->vla-object (list e)))
                    (if (not (vl-catch-all-error-p o))
                      (progn
                        (setq lyr (vla-get-Layer o))
                        (if (and lyr (/= (strcase lyr) "0")
                               (or (member e chain)
                                   (DEGQ:_cctv-layer-name-p lyr)))
                          (if (not (member e out))
                            (setq out (cons e out))
                          )
                        )
                      )
                    )
                  )
                )
              )
            )
            (setq i (1+ i))
          )
          (reverse out)
        )
      )
    )
  )
)

(defun DEGQ:_touching-polylines-for-block-anylayer (blkObj tolTouch / out ip mnw mxw ssCand i e ok)
  (setq out nil)
  (if (not blkObj)
    nil
    (progn
      (setq ip (deg-get-inspt blkObj))
      (setq mnw (list (- (car ip) tolTouch) (- (cadr ip) tolTouch) 0.0))
      (setq mxw (list (+ (car ip) tolTouch) (+ (cadr ip) tolTouch) 0.0))
      (setq ssCand (ssget "_C" mnw mxw '((0 . "LWPOLYLINE,POLYLINE"))))
      (if (not ssCand)
        nil
        (progn
          (setq i 0)
          (while (< i (sslength ssCand))
            (setq e (ssname ssCand i))
            (if (= (strcase (cdr (assoc 8 (entget e)))) (DEG:VAL 'O2)) (setq e nil))
                (if (= (strcase (cdr (assoc 8 (entget e)))) "0") (setq e nil))
            (if (and e (not (deg-layerE-ename-p e))) (setq e nil))
            (if e
              (progn
                (setq ok (DEGQ:_touch-block-to-poly? blkObj e tolTouch))
                (if ok
                  (if (not (member e out))
                    (setq out (cons e out))
                  )
                )
              )
            )
            (setq i (1+ i))
          )
          (reverse out)
        )
      )
    )
  )
)

(defun DEGQ:_mark-nonchain-touched-polys-red (blkObj chain tolTouch / lst e o)
  (setq lst (DEGQ:_touching-polylines-for-block-anylayer blkObj tolTouch))
  (if (and lst (> (length lst) 1))
    (foreach e lst
      (if (and e (not (member e chain)))
        (progn
          (setq o (vl-catch-all-apply 'vlax-ename->vla-object (list e)))
          (if (not (vl-catch-all-error-p o))
            (if (vlax-property-available-p o 'Color)
              nil
            )
          )
        )
      )
    )
  )
  lst
)

(defun DEGQ:_touching-polylines-in-chain-for-block (blkObj chain tolTouch / out polyE)
  (setq out (ssadd))
  (foreach polyE chain
    (if (and polyE (= (type polyE) 'ENAME)
             (not (deg-layer0-ename-p polyE))
             (member (cdr (assoc 0 (entget polyE))) '("LWPOLYLINE" "POLYLINE")))
      (if (DEGQ:_touch-block-to-poly? blkObj polyE tolTouch)
        (ssadd polyE out)
      )
    )
  )
  out
)

(defun DEGQ:_touching-polyline-layers-for-block (blkObj chain tolTouch / ss i e o lyr out)
  (setq out nil)
  (setq ss (DEGQ:_touching-polylines-in-chain-for-block blkObj chain tolTouch))
  (if ss
    (progn
      (setq i 0)
      (while (< i (sslength ss))
        (setq e (ssname ss i))
        (if e
          (progn
            (setq o (vl-catch-all-apply 'vlax-ename->vla-object (list e)))
            (if (not (vl-catch-all-error-p o))
              (progn
                (setq lyr (vla-get-Layer o))
                (if (and lyr (/= (strcase lyr) "0") (not (member lyr out)))
                  (setq out (cons lyr out))
                )
              )
            )
          )
        )
        (setq i (1+ i))
      )
    )
  )
  (reverse out)
)



(defun DEGQ:_nearest-touching-polyline-layer (blkObj chain tolTouch / ip bestE bestD polyE cp d)
  (setq ip (DEGQ:_v2l (vla-get-InsertionPoint blkObj)))
  (setq bestE nil)
  (setq bestD 1e99)
  (if ip
    (foreach polyE chain
      (if (and polyE (= (type polyE) 'ENAME)
               (member (cdr (assoc 0 (entget polyE))) '("LWPOLYLINE" "POLYLINE")))
        (progn
          (setq cp (vlax-curve-getclosestpointto polyE ip))
          (if cp
            (progn
              (setq d (DEGQ:_dist2d ip cp))
              (if (and (<= d tolTouch) (< d bestD))
                (progn (setq bestD d) (setq bestE polyE))
              )
            )
          )
        )
      )
    )
  )
  (if bestE
    (vla-get-Layer (vlax-ename->vla-object bestE))
    nil
  )
)

(defun DEGQ:_doseme_expand_filtered (chain ssBlocksNoDoseme tolTouch / hChain polyE ssDoseme i blkE blkObj
                                         touchedByChain ipd mnw mxw ssCand j candE
                                         newSeeds added pack)

  (setq hChain nil)
  (foreach polyE chain
    (if (and polyE (= (type polyE) 'ENAME)
             (not (deg-layer0-ename-p polyE)))
      (setq hChain (cons (DEGQ:_ename-handle polyE) hChain))
    )
  )

  (setq ssDoseme (ssget "X" (list (cons 0 "INSERT") (cons 2 (DEG:VAL 'M1)))))
  (if (not ssDoseme)
    chain
    (progn
      (setq i 0)
      (while (< i (sslength ssDoseme))
        (setq blkE   (ssname ssDoseme i))
        (setq blkObj (vlax-ename->vla-object blkE))

        (setq touchedByChain nil)
        (foreach polyE chain
          (if (and (not touchedByChain)
                   (member (cdr (assoc 0 (entget polyE))) '("LWPOLYLINE" "POLYLINE")))
            (if (DEGQ:_touch-block-to-poly? blkObj polyE tolTouch)
              (setq touchedByChain T)
            )
          )
        )

        (if touchedByChain
          (progn
            (setq ipd (DEGQ:_v2l (vla-get-InsertionPoint blkObj)))
            (if ipd
              (progn
                (setq mnw (list (- (car ipd) tolTouch) (- (cadr ipd) tolTouch) 0.0))
                (setq mxw (list (+ (car ipd) tolTouch) (+ (cadr ipd) tolTouch) 0.0))

                (setq ssCand (ssget "_C" mnw mxw '((0 . "LWPOLYLINE,POLYLINE"))))
                (if ssCand
                  (progn
                    (setq newSeeds nil)
                    (setq j 0)
                    (while (< j (sslength ssCand))
                      (setq candE (ssname ssCand j))

                      (if (DEGQ:_touch-block-to-poly? blkObj candE tolTouch)
                        (progn
                          (if (DEGQ:_poly-touches-any-selected-block? candE ssBlocksNoDoseme tolTouch)
                            (setq newSeeds (cons candE newSeeds))
                          )
                        )
                      )

                      (setq j (1+ j))
                    )

                    (foreach candE newSeeds
                      (if (and candE (= (type candE) 'ENAME))
                        (if (not (DEGQ:_handle-in-list (DEGQ:_ename-handle candE) hChain))
                          (progn
                            (setq added (DEGN-DEGA--chain candE))
            (setq added (DEGQ:_filter-chain-cctv added))
                            (if added
                              (progn
                                (setq pack (DEGQ:_append-unique-by-handle hChain chain added))
                                (setq hChain (car pack))
                                (setq chain  (cadr pack))
                              )
                            )
                          )
                        )
                      )
                    )
                  )
                )
              )
            )
          )
        )

        (setq i (1+ i))
      )
      chain
    )
  )
)

  



(defun DEGQ:RUN ( / pasteCount refEnt refObj refLayer firstStart lastBottom firstSet pastedBlks ent obj plLayer
    refStartPt
    tolTouch
    chain ends blocks blocksND
    ip baseX baseY
    i blkE blkObj lyr
    ms doc cpObj cpE
    tgt disp
    _idx _cnt _dx _x
    ssNew
    blksSorted lyrList prevBottom plObj _lyr _y _leadSign _vlen _sira _ipV _ip _tpt _tx
    dkkItem dkkObj
  )
  (vl-load-com)


(defun DEGQ:_regapp (app /)
  (if (not (tblsearch "APPID" app))
    (regapp app)
  )
  app
)

(defun DEGQ:_mark-created (e /)
  (if (and e (= (type e) 'ENAME))
    (progn
      (DEGQ:_regapp "DEGQ")
      (entmod (append (entget e) (list (list -3 (list "DEGQ" (cons 1000 "CREATED"))))))
      (entupd e)
    )
  )
  e
)

(defun DEGQ:_is-created (e / x)
  (if (and e (= (type e) 'ENAME))
    (progn
      (setq x (assoc -3 (entget e '("DEGQ"))))
      (and x (vl-string-search "CREATED" (vl-prin1-to-string x)))
    )
    nil
  )
)

  (setq tolTouch (DEG:CFG-TOL-NUM-OR 'DN_BLOCK_TOL 1.0))
  (setq *degk-attsync-names* nil)
  (setq firstSet nil firstStart nil lastBottom nil prevBottom nil blksSorted nil lyrList nil)

  (if (and (boundp '*degk-dispatch-sel*) *degk-dispatch-sel*)
    (progn (setq sel *degk-dispatch-sel*) (setq *degk-dispatch-sel* nil))
    (setq sel (entsel "\nDEGQ: Polyline seç: ")))
  (if (not sel) (progn (princ) (exit)))
  (setq ent (car sel))
  (setq pickPt (cadr sel))
(setq obj (vlax-ename->vla-object ent))
  (setq refEnt ent)
  (setq refObj obj)
  (setq refLayer (vla-get-Layer refObj))

  (setq refStartPt (DEGQ:_get-pl-startpt ent pickPt))

  (setq plLayer (strcase (vla-get-Layer obj)))
  (if (not (DEGQ:_cctv-layer-name-p plLayer))
    (progn (princ "\n\nDEGQ: Seçilen polyline CCTV layerýnda deðil.") (princ) (exit))
  )

  (setq chain (DEGN-DEGA--chain ent))
  (setq chain (DEGQ:_filter-chain-cctv chain))
  (if (not chain) (progn (princ "\n\nDEGQ: Chain bulunamadý.") (princ) (exit)))

  (setq ends   (DEGN-DEGA--chain-ends chain DEGN-DEGA--TOL))
  (setq blocks (DEGN-DEGA--blocks-near ends DEGN-DEGA--TOLBLOCK))
  (setq blocksND (DEGQ:_filter-blocks-with-sira-no (DEGQ:_filter-out-doseme-blocks blocks)))
  (setq blocksND (DEG:SS-REMOVE-IGNORED-BLOCKS blocksND))

  (setq chain (DEGQ:_doseme_expand_filtered chain blocksND tolTouch))


  (DEGQ:_set-chain-polylines-white chain)
  (setq ends     (DEGN-DEGA--chain-ends chain DEGN-DEGA--TOL))
  (setq blocks   (DEGN-DEGA--blocks-near ends DEGN-DEGA--TOLBLOCK))
  (setq blocksND (DEGQ:_filter-blocks-with-sira-no (DEGQ:_filter-out-doseme-blocks blocks)))
  (setq blocksND (DEG:SS-REMOVE-IGNORED-BLOCKS blocksND))

  (if (or (null blocksND) (= (sslength blocksND) 0))
    (progn (princ "\n\nDEGQ: (Doseme hariç) block bulunamadý.") (princ) (exit))
  )

  (setq ip (getpoint "\nYapýþtýrma baþlangýç noktasý: "))
  (if (not ip) (progn (princ) (exit)))
  (setq baseX (car ip) baseY (cadr ip))

  (setq doc (vla-get-ActiveDocument (vlax-get-acad-object)))
  (setq ms  (vla-get-ModelSpace doc))

  (setq pastedBlks nil)
  (setq ssNew (ssadd))

  (setq blksSorted (DEGQ:_sort-blocks-by-sirano-int blocksND))

  (if (degkk--active-p)
    (setq blksSorted (degkk--prepare-items blksSorted))
  )

  (setq pasteCount (length blksSorted))

  (setq i 0)
  (foreach blkE blksSorted
    (setq blkObj (vlax-ename->vla-object blkE))
    (degk--attsync-add blkObj)
    (setq lyrList (DEGQ:_touching-polyline-layers-for-block-global blkObj chain tolTouch))
    (if (degkk--active-p)
      (foreach dkkItem (degkk--group-items blkObj)
        (setq dkkObj (degkk--as-object dkkItem))
        (if dkkObj
          (setq lyrList
            (append lyrList
                    (DEGQ:_touching-polyline-layers-for-block-global dkkObj chain tolTouch)))
        )
      )
    )
    (setq lyrList (degkk--unique-strings lyrList))
    (setq lyrList (vl-remove-if-not 'deg-layerE-str-p lyrList))
    (if (or (null lyrList) (= (length lyrList) 0))
      (setq lyrList nil)
    )
    (DEGQ:_mark-nonchain-touched-polys-red blkObj chain tolTouch)

    (setq cpObj (vla-Copy blkObj))

    (DEGQ:_make-scale-positive cpObj)
    (degk--ensure-layer (DEG:VAL 'O2))
    (vla-put-Layer cpObj (DEG:VAL 'O2))


    (setq pastedBlks (cons (DEG:ENAME cpObj) pastedBlks))
    (setq cpE   (vlax-vla-object->ename cpObj))

    (if (= (vla-get-ObjectName cpObj) "AcDbBlockReference")
      (vla-put-Rotation cpObj 0.0)
    )

    (ssadd cpE ssNew)

    (setq tgt (list (+ baseX (* i (DEG:CFG-DK-NUM-OR 'DKX_COPY_SPACING 140.0))) baseY 0.0))
    (if (not firstSet)
      (progn
        (setq firstStart (list (- (car tgt) (DEG:CFG-DK-NUM-OR 'DKX_FIRSTSTART_X 110.0)) (- (cadr tgt) (DEG:CFG-DK-NUM-OR 'DKX_FIRSTSTART_Y 100.0))))
        (setq firstSet T)
      )
    )
    (setq prevBottom lastBottom)
    (setq lastBottom (list (- (car tgt) (DEG:CFG-DK-NUM-OR 'DKX_LASTBOTTOM_X 10.0)) (- (cadr tgt) (DEG:CFG-DK-NUM-OR 'DKX_LASTBOTTOM_Y 100.0))))


    (setq disp
      (mapcar '-
        tgt
        (DEGQ:_v2l (vla-get-InsertionPoint blkObj))
      )
    )
    (vla-Move cpObj (vlax-3d-point '(0 0 0)) (vlax-3d-point disp))
    (if (DEGQ:_is-klemens-terminal cpObj)
      (vla-Move cpObj (vlax-3d-point '(0 0 0)) (vlax-3d-point '(0 5.25 0)))
    )
    (degk--reset-insert-attrs cpE)
    (if (degkk--active-p)
      (degk--set-att cpObj "ADET" (strcat "x" (itoa (degkk--item-count blkObj))))
    )

(ssadd cpE ssNew)

    (DEGQ:_ensure-layer doc "e_kolon_numarasi")

    (setq _sira "")
    (if (and cpObj (vlax-method-applicable-p cpObj 'GetAttributes))
      (foreach a (vlax-safearray->list (vlax-variant-value (vla-GetAttributes cpObj)))
        (if (= (strcase (vla-get-TagString a)) "SIRA_NO")
          (setq _sira (vla-get-TextString a))
        )
      )
    )
    (if (= _sira "") (setq _sira (DEGQ:_attval cpObj "SIRA_NO")))
    (if (= _sira "") (setq _sira "<NO_SIRA_NO>"))

    (setq _ipV (deg-get-inspt cpObj))
    (setq _ip  (cond
                 ((= (type _ipV) 'VARIANT)  (vlax-safearray->list (vlax-variant-value _ipV)))
                 ((= (type _ipV) 'SAFEARRAY)(vlax-safearray->list _ipV))
                 (T (list (car tgt) (cadr tgt) 0.0))
               )
    )
    (setq _tpt (list (car _ip) (+ (cadr _ip) (DEG:CFG-DK-NUM-OR 'DKX_TEXT_OFFSET_Y 70.0)) (if (caddr _ip) (caddr _ip) 0.0)))

    (if (not (degkk--active-p))
      (progn
        (setq _tx  (vla-AddText ms _sira (vlax-3d-point _tpt) (DEG:CFG-DK-NUM-OR 'DKX_TEXT_HEIGHT 25.0)))
        (vla-put-Layer _tx "e_kolon_numarasi")
        (vla-put-Rotation _tx (/ pi 2.0))
        (vla-put-Alignment _tx acAlignmentMiddleLeft)
        (vla-put-TextAlignmentPoint _tx (vlax-3d-point _tpt))
        (ssadd (vlax-vla-object->ename _tx) ssNew)
      )
    )

    (DEGQ:_attclear cpObj "SIRA_NO")
(setq _cnt (length lyrList))
(setq _idx 0)
(foreach _lyr lyrList
  (if (or (null _lyr) (= _lyr ""))
    (setq _lyr (if refLayer refLayer (getvar "CLAYER")))
  )
  (DEGQ:_ensure-layer doc _lyr)

  (setq _dx 0.0)
  (if (= _cnt 3)
    (cond
      ((= _idx 1) (setq _dx (- (DEG:CFG-DK-NUM-OR 'DKX_MULTI_DX 10.0))))
      ((= _idx 2) (setq _dx  (DEG:CFG-DK-NUM-OR 'DKX_MULTI_DX 10.0)))
    )
  )

  (setq _x (+ (car tgt) _dx))
  (setq _y (cadr tgt))
  (setq _leadSign nil)
  (if (> _idx 0)
    (setq _leadSign (if (< _dx 0.0) 1.0 -1.0))
  )
  (if (> _idx 0) (setq _y (- _y (DEG:CFG-DK-NUM-OR 'DKX_MULTI_DROP_Y 10.0))))
  (setq _vlen (if (> _idx 0) (DEG:CFG-DK-NUM-OR 'DKX_VLEN_SECONDARY 90.0) (DEG:CFG-DK-NUM-OR 'DKX_VLEN_MAIN 100.0))) ;; 2. ve 3. polyline 10 birim kýsa

  (if (= i (1- pasteCount))
    (cond
      ((= _cnt 3)
        (cond
          ((= _idx 1)
            (setq plObj (DEGQ:_add-under-polyline-filleted-hlen ms _x _y _lyr _vlen (DEG:CFG-DK-NUM-OR 'DKX_HLEN_LAST3_LEFT 10.0) _leadSign))
          )
          ((= _idx 2)
            (setq plObj (DEGQ:_add-under-polyline-last ms _x _y _lyr _vlen (DEG:CFG-DK-NUM-OR 'DKX_HLEN_LAST3_RIGHT 20.0) _leadSign))
          )
          (T
            (setq plObj (DEGQ:_add-under-polyline-last ms _x _y _lyr _vlen (DEG:CFG-DK-NUM-OR 'DKX_HLEN_DEFAULT 150.0) _leadSign))
          )
        )
      )
      ((= _cnt 2)
        (cond
          ((= _idx 1)
            (setq plObj (DEGQ:_add-under-polyline-last ms _x _y _lyr _vlen (DEG:CFG-DK-NUM-OR 'DKX_HLEN_LAST2 20.0) _leadSign))
          )
          (T
            (setq plObj (DEGQ:_add-under-polyline-last ms _x _y _lyr _vlen (DEG:CFG-DK-NUM-OR 'DKX_HLEN_DEFAULT 150.0) _leadSign))
          )
        )
      )
      (T
        (setq plObj (DEGQ:_add-under-polyline-last ms _x _y _lyr _vlen (DEG:CFG-DK-NUM-OR 'DKX_HLEN_DEFAULT 150.0) _leadSign))
      )
    )
    (setq plObj (DEGQ:_add-under-polyline-filleted ms _x _y _lyr _vlen _leadSign))
  )
  (ssadd (vlax-vla-object->ename plObj) ssNew)
  (setq _idx (1+ _idx))
)
(setq i (1+ i))
  )

  (if (and firstSet firstStart prevBottom refLayer (deg-layerE-str-p refLayer) (/= (strcase refLayer) "0"))
    (DEGQ:_add-2pt-lwpoly ms firstStart prevBottom refLayer)
  )

  (sssetfirst nil ssNew)

  (vl-catch-all-apply 'DEGQ:_move-klemens-terminal (list pastedBlks))
  (degk--attsync-run)
  (princ)
)

(princ)


(defun DEGQ:_set-chain-polylines-white (chain /)
  nil
)

(defun DEGQ:_mark-nonchain-touched-polys-red (blkObj chain tolTouch / lst)
  (setq lst (DEGQ:_touching-polylines-for-block-anylayer blkObj tolTouch))
  lst
)




(vl-load-com)

(defun degk--curve-ok? (ent / r)
  (setq r (vl-catch-all-apply 'vlax-curve-getStartPoint (list ent)))
  (not (vl-catch-all-error-p r))
)

(defun degk--poly-touch-insertion? (plEnt blkObj tol / ins cp)
  (setq ins (deg-get-inspt blkObj))
  (and ins
       (degk--point-near-loop-bounds-p ins (degk--loop-bounds plEnt) tol)
       (setq cp (deg-safe-closest-point plEnt ins))
       (<= (distance ins cp) tol))
)

(defun degk--block-touches-loop-p (loopEnts blkObj tol / hit plEnt)
  ;; Tek bir loop birden fazla polyline parcasindan olusabilir.
  (setq hit nil)
  (foreach plEnt loopEnts
    (if (and (not hit)
             plEnt
             (degk--curve-ok? plEnt)
             (degk--poly-touch-insertion? plEnt blkObj tol))
      (setq hit T)
    )
  )
  hit
)

(defun degk--dist-along (plEnt pt)
  (deg-safe-dist-at-point plEnt (deg-safe-closest-point plEnt pt))
)

(defun degk--get-att (blkObj tagName / res atts a tg val)
  (setq res nil)
  (setq atts (degk--att-list blkObj))
  (foreach a atts
    (setq tg (vl-catch-all-apply 'vla-get-TagString (list a)))
    (if (not (vl-catch-all-error-p tg))
      (progn
        (if (= (strcase tg) (strcase tagName))
          (progn
            (setq val (vl-catch-all-apply 'vla-get-TextString (list a)))
            (if (not (vl-catch-all-error-p val))
              (setq res val)
            )
          )
        )
      )
    )
  )
  (degk--clean-text res)
)

(defun degk--use-from-lower-sira-records
  (records totalLen / rec dist endGap n startDist startNum endDist endNum)
  (foreach rec records
    (setq dist (car rec)
          n (cadr rec)
          endGap (- totalLen dist))
    (if (or (null startDist) (< dist startDist))
      (setq startDist dist startNum n)
    )
    (if (or (null endDist) (< endGap endDist))
      (setq endDist endGap endNum n)
    )
  )
  (cond
    ((and startNum endNum (< startNum endNum)) T)
    ((and startNum endNum (> startNum endNum)) nil)
    ((and startNum endNum) (<= startDist endDist))
    (startNum T)
    (endNum nil)
    (T T)
  )
)

(defun degk--use-from-lower-sira-side
  (plEnt blocks totalLen / blkObj ins dist n records)
  (foreach blkObj blocks
    (setq n (degk--sira-min-number (degk--get-att blkObj "SIRA_NO")))
    (if n
      (progn
        (setq ins (deg-get-inspt blkObj))
        (if ins
          (progn
            (setq dist (degk--dist-along plEnt ins))
            (setq records (cons (list dist n) records))
          )
        )
      )
    )
  )
  (degk--use-from-lower-sira-records records totalLen)
)

(defun degk--set-att (blkObj tagName newVal / atts a tg)
  (setq newVal (degk--clean-text newVal))
  (degk--make-object-and-atts-editable blkObj)
  (setq atts (degk--att-list blkObj))
  (foreach a atts
    (setq tg (vl-catch-all-apply 'vla-get-TagString (list a)))
    (if (and (not (vl-catch-all-error-p tg)) (= (strcase tg) (strcase tagName)))
      (vl-catch-all-apply 'vla-put-TextString (list a newVal))
    )
  )
  nil
)


;; ------------------------------
;; DK/DEGV/DEGQ: ATTSYNC (unique block names)
;; ------------------------------
(setq *degk-attsync-names* nil)

(defun degk--blockname (blkObj / n)
  (setq n nil)
  (if (and blkObj (= (type blkObj) 'VLA-OBJECT))
    (progn
      (if (vlax-property-available-p blkObj 'EffectiveName)
        (setq n (vl-catch-all-apply 'vla-get-EffectiveName (list blkObj)))
      )
      (if (or (null n) (vl-catch-all-error-p n))
        (setq n (vl-catch-all-apply 'vla-get-Name (list blkObj)))
      )
      (if (vl-catch-all-error-p n) (setq n nil))
    )
  )
  (if (and n (= (type n) 'STR)) n nil)
)

(defun degk--room-name-key (name /)
  ;; Turkce karakterleri de sabit bir ASCII anahtara indirger.
  (strcase
    (vl-string-translate
      "ÝýÐðÜüÞþÖöÇç"
      "IiGgUuSsOoCc"
      (if name name "")))
)

(defun degk--room-fire-panel-p (blkObj / names name key hit)
  (setq names (if blkObj (DEG:BLOCK-NAMES blkObj) nil)
        hit nil)
  (foreach name names
    (setq key (degk--room-name-key name))
    (if (member key
          '("E_FIRE_ALARM_PANEL_100" "E_YANGIN_IHBAR_PANELI_100"
            "E_ANNOUNCEMENT_CENTER_100" "E_ANONS_MERKEZI_100"))
      (setq hit T)))
  hit
)

(defun degk--room-power-supply-p (blkObj / names name key hit)
  (setq names (if blkObj (DEG:BLOCK-NAMES blkObj) nil)
        hit nil)
  (foreach name names
    (setq key (degk--room-name-key name))
    (if (member key '("E_POWER_SUPPLY_100" "E_GUC_KAYNAGI_100"))
      (setq hit T)))
  hit
)

(defun degk--room-source-blocks (pickset / i ent ed obj powerEnt panelEnt)
  ;; Oda sembolleri yalniz kullanicinin alan secimine giren INSERT'lerden gelir.
  (setq i 0)
  (while (and pickset
              (< i (sslength pickset))
              (or (null powerEnt) (null panelEnt)))
    (setq ent (ssname pickset i)
          ed  (if ent (entget ent) nil)
          obj nil)
    (if (and ed (= (cdr (assoc 0 ed)) "INSERT"))
      (progn
        (setq obj (vl-catch-all-apply 'vlax-ename->vla-object (list ent)))
        (if (not (vl-catch-all-error-p obj))
          (cond
            ((and (null powerEnt) (degk--room-power-supply-p obj))
              (setq powerEnt ent))
            ((and (null panelEnt) (degk--room-fire-panel-p obj))
              (setq panelEnt ent))))))
    (setq i (1+ i)))
  (if (and powerEnt panelEnt)
    (list powerEnt panelEnt)
    nil)
)

(defun degk--flasher-terminal-module-p (blkObj / rec value key)
  (if (and (boundp '*degk-source-cache-active*) *degk-source-cache-active* blkObj)
    (setq key (vla-get-Name blkObj)))
  (if (and (boundp '*degk-source-cache-active*) *degk-source-cache-active*)
    (if (setq rec (assoc key *degk-terminal-type-cache*))
      (cdr rec)
      (progn
        (setq value (degk--flasher-terminal-module-uncached-p blkObj)
              *degk-terminal-type-cache* (cons (cons key value) *degk-terminal-type-cache*))
        value))
    (degk--flasher-terminal-module-uncached-p blkObj)))

(defun degk--source-block-eligible-p (blkObj / rec value key layer)
  (setq layer (strcase (vla-get-Layer blkObj)))
  (if (and (boundp '*degk-source-cache-active*) *degk-source-cache-active*)
    (setq key (list (vla-get-Name blkObj) layer)))
  (if (and (boundp '*degk-source-cache-active*) *degk-source-cache-active*
           (setq rec (assoc key *degk-source-eligible-cache*)))
    (cdr rec)
    (progn
      (setq value (and (/= layer "0")
                       (not (DEG:IGNORE-BLOCK-OBJ? blkObj))))
      (if (and (boundp '*degk-source-cache-active*) *degk-source-cache-active*)
        (setq *degk-source-eligible-cache* (cons (cons key value) *degk-source-eligible-cache*)))
      value)))

(defun degk--flasher-terminal-module-uncached-p (blkObj / names name hit)
  ;; Dinamik/anonim bloklarda yalniz EffectiveName yeterli olmayabilir.
  ;; Tum kullanilabilir adlari ve ad varyasyonlarini kontrol et.
  (setq names (if blkObj (DEG:BLOCK-NAMES blkObj) nil)
        hit nil)
  (foreach name names
    (if (or (deg-eq name "E_SOUNDER_MODULE_100")
            (deg-eq name "E_SIREN_KONTROL_MODÜL_100")
            (deg-eq name "E_SIREN_KONTROL_MODUL_100")
            (deg-wcmatch name "*SOUNDER*MODULE*")
            (deg-wcmatch name "*SIREN*KONTROL*MOD*"))
      (setq hit T))
  )
  hit
)

(defun degk--monitor-module-p (blkObj / names name hit)
  ;; Ingilizce ve Turkce monitor modul adlari; dinamik/anonim bloklarda
  ;; EffectiveName ile gercek block adi birlikte kontrol edilir.
  (setq names (if blkObj (DEG:BLOCK-NAMES blkObj) nil)
        hit nil)
  (foreach name names
    (if (or (deg-eq name "E_MONITOR_MODULE_100")
            (deg-eq name "E_MONÝTÖR_MODÜL_100")
            (deg-eq name "E_MONITOR_MODUL_100")
            (deg-wcmatch name "*MONITOR*MODULE*")
            (deg-wcmatch name "*MONÝTÖR*MODÜL*")
            (deg-wcmatch name "*MONITOR*MODUL*"))
      (setq hit T))
  )
  hit
)

(defun degk--column-anchor-module-p (blkObj)
  (or (degk--flasher-terminal-module-p blkObj)
      (degk--monitor-module-p blkObj))
)

(defun degk--point-in-bbox-tol-p (pt bb tol / mn mx)
  (if (not (numberp tol)) (setq tol 0.0))
  (setq tol (abs tol)
        mn  (if bb (car bb) nil)
        mx  (if bb (cadr bb) nil))
  (and (deg-pt3 pt)
       (deg-pt3 mn)
       (deg-pt3 mx)
       (>= (car pt) (- (car mn) tol))
       (<= (car pt) (+ (car mx) tol))
       (>= (cadr pt) (- (cadr mn) tol))
       (<= (cadr pt) (+ (cadr mx) tol)))
)

(defun degk--point-bbox-gap-2d (pt bb / mn mx x y cx cy)
  (setq mn (if bb (car bb) nil)
        mx (if bb (cadr bb) nil))
  (if (and (deg-pt3 pt) (deg-pt3 mn) (deg-pt3 mx))
    (progn
      (setq x  (car pt)
            y  (cadr pt)
            cx (max (car mn) (min x (car mx)))
            cy (max (cadr mn) (min y (cadr mx))))
      (distance (list x y 0.0) (list cx cy 0.0)))
    nil)
)

(defun degk--flasher-terminal-endpoint-score
  (plEnt blkObj tol / sharpTol bb sp ep gs ge endPt ins contact totalLen d)
  ;; Terminal seciminde ana olcut block base noktasi degil, hattin gercek
  ;; ucunun gorunen block alanina temasidir. Hat ortasindaki kesisim yalniz
  ;; daha dusuk oncelikli yedek olarak kabul edilir.
  (if (not (numberp tol)) (setq tol 0.0))
  (setq sharpTol
          (min (abs tol)
               (max 0.000001 (* 0.1 (DEG:PLAN-UNIT-SCALE))))
        bb (degk--get-bbox-visible-by-blockdef blkObj))
  (if (null bb) (setq bb (degk--ent-bbox blkObj)))
  (setq sp (vl-catch-all-apply 'vlax-curve-getStartPoint (list plEnt))
        ep (vl-catch-all-apply 'vlax-curve-getEndPoint (list plEnt)))
  (if (vl-catch-all-error-p sp) (setq sp nil))
  (if (vl-catch-all-error-p ep) (setq ep nil))
  (setq gs (if sp (degk--point-bbox-gap-2d sp bb) nil)
        ge (if ep (degk--point-bbox-gap-2d ep bb) nil))
  (cond
    ((and (numberp gs) (<= gs sharpTol)
          (or (not (numberp ge)) (<= gs ge)))
      (setq endPt sp))
    ((and (numberp ge) (<= ge sharpTol))
      (setq endPt ep)))
  (if endPt
    (progn
      ;; Birden fazla buyuk/ust uste bbox ayni ucu kapsarsa gercek INSERT'e
      ;; yakin olan kazanir; katsayi yalniz esitligi bozar.
      (setq ins (deg-get-inspt blkObj))
      (+ (min (if (numberp gs) gs 1.0e99)
              (if (numberp ge) ge 1.0e99))
         (if ins (* 1.0e-6 (distance endPt ins)) 0.0)))
    (progn
      (setq contact (degk--flasher-terminal-contact-point plEnt blkObj tol))
      (if contact
        (progn
          (setq totalLen
            (vl-catch-all-apply
              'vlax-curve-getDistAtParam
              (list plEnt (vlax-curve-getEndParam plEnt))))
          (if (vl-catch-all-error-p totalLen) (setq totalLen 0.0))
          (setq d (degk--dist-along plEnt contact))
          (if (not (numberp d)) (setq d 0.0))
          (+ 1.0e12 (min d (abs (- totalLen d)))))
        nil)))
)

(defun degk--flasher-terminal-contact-point
  (plEnt blkObj tol / plObj res lst handle bbRec bb sharpTol best sp ep)
  ;; Sounder/siren kontrol modullerinde base noktasi yerine planda gorunen
  ;; blok geometrisini kullan. Once gercek kesisim, sonra gorunen geometri
  ;; sinirinin toleransli temas kontrolu yapilir. Attribute/text extents'i
  ;; degk--get-bbox-visible-by-blockdef tarafindan hesaba katilmaz.
  (setq plObj
    (cond
      ((= (type plEnt) 'VLA-OBJECT) plEnt)
      ((= (type plEnt) 'ENAME)
        (setq res (vl-catch-all-apply 'vlax-ename->vla-object (list plEnt)))
        (if (vl-catch-all-error-p res) nil res))
      (T nil)))
  (if (not (numberp tol)) (setq tol 0.0))
  (setq tol (abs tol)
        ;; Yakin modullerin hattini karistirmamak icin bu ozel yedek
        ;; kontrolde fiziksel tolerans en fazla 1 mm'dir.
        sharpTol
          (min tol
               (max 0.000001 (* 0.1 (DEG:PLAN-UNIT-SCALE)))))

  ;; AutoCAD/GstarCAD destekliyorsa blok referansinin gercek cizgileriyle
  ;; dogrudan kesisim en kesin sonuc olur.
  (if (and plObj blkObj)
    (progn
      (setq res
        (vl-catch-all-apply
          'vlax-invoke
          (list plObj 'IntersectWith blkObj 0)))
      (if (not (vl-catch-all-error-p res))
        (progn
          (setq lst (vl-catch-all-apply 'DEG:PT->LIST (list res)))
          (if (and (not (vl-catch-all-error-p lst))
                   (listp lst)
                   (>= (length lst) 2))
            (setq best
              (list (nth 0 lst)
                    (nth 1 lst)
                    (if (and (>= (length lst) 3) (numberp (nth 2 lst)))
                      (nth 2 lst)
                      0.0)))))))
  )

  (if (and (null best) plObj blkObj)
    (progn
      (setq handle (degkk--object-handle blkObj)
            bbRec
              (if (and (/= handle "")
                       (boundp '*degk-flasher-contact-bbox-cache*))
                (assoc handle *degk-flasher-contact-bbox-cache*)
                nil)
            bb (if bbRec (cdr bbRec) nil))
      (if (null bb)
        (progn
          (setq bb (degk--get-bbox-visible-by-blockdef blkObj))
          (if (null bb) (setq bb (degk--ent-bbox blkObj)))
          (if (and bb (/= handle "")
                   (boundp '*degk-flasher-contact-bbox-cache*))
            (setq *degk-flasher-contact-bbox-cache*
              (cons (cons handle bb) *degk-flasher-contact-bbox-cache*)))))
      (if bb
        (progn
          ;; IntersectWith kullanilamiyorsa yalniz polyline'in gercek ucunu
          ;; kabul et. Hattin ortasinda kalan komsu modul artik temas sayilmaz.
          (setq sp (vl-catch-all-apply 'vlax-curve-getStartPoint (list plObj))
                ep (vl-catch-all-apply 'vlax-curve-getEndPoint (list plObj)))
          (cond
            ((and (not (vl-catch-all-error-p sp))
                  (degk--point-in-bbox-tol-p sp bb sharpTol))
              (setq best sp))
            ((and (not (vl-catch-all-error-p ep))
                  (degk--point-in-bbox-tol-p ep bb sharpTol))
              (setq best ep)))))))
  best
)

(defun degk--flasher-terminal-touches-loop-p (loopEnts blkObj tol / hit plEnt)
  ;; Genis blok-alani temasi yalniz flasor terminalini bulmak icindir.
  ;; Modulu genel loop cihaz listesine dahil etmez.
  (setq hit nil)
  (foreach plEnt loopEnts
    (if (and (not hit)
             plEnt
             (degk--curve-ok? plEnt)
             (degk--flasher-terminal-contact-point plEnt blkObj tol))
      (setq hit T))
  )
  hit
)

(defun degk--flasher-loop-layer-p (layer)
  (and layer
       (or (deg-eq layer "E_FLAÞÖR")
           (deg-eq layer "E_FLASOR")
           (deg-eq layer "E_FLASHER")
           (deg-eq layer "E_STROBE")
           (deg-eq layer "E_STROBE_LINE")
           (deg-wcmatch layer "*FLAÞ*")
           (deg-wcmatch layer "*FLAS*")
           (deg-wcmatch layer "*FLASH*")
           (deg-wcmatch layer "*STROBE*")))
 )

(defun degk--flasher-terminal-key (blkObj / names name key)
  ;; Anonymous/dynamic block adlarini ayni mantiksal modul anahtarinda topla.
  (setq names (if blkObj (DEG:BLOCK-NAMES blkObj) nil))
  (foreach name names
    (cond
      ((deg-wcmatch name "*SOUNDER*MODULE*")
        (setq key "SOUNDER_MODULE"))
      ((deg-wcmatch name "*SIREN*KONTROL*MOD*")
        (setq key "SIREN_KONTROL_MODULE")))
  )
  (if key key (degkk--symbol-key blkObj))
)

(defun degk--flasher-module-last (ordered / normal modules pair)
  ;; Kaynak hattin cizim yonu ne olursa olsun kontrol modulu loopun kapanan
  ;; ucunda kalir. Diger bloklarin kendi aralarindaki sirasi korunur.
  (foreach pair ordered
    (if (degk--flasher-terminal-module-p (cdr pair))
      (setq modules (cons pair modules))
      (setq normal (cons pair normal)))
  )
  (append (reverse normal) (reverse modules))
)

(defun degk--same-block-p (a b / ha hb)
  (setq ha (if a (degkk--object-handle a) "")
        hb (if b (degkk--object-handle b) ""))
  (and (/= ha "") (= ha hb))
)

(defun degk--column-terminal-copy-put
  (sourceObj copyObj anchorPt layoutRow layoutFloor / handle item itemObj itemHandle kept)
  ;; Kolon semasinda gercekten olusan terminal kopyalarini kaynak eslesmesinden
  ;; bagimsiz tut. Ayni INSERT farkli kaynaklara map edilse bile bir kez kaydolur.
  (if (and copyObj anchorPt (= (type copyObj) 'VLA-OBJECT))
    (progn
      (setq handle (strcase (degkk--object-handle copyObj)))
      (if (/= handle "")
        (progn
          (foreach item
            (if (boundp '*degk-column-terminal-copies*)
              *degk-column-terminal-copies*
              nil)
            (setq itemObj (car item)
                  itemHandle
                    (if (and itemObj (= (type itemObj) 'VLA-OBJECT))
                      (strcase (degkk--object-handle itemObj))
                      ""))
            (if (/= itemHandle handle)
              (setq kept (cons item kept))))
          (setq *degk-column-terminal-copies*
            (cons
              (list copyObj anchorPt layoutRow layoutFloor sourceObj)
              (reverse kept)))))))
  copyObj
)

(defun degk--area-module-copy-put (sourceObj copyObj anchorPt layoutRow layoutFloor / handle key sourceIns sourceSira)
  ;; Kaynak plandaki modul ile kolon semasindaki kopyasini eslestir.
  ;; DKK ayni sembolleri topladiginda sembol anahtari ikinci kaynak
  ;; modulun de ayni kopyaya baglanabilmesini saglar.
  (if (and sourceObj copyObj anchorPt
           (= (type copyObj) 'VLA-OBJECT))
    (progn
      (setq handle     (degkk--object-handle sourceObj)
            key        (degk--flasher-terminal-key sourceObj)
            sourceIns  (deg-get-inspt sourceObj)
            sourceSira (degk--clean-text (degk--get-att sourceObj "SIRA_NO")))
      (if (not (numberp layoutRow)) (setq layoutRow nil))
      (if (not (numberp layoutFloor)) (setq layoutFloor nil))
      ;; Monitor modulleri de kaynak-kopya haritasina girer; ancak flasor
      ;; looplarinin kullanabilecegi bos terminal havuzuna eklenmez.
      (if (or (degk--flasher-terminal-module-p sourceObj)
              (degk--flasher-terminal-module-p copyObj))
        (degk--column-terminal-copy-put
          sourceObj copyObj anchorPt layoutRow layoutFloor))
      (if (/= handle "")
        (setq *degk-area-module-copy-map*
          (cons (list handle copyObj anchorPt layoutRow layoutFloor)
                (if (boundp '*degk-area-module-copy-map*)
                  *degk-area-module-copy-map*
                  nil))))
      (if (/= key "")
        (setq *degk-area-module-symbol-map*
          (cons (list key copyObj anchorPt sourceIns sourceSira handle layoutRow layoutFloor)
                (if (boundp '*degk-area-module-symbol-map*)
                  *degk-area-module-symbol-map*
                  nil))))
    )
  )
  copyObj
)

(defun degk--area-module-copy-get (sourceObj wantedFloor / handle records item rec)
  ;; Ayni kaynak modul birden fazla katta kopyalanabilir. Kat biliniyorsa
  ;; baska kattaki en son kopyaya dusmek yerine yalniz ayni kati kabul et.
  (setq handle  (if sourceObj (degkk--object-handle sourceObj) "")
        records (if (boundp '*degk-area-module-copy-map*)
                  *degk-area-module-copy-map*
                  nil))
  (foreach item records
    (if (and (null rec)
             (= (car item) handle)
             (or (not (numberp wantedFloor))
                 (and (numberp (nth 4 item))
                      (= wantedFloor (nth 4 item)))))
       (setq rec item))
  )
  ;; Kat bilinmiyorsa fiziksel kaynak kimligiyle herhangi bir kopya yedek
  ;; olarak kullanilabilir. Kat biliniyorsa baska kattaki kopyaya gecme.
  (if (and (null rec) (not (numberp wantedFloor)))
    (foreach item records
      (if (and (null rec) (= (car item) handle))
        (setq rec item))))
  ;; Flasor loopu yalniz planda gercekten bagli oldugu kaynak modulun
  ;; kolon kopyasina gidebilir. Ayni tipteki baska bir module sembol/mesafe
  ;; ile dusmek iki farkli loopu tek kontrol modulunde birlestiriyordu.
  (if rec (cdr rec) nil)
)

(defun degk--area-module-symbol-get (sourceObj wantedFloor / key sourceIns sourceSira records rec candidateIns candidateSira candidateFloor score best bestScore)
  (setq key        (if sourceObj (degk--flasher-terminal-key sourceObj) "")
        sourceIns  (if sourceObj (deg-get-inspt sourceObj) nil)
        sourceSira (if sourceObj
                     (degk--clean-text (degk--get-att sourceObj "SIRA_NO"))
                     "")
        records    (if (boundp '*degk-area-module-symbol-map*)
                     *degk-area-module-symbol-map*
                     nil))
  (foreach rec records
    (setq candidateFloor (nth 7 rec))
    (if (and (= (car rec) key)
             (or (not (numberp wantedFloor))
                 (and (numberp candidateFloor)
                      (= wantedFloor candidateFloor))))
      (progn
        (setq candidateIns  (nth 3 rec)
              candidateSira (if (nth 4 rec) (nth 4 rec) "")
              score
                (cond
                  ((and (/= sourceSira "") (= sourceSira candidateSira)) 0.0)
                  ((and sourceIns candidateIns) (+ 1.0 (distance sourceIns candidateIns)))
                  (T 1.0e99)))
        (if (or (null bestScore) (< score bestScore))
          (setq best rec
                bestScore score))
      )
    )
  )
  (if best
    (list (nth 1 best) (nth 2 best) (nth 6 best) (nth 7 best))
    nil)
)

(defun degk--flasher-terminal-from-touched (plEnt touched tol / blkObj score best bestScore)
  ;; Birden fazla kontrol modulu varsa polyline ucuna gercekten temas edeni al.
  (foreach blkObj touched
    (if (degk--flasher-terminal-module-p blkObj)
      (progn
        (setq score
          (degk--flasher-terminal-endpoint-score plEnt blkObj tol))
        (if (and (numberp score)
                 (or (null bestScore) (< score bestScore)))
          (setq best blkObj
                bestScore score))
      )
    )
  )
  best
)

(defun degk--flasher-terminal-on-polyline (plEnt blockObjs tol / touched blkObj)
  ;; Yerlesim kati hesaplanmadan once flasor/strobe hattinin baglandigi
  ;; kontrol modulunu bul. DK:BASE ile ayni temas testini kullanir.
  (foreach blkObj blockObjs
    (if (and (degk--flasher-terminal-module-p blkObj)
             (degk--flasher-terminal-contact-point plEnt blkObj tol))
      (setq touched (cons blkObj touched))
    )
  )
  (if touched
    (degk--flasher-terminal-from-touched plEnt touched tol)
    nil
  )
)

(defun degk--block-first-layout-info (blkObj / siraList sira layout result)
  (setq siraList (degk--expand-sira-no (degk--get-att blkObj "SIRA_NO")))
  (if (null siraList)
    (setq siraList (list (degk--get-att blkObj "SIRA_NO"))))
  (while (and siraList (null result))
    (setq sira     (degk--clean-text (car siraList))
          siraList (cdr siraList)
          layout   (if (/= sira "") (degk--layout-key-from-sira sira) nil))
    (if layout (setq result (list sira layout)))
  )
  result
)

(defun degk--block-touches-selected-normal-p (blkObj polylines tol / i ent layer hit)
  ;; Yalniz secilen normal looplardan birinde kopyalanacak modul, flasor
  ;; yerlesimi icin gercek kolon hizasi ankraji olabilir.
  (setq i 0)
  (while (and polylines (< i (sslength polylines)) (not hit))
    (setq ent   (ssname polylines i)
          layer (if ent (cdr (assoc 8 (entget ent))) nil))
    (if (and ent
             layer
             (not (degk--flasher-loop-layer-p layer))
             ;; DK:BASE normal loopta modulu tam olarak bu base-noktasi
             ;; testiyle kopyalar. Ayni testi kullan ki atanmis modulun kolon
             ;; semasinda gercek bir kopyasi mutlaka bulunsun.
             (degk--block-touches-loop-p (list ent) blkObj tol))
      (setq hit T))
    (setq i (1+ i))
  )
  hit
)

(defun degk--flasher-terminal-fallback
  (plEnt blockObjs polylines tol sourceSira / sourceLayout sourceFloor blkObj info layout sameFloor copyable ins cp gap rank best bestRank bestGap)
  ;; Flasor polyline'i kontrol modulune fiziksel olarak degmiyorsa once ayni
  ;; katta ve secilen normal loopta kopyalanacak modulu, sonra en yakin uygun
  ;; modulu sec. Boylece hem kat hem de kolon semasindaki gercek hiza korunur.
  (setq sourceLayout (degk--layout-key-from-sira sourceSira)
        sourceFloor  (if sourceLayout (car sourceLayout) nil))
  (foreach blkObj blockObjs
    (if (degk--flasher-terminal-module-p blkObj)
      (progn
        (setq info       (degk--block-first-layout-info blkObj)
              layout     (if info (cadr info) nil)
              sameFloor  (and (numberp sourceFloor)
                              layout
                              (= sourceFloor (car layout)))
              copyable   (degk--block-touches-selected-normal-p
                           blkObj polylines tol)
              ins        (deg-get-inspt blkObj)
              cp         (if ins (deg-safe-closest-point plEnt ins) nil)
              gap        (if (and ins cp) (distance ins cp) 1.0e99)
              rank
                (cond
                  ((and sameFloor copyable) 0)
                  (copyable 1)
                  (sameFloor 2)
                  (T 3)))
        (if (or (null bestRank)
                (< rank bestRank)
                (and (= rank bestRank) (< gap bestGap)))
          (setq best     blkObj
                bestRank rank
                bestGap  gap))
      )
    )
  )
  best
)

(defun degk--records-flasher-last (records / normal flasher rec ent layer)
  ;; Once ana/yangin looplari kopyalanir; boylece flasor loopu kendi
  ;; kontrol modulunun kolon semasindaki gercek konumunu bulabilir.
  (foreach rec records
    (setq ent   (nth 4 rec)
          layer (if ent (cdr (assoc 8 (entget ent))) nil))
    (if (and layer (degk--flasher-loop-layer-p layer))
      (setq flasher (cons rec flasher))
      (setq normal (cons rec normal)))
  )
  (append (reverse normal) (reverse flasher))
)

(defun degk--layout-record-flasher-p (rec / ent layer)
  (setq ent   (nth 4 rec)
        layer (if ent (cdr (assoc 8 (entget ent))) nil))
  (and layer (degk--flasher-loop-layer-p layer))
)

(defun degk--flasher-record-copy-x (rec / sourceObj copyRec anchor p)
  ;; Terminal kopyalari normal looplar islenirken kaydedilir. Siralama,
  ;; plandaki kaynak konumdan degil kolon semasindaki gercek kopyadan yapilir.
  (setq sourceObj (nth 6 rec)
        copyRec   (if sourceObj
                    (degk--area-module-copy-get sourceObj (nth 1 rec))
                    nil)
        anchor    (if copyRec (cadr copyRec) nil))
  (if (and anchor (numberp (car anchor)) (numberp (cadr anchor)))
    (setq p (trans anchor 0 1))
    (if sourceObj
      (setq p (trans (deg-get-inspt sourceObj) 0 1))
    )
  )
  (if (and p (numberp (car p))) (car p) -1.0e99)
)

(defun degk--flasher-record-right-first-less-p (a b / floorA floorB xA xB indexA indexB)
  ;; Katlar kendi sirasini korur; ayni katta terminali daha sagda olan
  ;; ozel loop once islenir ve boylece yukariya en yakin baglanti seviyesini alir.
  (setq floorA (nth 1 a)
        floorB (nth 1 b)
        xA     (degk--flasher-record-copy-x a)
        xB     (degk--flasher-record-copy-x b)
        indexA (nth 3 a)
        indexB (nth 3 b))
  (cond
    ((/= floorA floorB) (< floorA floorB))
    ((> (abs (- xA xB)) 1e-6) (> xA xB))
    (T (< indexA indexB)))
)

(defun degk--sort-flasher-records-right-first (records /)
  (vl-sort records 'degk--flasher-record-right-first-less-p)
)

(defun degk--flasher-records-connected-first (records / connected openRecords rec sourceObj)
  ;; Once kolon kopyasi gercekten bulunan bagli looplari isle. Boylece daha
  ;; sonra gelen acik looplar yalniz gercekte bos kalan terminali kullanir.
  (foreach rec records
    (setq sourceObj (nth 6 rec))
    (if (and sourceObj
             (degk--area-module-copy-get sourceObj (nth 1 rec)))
      (setq connected (cons rec connected))
      (setq openRecords (cons rec openRecords))))
  (append (reverse connected) (reverse openRecords))
)

;; DKK: DK'nin kopyalama yollarinda ayni sembolleri tek blokta toplar.
(defun degkk--active-p ()
  (and (boundp '*DEG_DKK_MODE*) *DEG_DKK_MODE*)
)

(defun degkk--as-object (item / obj)
  (cond
    ((= (type item) 'VLA-OBJECT) item)
    ((= (type item) 'ENAME)
      (setq obj (vl-catch-all-apply 'vlax-ename->vla-object (list item)))
      (if (vl-catch-all-error-p obj) nil obj)
    )
    (T nil)
  )
)

(defun degkk--object-handle (blkObj / h)
  (setq h (if blkObj (vl-catch-all-apply 'vla-get-Handle (list blkObj)) nil))
  (if (or (null h) (vl-catch-all-error-p h)) "" h)
)

(defun degkk--symbol-key (item / obj n h)
  (setq obj (degkk--as-object item)
        n   (if obj (degk--blockname obj) nil)
        h   (if obj (degkk--object-handle obj) ""))
  (cond
    ((and n (/= n "")) (strcase n))
    ((/= h "") (strcat "#" h))
    (T "#UNKNOWN")
  )
)

(defun degkk--normal-group-key (blkObj / key handle)
  ;; DKK normal sembolleri ayni polyline icinde ozetlemeye devam eder.
  ;; Flasor terminal ve monitor modulleri fiziksel baglanti hedefidir; ayni
  ;; blok adina sahip olsalar bile kaynak INSERT handle'i ile ayrilmalidir.
  (setq key (degkk--symbol-key blkObj))
  (if (degk--column-anchor-module-p blkObj)
    (progn
      (setq handle (degkk--object-handle blkObj))
      (if (/= handle "")
        (setq key (strcat key "|ANCHOR|" handle))))
  )
  key
)

(defun degkk--unique-strings (items / out seen item key)
  (foreach item items
    (if (= (type item) 'STR)
      (progn
        (setq key (strcase item))
        (if (not (member key seen))
          (setq seen (cons key seen)
                out  (cons item out))
        )
      )
    )
  )
  (reverse out)
)

(defun degkk--prepare-items (items / counts groups unique seen item key rec)
  (setq counts nil groups nil unique nil seen nil)
  (foreach item items
    (setq key (degkk--symbol-key item))
    (if (setq rec (assoc key counts))
      (setq counts (subst (cons key (1+ (cdr rec))) rec counts))
      (setq counts (cons (cons key 1) counts))
    )
    (if (setq rec (assoc key groups))
      (setq groups (subst (cons key (append (cdr rec) (list item))) rec groups))
      (setq groups (cons (cons key (list item)) groups))
    )
    (if (not (member key seen))
      (setq seen   (cons key seen)
            unique (cons item unique))
    )
  )
  (setq *DEG_DKK_LIST_COUNTS* counts
        *DEG_DKK_LIST_GROUPS* groups)
  (reverse unique)
)

(defun degkk--item-count (item / rec)
  (setq rec (assoc (degkk--symbol-key item) *DEG_DKK_LIST_COUNTS*))
  (if rec (cdr rec) 1)
)

(defun degkk--group-items (item / rec)
  (setq rec (assoc (degkk--symbol-key item) *DEG_DKK_LIST_GROUPS*))
  (if rec (cdr rec) (list item))
)

(defun degkk--normal-token (blkObj siraOne / h)
  (setq h (degkk--object-handle blkObj))
  (strcat h "|" (degk--clean-text siraOne))
)

(defun degkk--normal-occurrence-state (blkObj siraOne / token key rec count pastedObj)
  (setq token (degkk--normal-token blkObj siraOne))
  (if (member token *DEG_DKK_SEEN_OCCURRENCES*)
    'SEEN
    (progn
      (setq *DEG_DKK_SEEN_OCCURRENCES* (cons token *DEG_DKK_SEEN_OCCURRENCES*)
            key (degkk--normal-group-key blkObj)
            rec (assoc key *DEG_DKK_GROUPS*))
      (if rec
        (progn
          (setq count (1+ (cadr rec))
                pastedObj (caddr rec))
          (setq *DEG_DKK_GROUPS*
            (subst (list key count pastedObj) rec *DEG_DKK_GROUPS*))
          (if pastedObj
            (degk--set-att pastedObj "ADET" (strcat "x" (itoa count)))
          )
          'DUPLICATE
        )
        'NEW
      )
    )
  )
)

(defun degkk--register-normal-copy (blkObj copyObj / key)
  (if (and copyObj (= (type copyObj) 'VLA-OBJECT))
    (progn
      (setq key (degkk--normal-group-key blkObj)
            *DEG_DKK_GROUPS* (cons (list key 1 copyObj) *DEG_DKK_GROUPS*))
      (degk--set-att copyObj "ADET" "x1")
    )
  )
  copyObj
)

(defun degk--attsync-add (blkObj /) nil)


(defun degk--attsync-run-one (blkName /) nil)


(defun degk--attsync-run ( /) nil)
;; ------------------------------------------------------------
;; DK: YENI YAPISTIRILAN BLOKLARDA ATTRIBUTE KONUMUNU
;; BLOK TANIMINDAKI ORJINAL KONUMA CEK (PLANI ETKILEMEZ)
;; ------------------------------------------------------------

(defun degk--assoc-put (code val lst / a)
  (if (setq a (assoc code lst))
    (subst (cons code val) a lst)
    (append lst (list (cons code val)))
  )
)

(defun degk--xf-pt (pt ip sx sy sz rot / x y z x1 y1 z1 c s xr yr)
  (setq x (car pt) y (cadr pt) z (if (caddr pt) (caddr pt) 0.0))
  (setq x1 (* x sx))
  (setq y1 (* y sy))
  (setq z1 (* z sz))
  (setq c (cos rot) s (sin rot))
  (setq xr (- (* x1 c) (* y1 s)))
  (setq yr (+ (* x1 s) (* y1 c)))
  (list (+ (car ip) xr) (+ (cadr ip) yr) (+ (if (caddr ip) (caddr ip) 0.0) z1))
)

(defun degk--block-attdef-map (blkName / btr e d tag map)
  (setq map nil)
  (if (and blkName (/= blkName ""))
    (progn
      (setq btr (tblobjname "BLOCK" blkName))
      (if btr
        (progn
          (setq e (entnext btr))
          (while (and e (/= (cdr (assoc 0 (entget e))) "ENDBLK"))
            (setq d (entget e))
            (if (= (cdr (assoc 0 d)) "ATTDEF")
              (progn
                (setq tag (cdr (assoc 2 d)))
                (if tag (setq map (cons (cons (strcase tag) d) map)))
              )
            )
            (setq e (entnext e))
          )
        )
      )
    )
  )
  map
)

(defun degk--reset-insert-attrs (insE / insD insObj blkName effName ip rot sx sy sz amap a ad tag def p10 p11 new10 new11)
  (if (and insE (= (type insE) 'ENAME))
    (progn
      (setq insD (entget insE))
      (if (= (cdr (assoc 0 insD)) "INSERT")
        (progn
          (setq blkName (cdr (assoc 2 insD)))
          (setq ip  (cdr (assoc 10 insD)))
          (setq rot (cdr (assoc 50 insD))) (if (null rot) (setq rot 0.0))
          (setq sx  (cdr (assoc 41 insD))) (if (null sx) (setq sx 1.0))
          (setq sy  (cdr (assoc 42 insD))) (if (null sy) (setq sy sx))
          (setq sz  (cdr (assoc 43 insD))) (if (null sz) (setq sz 1.0))
          (setq amap (degk--block-attdef-map blkName))
          (if (null amap)
            (progn
              (setq insObj (vl-catch-all-apply 'vlax-ename->vla-object (list insE)))
              (if (not (vl-catch-all-error-p insObj))
                (progn
                  (setq effName (degk--blockname insObj))
                  (if (and effName (/= effName blkName))
                    (setq amap (degk--block-attdef-map effName))
                  )
                )
              )
            )
          )
          (setq a (entnext insE))
          (while (and a (/= (cdr (assoc 0 (entget a))) "SEQEND"))
            (setq ad (entget a))
            (if (= (cdr (assoc 0 ad)) "ATTRIB")
              (progn
                (setq ad (degk--assoc-put 50 0.0 ad))
                (setq tag (cdr (assoc 2 ad)))
                (if (and tag amap)
                  (progn
                    (setq def (cdr (assoc (strcase tag) amap)))
                    (if def
                      (progn
                        (setq p10 (cdr (assoc 10 def)))
                        (setq p11 (cdr (assoc 11 def)))
                        (if p10
                          (progn
                            (setq new10 (degk--xf-pt p10 ip sx sy sz rot))
                            (setq ad (degk--assoc-put 10 new10 ad))
                          )
                        )
                        (if (and p11 (assoc 11 ad))
                          (progn
                            (setq new11 (degk--xf-pt p11 ip sx sy sz rot))
                            (setq ad (degk--assoc-put 11 new11 ad))
                          )
                        )
                      )
                    )
                  )
                )
                (entmod ad)
                (entupd a)
              )
            )
            (setq a (entnext a))
          )
        )
      )
    )
  )
  nil
)
(defun degk--pad (n width / s)
  (setq s (itoa n))
  (while (< (strlen s) width)
    (setq s (strcat "0" s))
  )
  s
)

(defun degk--digit-string-p (s / i ch len ok)
  (setq s (vl-string-trim " \t\r\n" (if s s "")))
  (setq len (strlen s) i 1 ok (> len 0))
  (while (and ok (<= i len))
    (setq ch (substr s i 1))
    (if (or (< (ascii ch) 48) (> (ascii ch) 57))
      (setq ok nil)
    )
    (setq i (1+ i))
  )
  ok
)

(defun degk--tail-prefix-number (s / i ch num len)
  (setq s (vl-string-trim " \t\r\n" (if s s "")))
  (setq len (strlen s) num "" i len)
  (while (and (> i 0)
              (setq ch (substr s i 1))
              (>= (ascii ch) 48) (<= (ascii ch) 57))
    (setq num (strcat ch num))
    (setq i (1- i))
  )
  (list (substr s 1 i) num)
)

(defun degk--expand-sira-no (s / pos leftPart rightPart i ch numL numR prefixL startN endN width res n len parts info)
  (if (or (null s) (= s "")) (setq s ""))
  (setq s (vl-string-trim " \t\r\n" s))
  (setq pos (vl-string-search ",...," s))
  (if (null pos)
    (progn
      (setq parts (degk--split-commas s))
      (if (> (length parts) 1)
        (progn
          (setq info (degk--tail-prefix-number (car parts)))
          (setq prefixL (car info)
                numL    (cadr info)
                width   (strlen numL))
          (mapcar
            '(lambda (p / q)
               (setq q (vl-string-trim " \t\r\n" (if p p "")))
               (if (and (> width 0) (/= prefixL "") (degk--digit-string-p q))
                 (strcat prefixL (degk--pad (atoi q) (max width (strlen q))))
                 q
               )
             )
            parts
          )
        )
        (list s)
      )
    )
    (progn
      (setq leftPart  (substr s 1 pos))
      (setq rightPart (substr s (+ pos 6)))

      (setq len (strlen leftPart) numL "" i len)
      (while (and (> i 0)
                  (setq ch (substr leftPart i 1))
                  (>= (ascii ch) 48) (<= (ascii ch) 57))
        (setq numL (strcat ch numL))
        (setq i (1- i))
      )
      (setq prefixL (substr leftPart 1 i))

      (setq len (strlen rightPart) numR "" i 1)
      (while (and (<= i len)
                  (setq ch (substr rightPart i 1))
                  (>= (ascii ch) 48) (<= (ascii ch) 57))
        (setq numR (strcat numR ch))
        (setq i (1+ i))
      )

      (if (and (> (strlen numL) 0) (> (strlen numR) 0))
        (progn
          (setq startN (atoi numL)
                endN   (atoi numR)
                width  (max (strlen numL) (strlen numR)))
          (if (> startN endN)
            (list s)
            (progn
              (setq res '() n startN)
              (while (<= n endN)
                (setq res (cons (strcat prefixL (degk--pad n width)) res))
                (setq n (1+ n))
              )
              (reverse res)
            )
          )
        )
        (list s)
      )
    )
  )
)

(defun degk--pt-eq? (p q eps /)
  (while (and (listp p) (= (length p) 1) (listp (car p)))
    (setq p (car p))
  )
  (while (and (listp q) (= (length q) 1) (listp (car q)))
    (setq q (car q))
  )
  (and (listp p) (listp q)
       (numberp (car p)) (numberp (cadr p))
       (numberp (car q)) (numberp (cadr q))
       (<= (abs (- (car p) (car q))) eps)
       (<= (abs (- (cadr p) (cadr q))) eps))
)

(defun degk--under-pts (basePt dx dy len1 len2 / p0 p1 p2 p3 p4 yOff fixedLen)
  (setq yOff    (DEG:CFG-DK-SIGNED-NUM-OR 'DK_UNDER_Y_OFFSET 0.0)
        fixedLen (* 90.0 (DEG:PLAN-UNIT-SCALE)))
  (setq basePt (list (car basePt) (+ (cadr basePt) yOff) 0.0))
  (setq p0 (list (car basePt) (- (cadr basePt) fixedLen) 0.0))
  (setq p1 (list (car p0) (+ (cadr p0) len1) 0.0)) ;; uc: Y = baseY - 20 cm
  (setq p2 (list (+ (car p1) dx) (- (cadr p1) dy) 0.0))
  (setq p3 (list (car p2) (- (cadr p2) len2) 0.0))
  (setq p4 (list (+ (car p3) fixedLen) (cadr p3) 0.0))
  (list p0 p1 p2 p3 p4)
)

(defun degk--drop-under-rail-pts (pts drop / i p z out)
  ;; p1 ve p2 blok tarafindaki dirsek uclaridir; sabit kalir.
  ;; p0, p3 ve p4 iki blok arasindaki ust yatay hatti olusturur.
  (setq i 0
        out nil
        drop (if (and (numberp drop) (> drop 0.0)) drop 0.0))
  (foreach p pts
    (setq z (if (and (caddr p) (numberp (caddr p))) (caddr p) 0.0))
    (if (and (> drop 0.0) (member i '(0 3 4)))
      (setq p (list (car p) (- (cadr p) drop) z))
    )
    (setq out (cons p out)
          i (1+ i))
  )
  (reverse out)
)

(defun degk--normal-group-left-extension (/)
  (* 400.0 (DEG:PLAN-UNIT-SCALE))
)

(defun degk--pts-x-bounds (pts / p minX maxX)
  (foreach p pts
    (if (and (listp p) (numberp (car p)))
      (progn
        (if (or (null minX) (< (car p) minX)) (setq minX (car p)))
        (if (or (null maxX) (> (car p) maxX)) (setq maxX (car p)))
      )
    )
  )
  (if (and minX maxX) (list minX maxX) nil)
)

(defun degk--pts-at-x (pts targetX eps / p out)
  (setq eps (if (and (numberp eps) (> eps 0.0)) eps 1e-6))
  (if (numberp targetX)
    (foreach p pts
      (if (and (listp p)
               (numberp (car p))
               (numberp (cadr p))
               (<= (abs (- (car p) targetX)) eps))
        (setq out (cons p out)))))
  (reverse out)
)

(defun degk--pts-min-y (pts / p minY)
  (foreach p pts
    (if (and (listp p) (numberp (cadr p)))
      (if (or (null minY) (< (cadr p) minY))
        (setq minY (cadr p))
      )
    )
  )
  minY
)

(defun degk--move-lowest-rail-to-y (pts targetY / minY p z out)
  ;; Yalniz en alttaki yatay ray dugumlerini yeni seviyeye indirir;
  ;; blok temas/dirsek noktalari yerinde kalir.
  (setq minY (degk--pts-min-y pts))
  (if (and (numberp minY) (numberp targetY))
    (progn
      (foreach p pts
        (if (and (listp p)
                 (numberp (cadr p))
                 (<= (abs (- (cadr p) minY)) 1e-6))
          (progn
            (setq z (if (and (caddr p) (numberp (caddr p)))
                      (caddr p)
                      0.0))
            (setq p (list (car p) targetY z))
          )
        )
        (setq out (cons p out))
      )
      (reverse out)
    )
    pts
  )
)

(defun degk--close-under-pts (pts gap / rest body p minX leftExt leftX firstPt firstZ endPt endX endY z)
  (setq gap (if (numberp gap) (abs gap) 0.0)
        leftExt (degk--normal-group-left-extension))
  ;; Son p4 noktasi yalnizca saga dogru cikinti olusturur. Onu atip
  ;; son dikey ucundan asagi inerek alt hatti ayni polyline'a ekle.
  (setq rest pts
        body nil)
  (while (and rest (cdr rest))
    (setq body (cons (car rest) body)
          rest (cdr rest))
  )
  (setq body (reverse body))
  (foreach p body
    (if (and (listp p) (numberp (car p)) (numberp (cadr p)))
      (if (or (null minX) (< (car p) minX)) (setq minX (car p)))
    )
  )
  ;; Iki acik ucu fiziksel olarak 400 cm sola uzat. Ust hatta mevcut
  ;; ilk dugumu tasimak yerine yeni yatay dugum ekle; boylece capraz olusmaz.
  (setq leftX
    (if (and minX (> leftExt 1e-9))
      (- minX leftExt)
      minX))
  (if (and body leftX (> leftExt 1e-9))
    (progn
      (setq firstPt (car body)
            firstZ (if (and (caddr firstPt) (numberp (caddr firstPt)))
                     (caddr firstPt)
                     0.0)
            body (cons (list leftX (cadr firstPt) firstZ) body))
    )
  )
  (setq endPt (if body (last body) nil))
  (if (and endPt minX (> gap 1e-9))
    (progn
      (setq endX (car endPt)
            endY (cadr endPt)
            z (if (and (caddr endPt) (numberp (caddr endPt))) (caddr endPt) 0.0))
      (append
        body
        (list
          (list endX (- endY gap) z)
          (list leftX (- endY gap) z)))
    )
    body
  )
)

(defun degk--trim-at-last-block-contact (pts / rev)
  ;; Son blok icin p1 temas noktasindan sonra gelen p2-p3-p4; asagi donus,
  ;; geri donen hat ve sag cikintidir. Bunlari atarak polyline'i blokta bitir.
  (if (and pts (> (length pts) 3))
    (progn
      (setq rev (reverse pts))
      (reverse (cdddr rev))
    )
    pts
  )
)

(defun degk--extend-under-rails-left (pts leftX / firstPt lastPt z rev)
  ;; Etiket konumu degismeden, ust ve alt yatay hattin sol ucunu
  ;; ayni kattaki ilk loopun sol uc hizasina getir.
  (if (and pts (cdr pts) (numberp leftX))
    (progn
      (setq firstPt (car pts)
            lastPt  (last pts))
      (if (and (listp firstPt) (listp lastPt))
        (progn
          (setq z (if (and (caddr firstPt) (numberp (caddr firstPt)))
                    (caddr firstPt)
                    0.0)
                pts (cons (list leftX (cadr firstPt) z) (cdr pts))
                rev (reverse pts)
                z (if (and (caddr lastPt) (numberp (caddr lastPt)))
                    (caddr lastPt)
                    0.0)
                rev (cons (list leftX (cadr lastPt) z) (cdr rev))
                pts (reverse rev))
        )
      )
    )
  )
  pts
)

(defun degk--loop-left-fillet-data
  (pts radius direction / n firstPt secondPt prevPt lastPt rightX z0 z1 firstTip firstTan lastTan lastTip rest body outPts outBulges i bulgeValue)
  ;; Iki paralel loop rayinin sol acik uclarini ayni LWPOLYLINE icinde
  ;; gercek 90 derece yaylarla GR katina dogru cevirir. Ust yay soldaki,
  ;; alt yay sagdaki kombine dik hatta baglanir.
  (setq n         (length pts)
        radius    (if (numberp radius) (abs radius) 0.0)
        direction (if (and (numberp direction) (> direction 0.0)) 1.0 -1.0))
  (if (and (>= n 4) (> radius 1e-9))
    (progn
      (setq firstPt  (car pts)
            secondPt (cadr pts)
            prevPt   (nth (- n 2) pts)
            lastPt   (last pts))
      (if (and
            (listp firstPt) (listp secondPt) (listp prevPt) (listp lastPt)
            (numberp (car firstPt))  (numberp (cadr firstPt))
            (numberp (car secondPt)) (numberp (cadr secondPt))
            (numberp (car prevPt))   (numberp (cadr prevPt))
            (numberp (car lastPt))   (numberp (cadr lastPt))
            (<= (abs (- (cadr firstPt) (cadr secondPt))) 1e-6)
            (<= (abs (- (cadr prevPt) (cadr lastPt))) 1e-6)
            (<= (abs (- (car firstPt) (car lastPt))) 1e-6)
            (>= (- (car secondPt) (car firstPt)) 0.0)
            (>= (- (car prevPt) (car lastPt)) radius))
        (progn
          (setq rightX (car firstPt)
                z0 (if (and (caddr firstPt) (numberp (caddr firstPt)))
                     (caddr firstPt) 0.0)
                z1 (if (and (caddr lastPt) (numberp (caddr lastPt)))
                     (caddr lastPt) 0.0)
                rest (cdr pts)
                body nil)
          (if (> direction 0.0)
            ;; GF altinda: ust loop sag, alt loop sol kombine hatta baglanir.
            (setq firstTip
                    (list rightX
                          (+ (cadr firstPt) radius)
                          z0)
                  firstTan
                    (list (+ rightX radius) (cadr firstPt) z0)
                  lastTan
                    (list rightX (cadr lastPt) z1)
                  lastTip
                    (list (- rightX radius)
                          (+ (cadr lastPt) radius)
                          z1))
            ;; GF ve ustunde: ust loop sol, alt loop sag kombine hatta baglanir.
            (setq firstTip
                    (list (- rightX radius)
                          (- (cadr firstPt) radius)
                          z0)
                  firstTan
                    (list rightX (cadr firstPt) z0)
                  lastTan
                    (list (+ rightX radius) (cadr lastPt) z1)
                  lastTip
                    (list rightX
                          (- (cadr lastPt) radius)
                          z1)))
          ;; Ilk ve son eski acik dugumleri at; aradaki tum loop geometrisi kalir.
          (while (and rest (cdr rest))
            (setq body (cons (car rest) body)
                  rest (cdr rest)))
          (setq body    (reverse body)
                outPts  (append (list firstTip firstTan) body (list lastTan lastTip))
                n       (length outPts)
                i       0
                outBulges nil
                bulgeValue 0.414213562373095)
          (while (< i n)
            (setq outBulges
              (cons
                (cond
                  ;; Yaylar dik hatta dikey, loop rayina yatay teget olur.
                  ((= i 0) (* direction bulgeValue))
                  ((= i (- n 2)) (* (- direction) bulgeValue))
                  (T 0.0))
                outBulges)
              i (1+ i)))
          ;; Ucuncu sonuc kombine dik hatlarin gercek temas noktalaridir;
          ;; dorduncu sonuc sonraki looplar icin ortak sag ankraj X'idir.
          (list outPts (reverse outBulges) (list firstTip lastTip) rightX)
        )
        nil)
    )
    nil)
)

(defun degk--loop-left-square-data
  (pts radius direction / n firstPt secondPt prevPt lastPt rightX z0 z1 firstTip firstTan firstCorner lastTan lastTip lastCorner rest body outPts outBulges i)
  ;; Ilk/son loopta yuvarlak fillet yerine ayni temas noktalarini koruyan
  ;; filletsiz 90 derece dirsek kurar. Boylece loop multiline ucuna gelir,
  ;; birleþik dik hat ise uzamaz.
  (setq n         (length pts)
        radius    (if (numberp radius) (abs radius) 0.0)
        direction (if (and (numberp direction) (> direction 0.0)) 1.0 -1.0))
  (if (and (>= n 4) (> radius 1e-9))
    (progn
      (setq firstPt  (car pts)
            secondPt (cadr pts)
            prevPt   (nth (- n 2) pts)
            lastPt   (last pts))
      (if (and
            (listp firstPt) (listp secondPt) (listp prevPt) (listp lastPt)
            (numberp (car firstPt))  (numberp (cadr firstPt))
            (numberp (car secondPt)) (numberp (cadr secondPt))
            (numberp (car prevPt))   (numberp (cadr prevPt))
            (numberp (car lastPt))   (numberp (cadr lastPt))
            (<= (abs (- (cadr firstPt) (cadr secondPt))) 1e-6)
            (<= (abs (- (cadr prevPt) (cadr lastPt))) 1e-6)
            (<= (abs (- (car firstPt) (car lastPt))) 1e-6)
            (>= (- (car secondPt) (car firstPt)) 0.0)
            (>= (- (car prevPt) (car lastPt)) radius))
        (progn
          (setq rightX (car firstPt)
                z0 (if (and (caddr firstPt) (numberp (caddr firstPt)))
                     (caddr firstPt) 0.0)
                z1 (if (and (caddr lastPt) (numberp (caddr lastPt)))
                     (caddr lastPt) 0.0)
                rest (cdr pts)
                body nil)
          (if (> direction 0.0)
            (setq firstTip (list rightX (+ (cadr firstPt) radius) z0)
                  firstTan (list (+ rightX radius) (cadr firstPt) z0)
                  lastTan  (list rightX (cadr lastPt) z1)
                  lastTip  (list (- rightX radius) (+ (cadr lastPt) radius) z1))
            (setq firstTip (list (- rightX radius) (- (cadr firstPt) radius) z0)
                  firstTan (list rightX (cadr firstPt) z0)
                  lastTan  (list (+ rightX radius) (cadr lastPt) z1)
                  lastTip  (list rightX (- (cadr lastPt) radius) z1)))
          (setq firstCorner (list (car firstTip) (cadr firstTan) z0)
                lastCorner  (list (car lastTip) (cadr lastTan) z1))
          (while (and rest (cdr rest))
            (setq body (cons (car rest) body)
                  rest (cdr rest)))
          (setq body   (reverse body)
                outPts (append
                         (list firstTip firstCorner firstTan)
                         body
                         (list lastTan lastCorner lastTip))
                i 0
                outBulges nil)
          (while (< i (length outPts))
            (setq outBulges (cons 0.0 outBulges)
                  i (1+ i)))
          (list outPts (reverse outBulges) (list firstTip lastTip) rightX))
        nil))
    nil)
)

(defun degk--loop-record-mouth-y (rec / pts firstPt lastPt)
  ;; Loopun diger geometrisinden etkilenmeden kombine dik hatta bakan iki
  ;; agiz ucunun orta Y degerini verir.
  (setq pts (cadr rec))
  (if (and (listp pts)
           (>= (length pts) 2)
           (setq firstPt (car pts))
           (setq lastPt (last pts))
           (listp firstPt) (listp lastPt)
           (numberp (cadr firstPt))
           (numberp (cadr lastPt)))
    (/ (+ (cadr firstPt) (cadr lastPt)) 2.0)
    nil)
)

(defun degk--nearest-point-by-x (pt targets / target score bestScore best)
  (if (and (listp pt) (numberp (car pt)))
    (foreach target targets
      (if (and (listp target) (numberp (car target)) (numberp (cadr target)))
        (progn
          (setq score (abs (- (car pt) (car target))))
          (if (or (null bestScore) (< score bestScore))
            (setq bestScore score best target))))))
  best
)

(defun degk--square-existing-loop-record
  (rec targetPoints / oldEnt pts layer color n firstTip lastTip firstTarget lastTarget middle rev firstTan lastTan z0 z1 firstCorner lastCorner newPts newBulges i beforeEnt afterEnt makeRes)
  ;; Once filletli cizilmis bir loopun yalniz iki agiz yayini kare 90 dereceye
  ;; cevirir ve uclarini verilen kombine dik hat noktalarina uzatir.
  (setq oldEnt (car rec)
        pts    (cadr rec)
        layer  (nth 3 rec)
        color  (nth 4 rec)
        n      (if (listp pts) (length pts) 0))
  (if (and oldEnt (entget oldEnt) (>= n 4))
    (progn
      (setq firstTip (car pts)
            lastTip  (last pts)
            firstTarget (degk--nearest-point-by-x firstTip targetPoints)
            lastTarget  (degk--nearest-point-by-x lastTip targetPoints)
            middle   (cdr pts)
            rev      (reverse middle)
            middle   (reverse (cdr rev))
            firstTan (car middle)
            lastTan  (last middle))
      (if (and (listp firstTip) (listp lastTip)
               (listp firstTan) (listp lastTan)
               (numberp (car firstTip)) (numberp (cadr firstTip))
               (numberp (car lastTip))  (numberp (cadr lastTip))
               (numberp (cadr firstTan)) (numberp (cadr lastTan)))
        (progn
          (setq z0 (if (and (caddr firstTip) (numberp (caddr firstTip)))
                     (caddr firstTip) 0.0)
                z1 (if (and (caddr lastTip) (numberp (caddr lastTip)))
                     (caddr lastTip) 0.0)
                firstTip
                  (if firstTarget
                    (list (car firstTarget) (cadr firstTarget) z0)
                    firstTip)
                lastTip
                  (if lastTarget
                    (list (car lastTarget) (cadr lastTarget) z1)
                    lastTip)
                firstCorner (list (car firstTip) (cadr firstTan) z0)
                lastCorner  (list (car lastTip) (cadr lastTan) z1)
                newPts      (append
                              (list firstTip firstCorner)
                              middle
                              (list lastCorner lastTip))
                newBulges nil
                i 0)
          (while (< i (length newPts))
            (setq newBulges (cons 0.0 newBulges)
                  i (1+ i)))
          (setq beforeEnt (entlast)
                makeRes
                  (degk--entmake-lwpoly-bulges
                    newPts (reverse newBulges) layer color)
                afterEnt (entlast))
          (if (and makeRes afterEnt (not (eq beforeEnt afterEnt)))
            (progn
              (entdel oldEnt)
              afterEnt)
            nil))
        nil))
    nil)
)

(defun degk--loop-record-replace-entity
  (records oldEnt newEnt / rec out)
  (foreach rec records
    (setq out
      (cons
        (if (and oldEnt newEnt (eq (car rec) oldEnt))
          (cons newEnt (cdr rec))
          rec)
        out)))
  (reverse out)
)

(defun degk--redraw-loop-record-direction
  (rec radius direction / oldEnt rawPts layer color filletData newPts newBulges beforeEnt makeRes newEnt)
  ;; Kayitli ham loop geometrisinden yalniz sol agiz filletlerini yeniden kur.
  ;; Blocklar, terminal ucu, layer ve renk aynen korunur.
  (setq oldEnt (car rec)
        rawPts (nth 5 rec)
        layer  (nth 3 rec)
        color  (nth 4 rec)
        filletData
          (if rawPts
            (degk--loop-left-fillet-data rawPts radius direction)
            nil))
  (if filletData
    (progn
      (setq newPts     (car filletData)
            newBulges (cadr filletData)
            beforeEnt (entlast)
            makeRes
              (degk--entmake-lwpoly-bulges
                newPts newBulges layer color)
            newEnt (entlast))
      (if (and makeRes newEnt (not (eq beforeEnt newEnt)))
        (progn
          (if (and oldEnt (entget oldEnt)) (entdel oldEnt))
          (list newEnt newPts newBulges layer color rawPts direction))
        rec))
    rec)
)

(defun degk--redraw-loop-records-direction
  (records radius direction / rec out)
  (foreach rec records
    (setq out
      (cons
        (degk--redraw-loop-record-direction rec radius direction)
        out)))
  (reverse out)
)

(defun degk--loop-record-point-groups (records / rec pts groups)
  ;; Birlesik dik hat icin her loopun iki gercek fillet agzini dondurur.
  (foreach rec records
    (setq pts (cadr rec))
    (if (and (listp pts) (>= (length pts) 2))
      (setq groups (cons (list (car pts) (last pts)) groups))))
  (reverse groups)
)

(defun degk--delete-entity-list (entities / ent)
  (foreach ent entities
    (if (and ent (entget ent)) (entdel ent)))
  T
)

(defun degk--shift-lwpoly-x
  (ent delta mode / ed item vertexCount arcP bendCount vertexIndex pt moveP out result)
  ;; ALL tum dik hatti tasir. MOUTHS ise loop govdesini sabit tutup fillet/kare
  ;; dirsek ile uc noktalarini birlikte kaydirarak yatay kollari stretch eder.
  (setq ed (if (and ent (entget ent)) (entget ent) nil))
  (if (and ed
           (= (cdr (assoc 0 ed)) "LWPOLYLINE")
           (numberp delta))
    (progn
      (setq vertexCount 0
            arcP nil)
      (foreach item ed
        (if (= (car item) 10)
          (setq vertexCount (1+ vertexCount)))
        (if (and (= (car item) 42)
                 (numberp (cdr item))
                 (> (abs (cdr item)) 1e-9))
          (setq arcP T)))
      (setq bendCount (if arcP 2 3)
            vertexIndex 0
            out nil)
      (foreach item ed
        (if (= (car item) 10)
          (progn
            (setq pt (cdr item)
                  moveP
                    (or (= mode 'ALL)
                        (and (= mode 'MOUTHS)
                             (or (< vertexIndex bendCount)
                                 (>= vertexIndex (- vertexCount bendCount))))))
            (if (and moveP (listp pt) (numberp (car pt)))
              (setq item
                (cons 10
                  (cons (+ (car pt) delta) (cdr pt)))))
            (setq vertexIndex (1+ vertexIndex))))
        (setq out (cons item out)))
      (setq result (entmod (reverse out)))
      (if result
        (progn (entupd ent) T)
        nil))
    nil)
)

(defun degk--stretch-single-loop-to-panel
  (loopRecords riserLimits panelCenterX
   / rec ent leftPt rightPt currentCenter delta originalData)
  ;; Tek GF loopunun yalniz agiz/fillet bolgesini FAP merkezine stretch eder.
  ;; Sonuc: entity, eski DXF, delta, yeni sol/sag X ve iki agiz Y degeri.
  (setq rec (if (= (length loopRecords) 1) (car loopRecords) nil)
        ent (if (listp rec) (car rec) nil)
        leftPt
          (if (and (listp riserLimits) (>= (length riserLimits) 2))
            (nth 0 riserLimits)
            nil)
        rightPt
          (if (and (listp riserLimits) (>= (length riserLimits) 2))
            (nth 1 riserLimits)
            nil))
  (if (and ent (entget ent)
           (numberp panelCenterX)
           (listp leftPt) (listp rightPt)
           (numberp (car leftPt)) (numberp (cadr leftPt))
           (numberp (car rightPt)) (numberp (cadr rightPt)))
    (progn
      (setq currentCenter (/ (+ (car leftPt) (car rightPt)) 2.0)
            delta (- panelCenterX currentCenter)
            originalData (entget ent))
      (if (degk--shift-lwpoly-x ent delta 'MOUTHS)
        (list ent originalData delta
              (+ (car leftPt) delta)
              (+ (car rightPt) delta)
              (cadr leftPt)
              (cadr rightPt))
        nil))
    nil)
)

(defun degk--center-main-riser-in-shaft
  (loopRecords riserLimits riserEntities targetCenterX
   / leftX rightX currentCenter delta tasks rec ent task originals ok)
  ;; Katlar arasi cift kombine hatti saft merkezine al; ona baglanan looplarin
  ;; yalniz sol fillet/dirsek bolumlerini ayni miktarda stretch et.
  (if (and (numberp targetCenterX)
           (listp riserLimits)
           (>= (length riserLimits) 2)
           (numberp (car (nth 0 riserLimits)))
           (numberp (car (nth 1 riserLimits))))
    (progn
      (setq leftX (car (nth 0 riserLimits))
            rightX (car (nth 1 riserLimits))
            currentCenter (/ (+ leftX rightX) 2.0)
            delta (- targetCenterX currentCenter)
            tasks nil)
      (foreach rec loopRecords
        (if (and (listp rec)
                 (setq ent (car rec))
                 (entget ent))
          (setq tasks (cons (list ent 'MOUTHS) tasks))))
      (foreach ent riserEntities
        (if (and ent (entget ent))
          (setq tasks (cons (list ent 'ALL) tasks))))
      (if tasks
        (if (<= (abs delta) 1e-9)
          T
          (progn
            (setq originals nil
                  ok T)
            (foreach task tasks
              (if (not (assoc (car task) originals))
                (setq originals
                  (cons (cons (car task) (entget (car task))) originals))))
            (foreach task tasks
              (if (not (degk--shift-lwpoly-x
                         (car task) delta (cadr task)))
                (setq ok nil)))
            (if (not ok)
              (foreach task originals
                (if (entmod (cdr task)) (entupd (car task)))))
            ok))
        nil))
    nil)
)

(defun degk--first-entity-layer (entities / ent ed layer)
  (foreach ent entities
    (if (and (null layer)
             ent
             (setq ed (entget ent))
             (assoc 8 ed))
      (setq layer (cdr (assoc 8 ed)))))
  layer
)

(defun degk--rebuild-gf-down-riser
  (layer riserLimits loopRecords riserEntities / filletRadius newLoopRecords newLoopPointGroups newRiserLimits newRiserEntities)
  ;; GF-asagi ozel geometrisini tek adimda kur. Cagiran bu fonksiyonu
  ;; vl-catch-all ile calistirir; hata olursa eski riser limitleri kullanilir.
  (setq filletRadius
    (abs
      (- (car (nth 1 riserLimits))
         (car (nth 0 riserLimits)))))
  (if (<= filletRadius 1e-9)
    (setq filletRadius
      (abs (DEG:CFG-DK-NUM-OR 'DK_UNDER_X2 10.0))))
  (setq newLoopRecords
          (degk--redraw-loop-records-direction
            loopRecords filletRadius 1.0)
        newLoopPointGroups
          (degk--loop-record-point-groups newLoopRecords)
        *degk-last-combined-riser-limits* nil
        *degk-last-combined-riser-entities* nil)
  (if (and newLoopPointGroups
           (degk--draw-combined-riser
             layer newLoopPointGroups
             (if (<= (length newLoopPointGroups) 2) 'GF 'ALL)))
    (progn
      (setq newRiserLimits *degk-last-combined-riser-limits*
            newRiserEntities *degk-last-combined-riser-entities*)
      (if (and newRiserLimits
               (or newRiserEntities
                   (<= (length newLoopPointGroups) 2)))
        (progn
          (degk--delete-entity-list riserEntities)
          (if (> (length newLoopRecords) 1)
            (setq newLoopRecords
              (degk--square-outer-loop-records
                newLoopRecords newRiserLimits nil)))
          (list newRiserLimits newLoopRecords newRiserEntities))
        nil))
    nil)
)

(defun degk--square-outer-loop-records
  (records riserLimits squareTopP / rec y bottomRec bottomY topRec topY bottomTargets topTargets bottomEnt topEnt updatedRecords)
  ;; Isleme sirasina bakmaz. Kombine dik hattin disinda kalan geometrik en alt
  ;; loopu kare yapar. squareTopP dogruysa en ust loop da kare olur; aradaki
  ;; multiline'a bagli looplar filletli kalir.
  (setq updatedRecords records)
  (foreach rec records
    (setq y (degk--loop-record-mouth-y rec))
    (if (numberp y)
      (progn
        (if (or (null bottomY) (< y bottomY))
          (setq bottomY y bottomRec rec))
        (if (or (null topY) (> y topY))
          (setq topY y topRec rec)))))
  (if (and (listp riserLimits) (>= (length riserLimits) 4))
    (setq bottomTargets (list (nth 0 riserLimits) (nth 1 riserLimits))
          topTargets    (list (nth 2 riserLimits) (nth 3 riserLimits))))
  (if bottomRec
    (setq bottomEnt
      (degk--square-existing-loop-record bottomRec bottomTargets)))
  (if bottomEnt
    (setq updatedRecords
      (degk--loop-record-replace-entity
        updatedRecords (car bottomRec) bottomEnt)))
  (if (and squareTopP
           topRec
           (not (eq (car topRec) (car bottomRec))))
    (setq topEnt
      (degk--square-existing-loop-record topRec topTargets)))
  (if topEnt
    (setq updatedRecords
      (degk--loop-record-replace-entity
        updatedRecords (car topRec) topEnt)))
  updatedRecords
)

(defun degk--base-for-loop-open-anchor (anchorPt loopDrop / probe closed firstPt z)
  ;; DK'nin mevcut alt-hat geometrisini sifir noktasinda kurup acik ust ucun
  ;; konumunu olcer. Boylece flasor loopu, ofset ve kat dusurme ayarlari
  ;; degisse bile kaynak modulun temas noktasina tam olarak tasinir.
  (if (and anchorPt (numberp (car anchorPt)) (numberp (cadr anchorPt)))
    (progn
      (setq probe
        (degk--drop-under-rail-pts
          (degk--under-pts
            '(0.0 0.0 0.0)
            (DEG:CFG-DK-NUM-OR 'DK_UNDER_X1 10.0)
            (DEG:CFG-DK-NUM-OR 'DK_UNDER_X2 10.0)
            (DEG:CFG-DK-NUM-OR 'DK_UNDER_W 70.0)
            (DEG:CFG-DK-NUM-OR 'DK_UNDER_H 60.0))
          loopDrop)
        closed
          (degk--close-under-pts
            probe
            (DEG:CFG-DK-NUM-OR 'DK_UNDER_X2 10.0))
        firstPt (car closed)
        z (if (and (caddr anchorPt) (numberp (caddr anchorPt)))
            (caddr anchorPt)
            0.0))
      (if firstPt
        (list (- (car anchorPt) (car firstPt))
              (- (cadr anchorPt) (cadr firstPt))
              z)
        nil)
    )
    nil
  )
)

(defun degk--append-unique-point (pts pt eps / lastPt)
  (setq lastPt (if pts (car (last pts)) nil))
  (if (and lastPt (degk--pt-eq? lastPt pt eps))
    pts
    (append pts (list pt))
  )
)

(defun degk--prepend-flasher-module-link (pts anchorPt linkY / firstPt z rightOffset shiftedPt dropPt turnPt link)
  ;; Polyline modul base hizasinin 200 mm saginda baslar ve oradan looplarin
  ;; en alt hattinin altindaki ortak seviyeye dik iner. Base noktasindan
  ;; baslangica yatay bir parca cizilmez.
  (if (and pts
           anchorPt
           (numberp (car anchorPt))
           (numberp (cadr anchorPt))
           (numberp linkY))
    (progn
      (setq firstPt (car pts)
            z (if (and (caddr anchorPt) (numberp (caddr anchorPt)))
                (caddr anchorPt)
                0.0)
            ;; PLAN ayar tabani cm'dir: 20 cm = 200 mm.
            rightOffset (* 20.0 (DEG:PLAN-UNIT-SCALE))
            shiftedPt (list (+ (car anchorPt) rightOffset)
                            (cadr anchorPt)
                            z)
            dropPt (list (car shiftedPt) linkY z)
            turnPt
              (list
                (car firstPt)
                (cadr dropPt)
                (if (and (caddr firstPt) (numberp (caddr firstPt)))
                  (caddr firstPt)
                  z))
            link nil)
      (setq link (degk--append-unique-point link shiftedPt 1e-6))
      (setq link (degk--append-unique-point link dropPt 1e-6))
      (setq link (degk--append-unique-point link turnPt 1e-6))
      (setq link (degk--append-unique-point link firstPt 1e-6))
      (append link (cdr pts))
    )
    pts
  )
)

(defun degk--loop-name-from-sira (s / pos next)
  (setq s (degk--clean-text (if s s ""))
        pos nil
        next (vl-string-search "-" s))
  (while next
    (setq pos next
          next (vl-string-search "-" s (1+ next)))
  )
  (if (and pos (> pos 0))
    (vl-string-trim " \t\r\n" (substr s 1 pos))
    s)
)

(defun degk--select-last-panel-name (/ sel obj objName txt done)
  (setq txt ""
        done nil)
  (while (not done)
    (setq sel
      (entsel
        "\nDK: Son panel adi icin TEXT secin veya bos birakmak icin Enter: "))
    (if (null sel)
      (setq done T)
      (progn
        (setq obj (vl-catch-all-apply 'vlax-ename->vla-object (list (car sel))))
        (if (vl-catch-all-error-p obj)
          (princ "\nDK: Secilen nesne okunamadi; TEXT secin veya Enter'a basin.")
          (progn
            (setq objName (vl-catch-all-apply 'vla-get-ObjectName (list obj)))
            (if (and (not (vl-catch-all-error-p objName))
                     (member objName '("AcDbText" "AcDbMText")))
              (progn
                (setq txt (degk--clean-text (get-entity-text obj)))
                (if (/= txt "")
                  (setq done T)
                  (princ "\nDK: Secilen TEXT bos; baska TEXT secin veya Enter'a basin.")))
              (princ "\nDK: Secilen nesne TEXT degil; TEXT secin veya Enter'a basin."))
          )
        )
      )
    )
  )
  txt
)

(defun degk--loop-label-with-panel (loopName / panelName)
  (setq loopName
    (degk--clean-text (if loopName loopName "")))
  (setq panelName
    (if (and (boundp '*degk-last-panel-name*)
             (= (type *degk-last-panel-name*) 'STR))
      (vl-string-right-trim " -\t\r\n" *degk-last-panel-name*)
      ""))
  (cond
    ((= panelName "") loopName)
    ((= loopName "") panelName)
    (T (strcat panelName "-" loopName)))
)

(defun degk--split-hyphens (s / txt pos part out)
  (setq txt (degk--clean-text (if s s ""))
        out nil)
  (while (setq pos (vl-string-search "-" txt))
    (setq part (vl-string-trim " \t\r\n" (substr txt 1 pos))
          out  (cons part out)
          txt  (substr txt (+ pos 2)))
  )
  (reverse (cons (vl-string-trim " \t\r\n" txt) out))
)

(defun degk--token-first-number (s / i len ch code digits started done)
  (setq s       (degk--clean-text (if s s ""))
        i       1
        len     (strlen s)
        digits  ""
        started nil
        done    nil)
  (while (and (<= i len) (not done))
    (setq ch   (substr s i 1)
          code (ascii ch))
    (cond
      ((and (>= code 48) (<= code 57))
        (setq digits  (strcat digits ch)
              started T))
      (started
        (setq done T))
    )
    (setq i (1+ i))
  )
  (if (/= digits "") (atoi digits) nil)
)

(defun degk--roof-floor-p (floorNo)
  (and (numberp floorNo) (= floorNo 999999))
)

(defun degk--floor-token-number (s / token n firstCh lastCh)
  ;; Katlari tek bir sayisal eksende tut: 01=1, GF/ZK=0, BF/B01/1B=-1.
  ;; RF/CK daha sonra secimdeki en yuksek normal katin hemen ustune indirilir.
  (setq token (strcase (vl-string-trim " \t\r\n" (degk--clean-text (if s s "")))))
  (cond
    ((member token '("RF" "ÇK" "CK" "ROOF" "ROOF FLOOR" "ÇATI" "CATI" "ÇATI KATI" "CATI KATI")) 999999)
    ((member token '("GR" "GF" "ZK" "GROUND" "GROUND FLOOR" "ZEMIN" "ZEMÝN" "ZEMIN KAT" "ZEMÝN KAT")) 0)
    ((member token '("BF" "B.F." "BK" "B.K." "BASEMENT" "BASEMENT FLOOR" "BODRUM" "BODRUM KAT")) -1)
    ((or (wcmatch token "*BASEMENT*")
         (wcmatch token "*BODRUM*"))
      (setq n (degk--token-first-number token))
      (if (numberp n) (- (abs n)) -1))
    (T
      (setq n (degk--token-first-number token))
      (if (numberp n)
        (progn
          (setq firstCh (if (> (strlen token) 0) (substr token 1 1) "")
                lastCh  (if (> (strlen token) 0) (substr token (strlen token) 1) ""))
          (if (or (= firstCh "B") (= lastCh "B"))
            (- (abs n))
            n))
        nil)))
)

(defun degk--split-layout-path (s / txt pos part out)
  ;; Eski projelerde kat/loop bolumu '/' ile, yenilerde '-' ile ayrilabiliyor.
  (setq txt (degk--clean-text (if s s ""))
        out nil)
  (while (setq pos (vl-string-search "/" txt))
    (setq part (vl-string-trim " \t\r\n" (substr txt 1 pos))
          out  (cons part out)
          txt  (substr txt (+ pos 2))))
  (reverse (cons (vl-string-trim " \t\r\n" txt) out))
)

(defun degk--panel-path-layout (s / path parts token floorNo orderNo title)
  ;; FAP/panel-kati/panel-no/kat-loop[-cihaz] icin son bolum esastir.
  (setq path (degk--split-layout-path s))
  (if (>= (length path) 4)
    (progn
      (setq parts (degk--split-hyphens (last path))
            token (car parts)
            floorNo (degk--floor-token-number token)
            orderNo (if (cdr parts) (degk--token-first-number (cadr parts)) nil))
      (if (and (>= (length parts) 2) (numberp floorNo) (numberp orderNo))
        (progn
          (setq title (if (> (length parts) 2)
                        (degk--loop-name-from-sira s)
                        (degk--clean-text s)))
          (list floorNo orderNo title token))))))

(defun degk--layout-key-from-sira (s / title parts partCount floorNo orderNo pathParts pathCount panelLayout)
  ;; SIRA_NO sagdan okunur: son '-' oncesi loop, sondan ikinci '-' oncesi kattir.
  ;; En sondaki parca ust baslikta oldugu gibi yerlesim hesabina katilmaz.
  (setq title     (degk--loop-name-from-sira s)
        parts     (degk--split-hyphens s)
        partCount (length parts))
  (if (>= partCount 3)
    (setq floorNo (degk--floor-token-number (nth (- partCount 3) parts))
          orderNo (degk--token-first-number (nth (- partCount 2) parts))))
  ;; SM/GF/02-03 gibi yalniz cihaz sirasinda '-' kullanan eski bicim.
  (if (or (not (numberp floorNo)) (not (numberp orderNo)))
    (progn
      (setq pathParts (degk--split-layout-path title)
            pathCount (length pathParts))
      (if (>= pathCount 2)
        (setq floorNo (degk--floor-token-number (nth (- pathCount 2) pathParts))
              orderNo (degk--token-first-number (nth (1- pathCount) pathParts))))))
  (if (setq panelLayout (degk--panel-path-layout s))
    (setq floorNo (car panelLayout) orderNo (cadr panelLayout) title (caddr panelLayout)))
  (if (and (numberp floorNo) (numberp orderNo))
    (list floorNo orderNo title)
    nil)
)

(defun degk--floor-label-from-sira (s / clean title parts partCount token orderNo pathParts pathCount panelLayout)
  ;; Yerlesim hesabinda kullanilan kat parcasini yazildigi bicimiyle koru.
  ;; Ornekler: SM-GF-L03-01 -> GF, L02-L09-01 -> L02,
  ;; SM/GF/02-03 -> GF.
  (setq clean     (degk--clean-text (if s s ""))
        title     (degk--loop-name-from-sira clean)
        parts     (degk--split-hyphens clean)
        partCount (length parts))
  (if (>= partCount 3)
    (progn
      (setq token   (nth (- partCount 3) parts)
            orderNo (degk--token-first-number (nth (- partCount 2) parts)))
      (if (or (not (numberp (degk--floor-token-number token)))
              (not (numberp orderNo)))
        (setq token nil))))
  (if (null token)
    (progn
      (setq pathParts (degk--split-layout-path title)
            pathCount (length pathParts))
      (if (>= pathCount 2)
        (setq token   (nth (- pathCount 2) pathParts)
              orderNo (degk--token-first-number (nth (1- pathCount) pathParts))))
      (if (or (null token)
              (not (numberp (degk--floor-token-number token)))
              (not (numberp orderNo)))
        (setq token nil))))
  (if (setq panelLayout (degk--panel-path-layout s))
    (setq token (nth 3 panelLayout)))
  (degk--clean-text (if token token ""))
)

(defun degk--default-floor-label (floorNo)
  (cond
    ((not (numberp floorNo)) "")
    ((= floorNo 0) "GF")
    ((= floorNo -1) "BF")
    ((< floorNo -1) (strcat "B" (degk--pad (abs floorNo) 2)))
    (T (strcat "L" (degk--pad floorNo 2))))
)

(defun degk--english-ordinal (n / value mod100 mod10 suffix)
  (setq value  (abs (fix n))
        mod100 (rem value 100)
        mod10  (rem value 10)
        suffix
          (cond
            ((member mod100 '(11 12 13)) "TH")
            ((= mod10 1) "ST")
            ((= mod10 2) "ND")
            ((= mod10 3) "RD")
            (T "TH")))
  (strcat (itoa value) suffix)
)

(defun degk--expanded-floor-label
  (label floorNo / token n firstCh lastCh turkishBasementP turkishFloorP)
  ;; Kaynak kat kodunun dilini koruyarak dikey kat isimligini tam ada cevir.
  (setq token   (strcase (vl-string-trim " \t\r\n" (degk--clean-text (if label label ""))))
        n       (degk--token-first-number token)
        firstCh (if (> (strlen token) 0) (substr token 1 1) "")
        lastCh  (if (> (strlen token) 0) (substr token (strlen token) 1) "")
        turkishBasementP
          (or (wcmatch token "BK*,*BK,*BODRUM*")
              (and (= firstCh "B") (= lastCh "K")))
        turkishFloorP
          (or (= firstCh "K")
              (= lastCh "K")
              (wcmatch token "* KAT*")))
  (cond
    ((member token '("ÇK" "CK" "ÇATI" "CATI" "ÇATI KATI" "CATI KATI"))
      "ÇATI KATI")
    ((member token '("RF" "ROOF" "ROOF FLOOR"))
      "ROOF FLOOR")
    ((member token '("ZK" "ZEMIN" "ZEMÝN" "ZEMIN KAT" "ZEMÝN KAT"))
      "ZEMÝN KAT")
    ((member token '("GF" "GR" "GROUND" "GROUND FLOOR"))
      "GROUND FLOOR")
    ((member token '("BK" "B.K." "BODRUM" "BODRUM KAT"))
      "BODRUM KAT")
    ((member token '("BF" "B.F." "BASEMENT" "BASEMENT FLOOR"))
      "BASEMENT FLOOR")
    ((and turkishBasementP (numberp n))
      (strcat (itoa (abs n)) ". BODRUM KAT"))
    ((and (or (= firstCh "B") (= lastCh "B")
              (wcmatch token "*BASEMENT*"))
          (numberp n))
      (strcat (degk--english-ordinal n) " BASEMENT FLOOR"))
    ((and turkishFloorP (numberp n))
      (strcat (itoa (abs n)) ". KAT"))
    ((numberp n)
      (strcat (degk--english-ordinal n) " FLOOR"))
    ((and (numberp floorNo) (= floorNo 999999)) "ROOF FLOOR")
    ((and (numberp floorNo) (= floorNo 0)) "GROUND FLOOR")
    ((and (numberp floorNo) (< floorNo 0))
      (strcat (degk--english-ordinal (abs floorNo)) " BASEMENT FLOOR"))
    ((and (numberp floorNo) (> floorNo 0))
      (strcat (degk--english-ordinal floorNo) " FLOOR"))
    (T token))
)

(defun degk--polyline-first-sira (plEnt blockObjs tol excludeObj / touched blkObj totalLen useFromStart ordered ins dist key pair sira siraList result)
  ;; DK:BASE ile ayni hat yonu ve blok sirasi kullanilarak ust baslik bulunur.
  (foreach blkObj blockObjs
    (if (and (degk--poly-touch-insertion? plEnt blkObj tol)
             (or (null excludeObj)
                 (not (degk--same-block-p blkObj excludeObj))))
      (setq touched (cons blkObj touched)))
  )
  (if touched
    (progn
      (setq totalLen (vlax-curve-getDistAtParam plEnt (vlax-curve-getEndParam plEnt))
            useFromStart (degk--use-from-lower-sira-side plEnt touched totalLen)
            ordered nil)
      (foreach blkObj touched
        (setq ins  (deg-get-inspt blkObj)
              dist (degk--dist-along plEnt ins)
              key  (if useFromStart dist (- totalLen dist))
              ordered (cons (cons key blkObj) ordered)))
      (setq ordered (vl-sort ordered '(lambda (a b) (< (car a) (car b)))))
      (while (and ordered (null result))
        (setq pair     (car ordered)
              blkObj  (cdr pair)
              sira    (degk--get-att blkObj "SIRA_NO")
              siraList (degk--expand-sira-no sira))
        (if (null siraList) (setq siraList (list sira)))
        (while (and siraList (null result))
          (setq sira (degk--clean-text (car siraList))
                siraList (cdr siraList))
          (if (/= sira "") (setq result sira)))
        (setq ordered (cdr ordered)))
    )
  )
  result
)

(defun degk--polyline-first-layout-sira (plEnt blockObjs tol excludeObj / touched blkObj totalLen useFromStart ordered ins dist key pair siraList candidate result)
  ;; Ilk dolu SIRA_NO kat/loop biciminde olmayabilir. Flasor terminali
  ;; gorulemediginde hatta degen bloklar arasindan yerlesim bilgisi tasiyan
  ;; ilk gecerli SIRA_NO'yu ayni hat yonu sirasi ile bul.
  (foreach blkObj blockObjs
    (if (and (degk--poly-touch-insertion? plEnt blkObj tol)
             (or (null excludeObj)
                 (not (degk--same-block-p blkObj excludeObj))))
      (setq touched (cons blkObj touched)))
  )
  (if touched
    (progn
      (setq totalLen (vlax-curve-getDistAtParam plEnt (vlax-curve-getEndParam plEnt))
            useFromStart (degk--use-from-lower-sira-side plEnt touched totalLen)
            ordered nil)
      (foreach blkObj touched
        (setq ins  (deg-get-inspt blkObj)
              dist (degk--dist-along plEnt ins)
              key  (if useFromStart dist (- totalLen dist))
              ordered (cons (cons key blkObj) ordered)))
      (setq ordered (vl-sort ordered '(lambda (a b) (< (car a) (car b)))))
      (while (and ordered (null result))
        (setq pair     (car ordered)
              blkObj   (cdr pair)
              siraList (degk--expand-sira-no (degk--get-att blkObj "SIRA_NO")))
        (if (null siraList)
          (setq siraList (list (degk--get-att blkObj "SIRA_NO"))))
        (while (and siraList (null result))
          (setq candidate (degk--clean-text (car siraList))
                siraList  (cdr siraList))
          (if (and (/= candidate "")
                   (degk--layout-key-from-sira candidate))
            (setq result candidate)))
        (setq ordered (cdr ordered)))
    )
  )
  result
)

(defun degk--block-loop-sequence (blkObj / siraList sira parts n best)
  ;; Ayni loopun parcalari birlestiginde blok sirasi SIRA_NO'nun son
  ;; bolumunden gelir. Coklu SIRA_NO icin en kucuk eleman kullanilir.
  (setq siraList (degk--expand-sira-no (degk--get-att blkObj "SIRA_NO")))
  (if (null siraList)
    (setq siraList (list (degk--get-att blkObj "SIRA_NO"))))
  (foreach sira siraList
    (setq parts (degk--split-hyphens (degk--clean-text sira))
          n     (if parts (degk--token-first-number (last parts)) nil))
    (if (and (numberp n) (or (null best) (< n best)))
      (setq best n))
  )
  best
)

(defun degk--block-loop-order-key
  (blkObj loopEnts / ins seq memberIndex plEnt cp gap localDist bestGap bestIndex bestDist)
  (setq ins         (deg-get-inspt blkObj)
        seq         (degk--block-loop-sequence blkObj)
        memberIndex 0
        bestIndex   0
        bestDist    0.0)
  (foreach plEnt loopEnts
    (if (and plEnt (degk--curve-ok? plEnt))
      (progn
        (setq cp        (deg-safe-closest-point plEnt ins)
              gap       (if cp (distance ins cp) 1.0e99)
              localDist (if cp (degk--dist-along plEnt ins) 0.0))
        (if (not (numberp localDist)) (setq localDist 0.0))
        (if (or (null bestGap) (< gap bestGap))
          (setq bestGap   gap
                bestIndex memberIndex
                bestDist  localDist))
      )
    )
    (setq memberIndex (1+ memberIndex))
  )
  ;; SIRA_NO once gelir; geometrik konum yalniz esit/eksik sirada baglayicidir.
  (if (numberp seq)
    (+ (* (float seq) 1.0e12) (* (float bestIndex) 1.0e8) bestDist)
    (+ 9.0e15 (* (float bestIndex) 1.0e8) bestDist))
)

(defun degk--layout-record-less-p (a b / va vb fa fb oa ob ia ib)
  (setq va (car a) vb (car b)
        fa (nth 1 a) fb (nth 1 b)
        oa (nth 2 a) ob (nth 2 b)
        ia (nth 3 a) ib (nth 3 b))
  (cond
    ((and va (not vb)) T)
    ((and (not va) vb) nil)
    ((and va vb (/= fa fb)) (< fa fb))
    ((and va vb (/= oa ob)) (< oa ob))
    (T (< ia ib)))
)

(defun degk--sira-text-sequence (s / parts)
  (setq parts (degk--split-hyphens (degk--clean-text (if s s ""))))
  (if parts
    (degk--token-first-number (last parts))
    nil)
)

(defun degk--layout-record-title (rec / title sira)
  ;; Kat-loop-cihaz veya loop-cihaz bicimlerinin ikisinde de son '-'
  ;; sonrasini cihaz sirasi, oncesini ortak loop kimligi kabul et.
  (setq title (if rec (degk--clean-text (nth 8 rec)) "")
        sira  (if rec (degk--clean-text (nth 9 rec)) ""))
  (cond
    ((/= title "") (strcase title))
    ((/= sira "") (strcase (degk--loop-name-from-sira sira)))
    ((and rec (/= (degk--clean-text (nth 5 rec)) ""))
      (strcase (degk--loop-name-from-sira (nth 5 rec))))
    (T ""))
)

(defun degk--layout-record-members (rec / members ent)
  (setq members (nth 7 rec)
        ent     (nth 4 rec))
  (if members members (if ent (list ent) nil))
)

(defun degk--same-layout-loop-p (a b / titleA titleB specialA specialB terminalA terminalB)
  ;; Kat, loop sirasi ve loop basligi ayniysa polyline parcalari tek looptur.
  ;; Tek ayracli SIRA_NO'larda ortak baslik tek basina loop kimligidir.
  ;; Flasor/strobe hatlari normal looplarla ayni kayda kesinlikle girmez.
  (setq titleA    (degk--layout-record-title a)
        titleB    (degk--layout-record-title b)
        specialA  (if (degk--layout-record-flasher-p a) T nil)
        specialB  (if (degk--layout-record-flasher-p b) T nil)
        terminalA (nth 6 a)
        terminalB (nth 6 b))
  (and (/= titleA "")
       (= titleA titleB)
       ;; Terminale dogrudan degen ve devaminda terminale degmeyen parcalar
       ;; ayni SIRA_NO loop kimligindeyse tek loop olarak kalmalidir.
       (eq specialA specialB)
       ;; Ayni baslikli iki flasor parcasi farkli fiziksel kontrol modullerine
       ;; bagliysa iki ayri looptur. Terminale degmeyen devam parcasi ise kendi
       ;; terminal kaydiyla birlesmeye devam edebilir.
       (or (not specialA)
           (null terminalA)
           (null terminalB)
           (degk--same-block-p terminalA terminalB)))
)

(defun degk--layout-anchor-better-p (candidate current / termC termO validC validO seqC seqO)
  ;; Yerini bilen terminal parcasi once gelir. Terminal yoksa gecerli kat-loop
  ;; kaydi, o da yoksa en kucuk cihaz sirali parca ankraj olur.
  (setq termC  (if (nth 6 candidate) T nil)
        termO  (if (nth 6 current) T nil)
        validC (if (car candidate) T nil)
        validO (if (car current) T nil)
        seqC   (degk--sira-text-sequence (nth 9 candidate))
        seqO   (degk--sira-text-sequence (nth 9 current)))
  (cond
    ((and termC (not termO)) T)
    ((and termO (not termC)) nil)
    ((and validC (not validO)) T)
    ((and validO (not validC)) nil)
    ((and (numberp seqC) (numberp seqO) (/= seqC seqO)) (< seqC seqO))
    ((and (numberp seqC) (not (numberp seqO))) T)
    ((and (numberp seqO) (not (numberp seqC))) nil)
    (T (< (nth 3 candidate) (nth 3 current))))
)

(defun degk--combine-layout-records (a b / members ent terminalObj anchor title sourceSira)
  (setq members (degk--layout-record-members a))
  (foreach ent (degk--layout-record-members b)
    (if (not (member ent members))
      (setq members (append members (list ent)))
    )
  )
  (setq terminalObj (if (nth 6 a) (nth 6 a) (nth 6 b))
        anchor      (if (degk--layout-anchor-better-p b a) b a)
        title       (degk--layout-record-title anchor)
        sourceSira  (nth 9 anchor))
  (list (car anchor) (nth 1 anchor) (nth 2 anchor) (nth 3 anchor)
        (nth 4 anchor) (nth 5 anchor) terminalObj members title sourceSira)
)

(defun degk--merge-layout-records (records / merged rec rebuilt existing mergedP)
  ;; Secim sirasini koruyarak ayni loopun devam polyline'larini tek kayda indir.
  (setq merged nil)
  (foreach rec records
    (if (/= (degk--layout-record-title rec) "")
      (progn
        (setq rebuilt nil
              mergedP nil)
        (foreach existing merged
          (if (and (not mergedP)
                   (degk--same-layout-loop-p rec existing))
            (progn
              (setq rebuilt
                (cons (degk--combine-layout-records existing rec) rebuilt))
              (setq mergedP T))
            (setq rebuilt (cons existing rebuilt)))
        )
        (setq merged (reverse rebuilt))
        (if (not mergedP)
          (setq merged (append merged (list rec))))
      )
      (setq merged (append merged (list rec))))
  )
  merged
)

(defun degk--layout-record-gap-to-block (rec blkObj / ins best ent cp gap)
  (setq ins (deg-get-inspt blkObj)
        best 1.0e99)
  (if ins
    (foreach ent (degk--layout-record-members rec)
      (if (and ent (degk--curve-ok? ent))
        (progn
          (setq cp (deg-safe-closest-point ent ins))
          (if cp
            (progn
              (setq gap (distance ins cp))
              (if (< gap best) (setq best gap))))))))
  best
)

(defun degk--terminal-normal-layout (blkObj records tol / rec gap bestGap bestLayout)
  ;; Modulun kolon semasindaki kati kendi SIRA_NO'sundan farkli olabilir veya
  ;; SIRA_NO bos olabilir. Gercek kolon satirini, modulu kopyalayan normal
  ;; loop kaydindan bul. Birden cok temas varsa en yakin normal loopu kullan.
  (setq bestGap 1.0e99)
  (foreach rec records
    (if (and (car rec)
             (numberp (nth 1 rec))
             (not (degk--layout-record-flasher-p rec))
             (degk--block-touches-loop-p
               (degk--layout-record-members rec) blkObj tol))
      (progn
        (setq gap (degk--layout-record-gap-to-block rec blkObj))
        (if (< gap bestGap)
          (setq bestGap gap
                bestLayout (list (nth 1 rec) (nth 2 rec)))))))
  bestLayout
)

(defun degk--layout-record-with-terminal (rec terminalObj preferredLayout / info terminalSira layout outputSira)
  ;; Loop kimligini ve birlestirilmis polyline listesini koru; yalniz kolon
  ;; yerlesimini eslesen kontrol modulunun kat/loop kaydindan al.
  (setq info (degk--block-first-layout-info terminalObj)
        terminalSira (if info (car info) "")
        layout (if preferredLayout preferredLayout (if info (cadr info) nil))
        outputSira
          (if (and (null preferredLayout) (/= terminalSira ""))
            terminalSira
            (nth 5 rec)))
  (if layout
    (list T (car layout) (cadr layout) (nth 3 rec) (nth 4 rec)
          outputSira terminalObj (degk--layout-record-members rec)
          (nth 8 rec) (nth 9 rec))
    (list (car rec) (nth 1 rec) (nth 2 rec) (nth 3 rec) (nth 4 rec)
          (nth 5 rec) terminalObj (degk--layout-record-members rec)
          (nth 8 rec) (nth 9 rec)))
)

(defun degk--assign-unmatched-flasher-terminals
  (records allInserts polylines tol / used rec terminalObj handle wantedFloor blkObj info layout normalLayout copyable gap best bestGap bestHandle bestLayout out loopHandle)
  ;; Gercek temasla bulunan moduller once rezerve edilir. Fiziksel baglantisi
  ;; gorunmeyen loop, yalniz kendi katinda kolon semasina kopyalanacak ve henuz
  ;; kullanilmamis bir kontrol modulune bir kez atanir.
  (foreach rec records
    (if (and (degk--layout-record-flasher-p rec)
             (setq terminalObj (nth 6 rec)))
      (progn
        (setq handle (strcase (degkk--object-handle terminalObj)))
        (if (and (/= handle "") (not (member handle used)))
          (setq used (cons handle used))))))
  (foreach rec records
    (setq best nil bestGap 1.0e99 bestHandle "" bestLayout nil)
    (if (and (degk--layout-record-flasher-p rec)
             (null (nth 6 rec))
             (car rec)
             (numberp (setq wantedFloor (nth 1 rec))))
      (progn
        (foreach blkObj allInserts
          (if (and (degk--flasher-terminal-module-p blkObj)
                   (setq handle (strcase (degkk--object-handle blkObj)))
                   (/= handle "")
                   (not (member handle used)))
            (progn
              ;; Once kolon semasinda modulu olusturan normal loopun katini
              ;; kullan. Bu kayit yoksa eski SIRA_NO kat kontrolune geri don.
              (setq normalLayout
                      (degk--terminal-normal-layout blkObj records tol)
                    info
                      (if normalLayout
                        nil
                        (degk--block-first-layout-info blkObj))
                    layout
                      (if normalLayout normalLayout (if info (cadr info) nil))
                    copyable
                      (or normalLayout
                          (degk--block-touches-selected-normal-p
                            blkObj polylines tol)))
              (if (and copyable
                       layout
                       (= wantedFloor (car layout)))
                (progn
                  (setq gap (degk--layout-record-gap-to-block rec blkObj))
                  (if (< gap bestGap)
                    (setq best blkObj
                          bestGap gap
                          bestHandle handle
                          bestLayout layout)))))))
        (if best
          (progn
            (setq rec (degk--layout-record-with-terminal rec best bestLayout)
                  used (cons bestHandle used)
                  loopHandle (if (nth 4 rec) (cdr (assoc 5 (entget (nth 4 rec)))) ""))
            (princ
              (strcat "\nDK: Baglantisi gorunmeyen loop ayni kattaki bos module baglandi: loop="
                      (if loopHandle loopHandle "")
                      " modul=" bestHandle
                      " kat=" (itoa wantedFloor)))))))
    (setq out (cons rec out)))
  (reverse out)
)

(defun degk--terminal-copy-handle (copyRec / copyObj)
  (setq copyObj (if copyRec (car copyRec) nil))
  (if (and copyObj (= (type copyObj) 'VLA-OBJECT))
    (strcase (degkk--object-handle copyObj))
    "")
)

(defun degk--reserved-terminal-copy-handles (records / used rec sourceObj copyRec copyHandle)
  ;; Kolon kopyalari olustuktan sonra fiziksel baglantili tum modulleri once
  ;; rezerve et. Islenme sirasi, baglantisiz bir loopun dolu modulu calmasina
  ;; neden olmasin.
  (foreach rec records
    (if (and (degk--layout-record-flasher-p rec)
             (setq sourceObj (nth 6 rec))
             (setq copyRec
               (degk--area-module-copy-get sourceObj (nth 1 rec)))
             (/= (setq copyHandle (degk--terminal-copy-handle copyRec)) "")
             (not (member copyHandle used)))
      (setq used (cons copyHandle used))))
  used
)

(defun degk--unused-terminal-copy-for-layout
  (rec wantedFloor wantedRow used / items item sourceObj copyRec copyObj copyHandle itemRow itemFloor rowMatch floorMatch rank gap bestRank bestGap best)
  ;; Dogrudan kolon semasinda olusan gercek terminal INSERT'lerine bak. Kaynak
  ;; plandaki handle veya temas kaydi bos olsa bile ayni kattaki bos kopya bulunur.
  (setq items
          (if (boundp '*degk-column-terminal-copies*)
            *degk-column-terminal-copies*
            nil)
        bestGap 1.0e99)
  (foreach item items
    (setq copyObj (car item)
          copyRec (list (car item) (nth 1 item) (nth 2 item) (nth 3 item))
          sourceObj (nth 4 item)
          copyHandle (degk--terminal-copy-handle copyRec)
          itemRow (nth 2 item)
          itemFloor (nth 3 item)
          rowMatch
            (and (numberp wantedRow)
                 (numberp itemRow)
                 (= wantedRow itemRow))
          floorMatch
            (and (numberp wantedFloor)
                 (numberp itemFloor)
                 (= wantedFloor itemFloor))
          rank
            (cond
              (rowMatch 0)
              ;; Satir kaydi eski/eksik olsa bile ayni kattaki gercek kolon
              ;; kopyasini reddetme; bulunan kopyanin kendi satiri sonradan
              ;; loop yerlesimine birinci oncelikle uygulanir.
              (floorMatch 1)
              (T nil)))
    (if (and (numberp rank)
             copyObj
             (= (type copyObj) 'VLA-OBJECT)
             (/= copyHandle "")
             (not (member copyHandle used)))
      (progn
        (setq gap
          (if (and sourceObj
                   (= (type sourceObj) 'VLA-OBJECT)
                   (not (vl-catch-all-error-p sourceObj)))
            (degk--layout-record-gap-to-block rec sourceObj)
            0.0))
        (if (or (null bestRank)
                (< rank bestRank)
                (and (= rank bestRank) (< gap bestGap)))
          (setq bestRank rank
                bestGap gap
                best (list sourceObj copyRec copyHandle))))))
  best
)

(defun degk--normal-area-layout-records (polylines / tol allInserts sourceBlocks ss i ent blkObj blkLayer records mergedRecords sira sourceSira sourceTitle layout layoutSira layer terminalObj terminalSira terminalInfo terminalMode loopHandle terminalHandle)
  (setq tol        (DEG:CFG-TOL-NUM-OR 'DN_BLOCK_TOL 1.0)
        allInserts nil
        ss         (ssget "_X" '((0 . "INSERT"))))
  (if ss
    (progn
      (setq i 0)
      (while (< i (sslength ss))
        (setq ent    (ssname ss i)
              blkObj (if ent (vl-catch-all-apply 'vlax-ename->vla-object (list ent)) nil)
              blkLayer (if (and blkObj (not (vl-catch-all-error-p blkObj)))
                         (vl-catch-all-apply 'vla-get-Layer (list blkObj))
                         nil))
        (if (and blkObj
                 (not (vl-catch-all-error-p blkObj))
                 blkLayer
                 (not (vl-catch-all-error-p blkLayer))
                 (/= (strcase blkLayer) "0")
                 (not (DEG:IGNORE-BLOCK-OBJ? blkObj)))
          (setq allInserts (cons blkObj allInserts)))
        (setq i (1+ i)))
    )
  )
  (setq records nil i 0)
  (while (< i (sslength polylines))
    (setq ent    (ssname polylines i)
          layer  (if ent (cdr (assoc 8 (entget ent))) nil)
          terminalObj nil
          terminalSira ""
          terminalMode "YOK")
    ;; Flasor/strobe loopu kendi SIRA_NO katina degil, temas ettigi kontrol
    ;; modulunun katina gider. Ozel looplar sonradan islendigi icin bu katta
    ;; mevcut looplarin en sagina, son siraya yerlesir.
    (if (and layer (degk--flasher-loop-layer-p layer))
      (progn
        (setq terminalObj
          (degk--flasher-terminal-on-polyline ent allInserts tol))
        (if terminalObj (setq terminalMode "UC_TEMASI"))
      )
    )
    ;; Flasor loopunun kimligi kontrol modulunun SIRA_NO'sundan uretilmez.
    ;; Tum terminal modulleri kaynak cihaz listesinden cikartilir.
    (setq sourceBlocks
      (if (and layer (degk--flasher-loop-layer-p layer))
        (vl-remove-if 'degk--flasher-terminal-module-p allInserts)
        allInserts))
    ;; Mantiksal loop kimligi terminal modulunden degil loop cihazlarindan gelir.
    (setq sourceTitle (degk--source-loop-title (list ent))
          sourceSira
            (cond
              (sourceTitle (strcat sourceTitle "-01"))
              ((= *degk-number-mode* 'UNNUMBERED) "")
              (T (degk--polyline-first-sira ent sourceBlocks tol nil))))
    ;; Terminal baglantisi planda gorunmuyorsa ilk dolu fakat gecersiz degerde
    ;; kalma; ayni flasor hattindaki gecerli kat-loop SIRA_NO'sunu yedek al.
    (if (and (/= *degk-number-mode* 'UNNUMBERED) layer
             (degk--flasher-loop-layer-p layer)
             (null terminalObj)
             (null (degk--layout-key-from-sira sourceSira)))
      (progn
        (setq layoutSira
          (degk--polyline-first-layout-sira ent sourceBlocks tol nil))
        (if layoutSira (setq sourceSira layoutSira)))
    )
    ;; Fiziksel temas bulunmayan parcalara bu asamada otomatik modul atama.
    ;; Once ayni SIRA_NO loop kimligindeki polyline parcalari birlestirilir;
    ;; terminale gercekten degen parcanin kaynak modulu tum loopa aktarilir.
    (if (and layer (degk--flasher-loop-layer-p layer))
      (progn
        (setq loopHandle     (if ent (cdr (assoc 5 (entget ent))) "")
              terminalHandle (if terminalObj
                               (degkk--object-handle terminalObj)
                               "YOK"))
        (princ
          (strcat "\nDK terminal esleme: loop="
                  (if loopHandle loopHandle "")
                  " -> modul=" terminalHandle
                  " [" terminalMode "]"))))
    ;; Fiziksel olarak bu hatta bagli tek tag, kat ve loop kimliginin kaynagidir.
    (if sourceTitle (setq sourceSira (strcat sourceTitle "-01")))
    (setq sourceTitle
            (if (/= (degk--clean-text sourceSira) "")
              (degk--loop-name-from-sira sourceSira)
              "")
          sira sourceSira)
    ;; Terminalin SIRA_NO'su yalniz kat/loop yerlesim ankrajini belirler.
    (if terminalObj
      (progn
        (setq terminalInfo (degk--block-first-layout-info terminalObj)
              terminalSira
                (if terminalInfo
                  (car terminalInfo)
                  (degk--clean-text (degk--get-att terminalObj "SIRA_NO"))))))
    (if (/= terminalSira "")
      (setq sira terminalSira))
    (setq layout (if sira (degk--layout-key-from-sira sira) nil))
    (if layout
      (setq records
        (cons (list T (car layout) (cadr layout) i ent sira terminalObj
                    (list ent) sourceTitle sourceSira)
              records))
      (setq records
        (cons (list nil 0 0 i ent sira terminalObj
                    (list ent) sourceTitle sourceSira)
              records)))
    (setq i (1+ i))
  )
  ;; Baglantisiz flasor looplarini bu asamada kaynak plandaki tahmini module
  ;; atama. Gercek kolon kopyalari normal looplar cizildikten sonra secilir.
  (setq mergedRecords (degk--merge-layout-records (reverse records)))
  (vl-sort mergedRecords 'degk--layout-record-less-p)
)

(defun degk--ensure-loop-layer (layer / rec ent ed c62)
  (if (not (tblsearch "LAYER" layer))
    (entmake
      (list
        '(0 . "LAYER")
        '(100 . "AcDbSymbolTableRecord")
        '(100 . "AcDbLayerTableRecord")
        (cons 2 layer)
        '(70 . 0)
        '(62 . 7)
        '(6 . "Continuous")))
  )
  (setq ent (tblobjname "LAYER" layer))
  (if ent
    (progn
      (setq ed (entget ent)
            ed (degk--assoc-put 70 0 ed)
            c62 (cdr (assoc 62 ed)))
      (if (and (numberp c62) (< c62 0))
        (setq ed (degk--assoc-put 62 (abs c62) ed)))
      (entmod ed)
      (entupd ent))
  )
  layer
)

(defun degk--add-loop-text (pt txt layer height / data)
  (setq txt (degk--clean-text (if txt txt "")))
  (if (and pt (/= txt "") (> height 0.0))
    (progn
      (degk--ensure-loop-layer layer)
      (setq data
        (list
          '(0 . "TEXT")
          '(100 . "AcDbEntity")
          (cons 8 layer)
          '(100 . "AcDbText")
          (cons 10 pt)
          (cons 40 height)
          (cons 1 txt)
          '(50 . 0.0)
          '(41 . 1.0)
          '(7 . "STANDARD")
          '(71 . 0)
          '(72 . 0)
          '(100 . "AcDbText")
          '(73 . 0)))
      (entmakex data)
    )
  )
)

(defun degk--add-loop-intersection-mark (pt markLen layer / halfDiag z p0 p1)
  (if (and pt (numberp markLen) (> markLen 0.0))
    (progn
      ;; Merkezden iki yana esit uzayan, toplam markLen boyunda 45 derece isaret.
      (setq halfDiag (/ markLen 2.82842712474619)
            z        (if (and (caddr pt) (numberp (caddr pt))) (caddr pt) 0.0)
            p0       (list (- (car pt) halfDiag) (- (cadr pt) halfDiag) z)
            p1       (list (+ (car pt) halfDiag) (+ (cadr pt) halfDiag) z))
      (degk--entmake-lwpoly (list p0 p1) layer nil)
    )
  )
)

(defun degk--cable-loop-key (txt / key ch)
  (setq key (strcase (degk--clean-text txt)))
  (while (vl-string-search "LOOP" key) (setq key (vl-string-subst "L" "LOOP" key)))
  (foreach ch '(" " "-" "_")
    (while (vl-string-search ch key) (setq key (vl-string-subst "" ch key))))
  key)

(defun degk--perf-call (label fn args / started result elapsed rec)
  (if (not *degk-perf-active*)
    (apply fn args)
    (progn
      (setq started (getvar "MILLISECS")
            *degk-perf-stack* (cons label *degk-perf-stack*))
      (setq result (apply fn args)
            elapsed (- (getvar "MILLISECS") started))
      (if (< elapsed 0) (setq elapsed (+ elapsed 4294967296.0)))
      (setq rec (assoc label *degk-perf-data*)
            *degk-perf-stack* (cdr *degk-perf-stack*))
      (if rec
        (setq *degk-perf-data* (subst
          (list label (1+ (cadr rec)) (+ (caddr rec) elapsed)
                (max (nth 3 rec) elapsed)) rec *degk-perf-data*))
        (setq *degk-perf-data* (append *degk-perf-data*
          (list (list label 1 elapsed elapsed)))))
      result)))

(defun degk--perf-report (/ text rec)
  (setq *degk-perf-active* nil
        text "\n--- DK SURE RAPORU v2 ---\nAsamalar ic ice olabilir; sureleri toplamayiniz. Secim beklemeleri haric.")
  (foreach rec *degk-perf-data*
    (setq text (strcat text "\n" (car rec) ": "
      (rtos (/ (caddr rec) 1000.0) 2 3) " sn | adet=" (itoa (cadr rec))
      " | en uzun=" (rtos (/ (nth 3 rec) 1000.0) 2 3) " sn")))
  (setq text (strcat text "\nSecilen nesne=" (itoa *degk-perf-selected*)
    " | indeks text=" (itoa *degk-perf-texts*)
    " | indeks cizgi=" (itoa *degk-perf-leaders*)
    " | kesin temas testi=" (itoa *degk-perf-touches*)
    "\nAlan modu=" (cond ((= *degk-number-mode* 'NUMBERED) "NUMARALI")
                           ((= *degk-number-mode* 'UNNUMBERED) "NUMARASIZ") (T "SECILMEDI"))
    " | etiket-cizgi adayi=" (itoa (length *degk-title-index*))
    " | onbellekte loop=" (itoa (length *degk-title-cache*))))
  (foreach rec *degk-perf-stack*
    (setq text (strcat text "\nTamamlanamayan asama: " rec)))
  (setq *degk-perf-last-report* (strcat text "\n--- RAPOR SONU ---"))
  (princ))

(defun c:DKSURE ()
  (if *degk-perf-data* (degk--perf-report))
  (princ (if *degk-perf-last-report* *degk-perf-last-report*
    "\nHenuz DK sure raporu yok. Once DK calistirin."))
  (princ))

(defun degk--cable-source-index (areaSS / result)
  (setq *degk-ups-cable-texts* nil)
  (setq result (degk--perf-call "Kablo kaynak indeksi" 'degk--cable-source-index-body (list areaSS)))
  (if *degk-perf-active*
    (setq *degk-perf-texts* (length (car result))
          *degk-perf-leaders* (length (cadr result))))
  result)

(defun degk--tag-entity-points (ent ed / pts item elevation)
  ;; LINE parameters measure length, not vertex count. Preserve exact endpoints.
  (if (= (cdr (assoc 0 ed)) "LINE")
    (list (cdr (assoc 10 ed)) (cdr (assoc 11 ed)))
    (progn
      (setq elevation (cond ((cdr (assoc 38 ed))) (T 0.0)))
      (foreach item ed
        (if (= (car item) 10)
          (setq pts (cons (trans (list (cadr item) (caddr item) elevation) ent 0) pts))))
      (reverse pts))))

(defun degk--cable-source-index-body (areaSS / space ss i ent ed kind txt bb h texts leaders pts item)
  (setq space (if (and areaSS (> (sslength areaSS) 0))
                (cdr (assoc 410 (entget (ssname areaSS 0)))) "Model")
        ss (ssget "_X" (list '(0 . "TEXT,MTEXT,LINE,LWPOLYLINE") (cons 410 space))) i 0)
  (if ss
    (repeat (sslength ss)
      (setq ent (ssname ss i) i (1+ i) ed (entget ent) kind (cdr (assoc 0 ed)))
      (if (member kind '("TEXT" "MTEXT"))
        (progn
          (setq txt "")
          (foreach item ed (if (member (car item) '(1 3)) (setq txt (strcat txt (cdr item)))))
          (setq txt (degk--clean-text txt) h (cdr (assoc 40 ed))
                bb (vl-catch-all-apply 'degk--ent-bbox (list (vlax-ename->vla-object ent))))
          (if (vl-catch-all-error-p bb) (setq bb nil))
          (if (and bb h (> h 0.0) (/= txt ""))
            (setq texts (cons (list txt bb h (degk--cable-loop-key txt) (cdr (assoc 8 ed))) texts))))
        (if (or (= kind "LINE") (= 0 (logand 1 (cdr (assoc 70 ed)))))
          (progn
            ;; Tag ve loop temasini ayni WCS duzleminde karsilastir.
            (setq pts (degk--tag-entity-points ent ed))
            (if (>= (length pts) 2) (setq leaders (cons (list ent pts) leaders))))))))
  (list texts leaders))

(defun degk--numbered-device-p (ent / obj value)
  (setq obj (vl-catch-all-apply 'vlax-ename->vla-object (list ent)))
  (if (and (not (vl-catch-all-error-p obj)) (not (DEG:IGNORE-BLOCK-OBJ? obj)))
    (progn
      (setq value (vl-catch-all-apply 'degk--get-att (list obj "SIRA_NO")))
      (and (not (vl-catch-all-error-p value)) (/= (degk--clean-text value) "")))))

(defun degk--area-number-mode (areaSS / i ent ed numbered)
  (setq i 0)
  (while (and areaSS (< i (sslength areaSS)) (not numbered))
    (setq ent (ssname areaSS i) i (1+ i) ed (entget ent))
    (if (and (= (cdr (assoc 0 ed)) "INSERT") (/= (cdr (assoc 8 ed)) "0"))
      (setq numbered (degk--numbered-device-p ent))))
  (if numbered 'NUMBERED 'UNNUMBERED))

(defun degk--loop-bounds (ent / rec obj bb)
  (if (setq rec (assoc ent *degk-loop-bounds-cache*))
    (cdr rec)
    (progn
      (setq obj (vl-catch-all-apply 'vlax-ename->vla-object (list ent)))
      (if (not (vl-catch-all-error-p obj))
        (setq bb (vl-catch-all-apply 'degk--ent-bbox (list obj))))
      (if (vl-catch-all-error-p bb) (setq bb nil))
      (setq *degk-loop-bounds-cache* (cons (cons ent bb) *degk-loop-bounds-cache*))
      bb)))

(defun degk--point-near-loop-bounds-p (pt bb tol)
  (or (null bb)
      (and (>= (car pt) (- (caar bb) tol))
           (<= (car pt) (+ (caadr bb) tol))
           (>= (cadr pt) (- (cadar bb) tol))
           (<= (cadr pt) (+ (cadadr bb) tol)))))

(defun degk--cable-end-touches (pts loops tol / hit pt loopEnt near bb)
  (foreach loopEnt loops
    (if (not hit)
      (progn
        (setq bb (degk--loop-bounds loopEnt))
        (foreach pt (list (car pts) (last pts))
          (if (and (not hit) (degk--point-near-loop-bounds-p pt bb tol))
            (progn
              (if *degk-perf-active* (setq *degk-perf-touches* (1+ *degk-perf-touches*)))
              (setq near (vl-catch-all-apply 'vlax-curve-getClosestPointTo (list loopEnt pt)))
              (if (and (not (vl-catch-all-error-p near)) near (<= (distance pt near) tol))
                (setq hit T))))))))
  hit)

(defun degk--prepare-title-index (/ head leader rest a b bb h tol matches title layout segments segment lowY highY serial)
  (setq tol (DEG:CFG-TOL-NUM-OR 'DN_BLOCK_TOL 1.0)
        *degk-title-index* nil serial 0)
  ;; Polyline parcalarini her baslik icin tekrar dolasma.
  (foreach leader (cadr *degk-cable-index*)
    (setq rest (cadr leader))
    (while (cdr rest)
      (setq a (car rest) b (cadr rest) rest (cdr rest))
      (if (and (<= (abs (- (cadr a) (cadr b))) tol)
               (> (abs (- (car a) (car b))) 1e-9))
        (setq segments
          (cons (list (cadr a) (min (car a) (car b))
                      (max (car a) (car b)) leader (setq serial (1+ serial))) segments)))))
  (setq segments (vl-sort segments
    '(lambda (a b) (if (= (car a) (car b)) (< (nth 4 a) (nth 4 b)) (< (car a) (car b))))))
  (foreach head (car *degk-cable-index*)
    (setq bb (cadr head) h (caddr head) matches nil)
    (setq title (strcase (degk--clean-text (car head))))
    (while (vl-string-search "LOOP-" title)
      (setq title (vl-string-subst "L" "LOOP-" title)))
    (while (vl-string-search "LOOP" title)
      (setq title (vl-string-subst "L" "LOOP" title)))
    (setq layout (degk--layout-key-from-sira (strcat title "-01")))
    (if layout
      (progn
        (setq lowY (- (cadar bb) (* 2.0 h))
              highY (+ (cadar bb) (* 0.3 h)) rest segments)
        (while (and rest (< (caar rest) lowY)) (setq rest (cdr rest)))
        (while (and rest (<= (caar rest) highY))
          (setq segment (car rest) rest (cdr rest) leader (nth 3 segment))
          (if (and (> (- (nth 2 segment) (cadr segment)) h)
                   (>= (caar bb) (- (cadr segment) h))
                   (<= (caadr bb) (+ (nth 2 segment) h))
                   (not (member (car leader) matches)))
            (setq matches (cons (car leader) matches)
                  *degk-title-index*
                    (cons (list title (car leader) (cadr leader) head segment) *degk-title-index*)))))))
  (setq *degk-title-index-ready* T)
  *degk-title-index*)

(defun degk--source-loop-title (loops)
  (degk--perf-call "Kat-loop tag eslestirme"
    'degk--source-loop-title-body (list loops)))

(defun degk--source-loop-title-body (loops / ent rec entries entry found tol pending remaining)
  (if (not *degk-title-index-ready*)
    (degk--perf-call "Kat-loop etiketlerini bir kez hazirlama" 'degk--prepare-title-index nil))
  (setq tol (DEG:CFG-TOL-NUM-OR 'DN_BLOCK_TOL 1.0))
  (setq remaining loops)
  (while (and remaining (not found))
    (setq ent (car remaining) remaining (cdr remaining))
    (if (setq rec (assoc ent *degk-title-cache*))
      (setq entries (cdr rec))
      (progn
        (setq entries nil pending *degk-title-index*)
        (while (and pending (not entries))
          (setq entry (car pending) pending (cdr pending))
          (if (and (not (member (cadr entry) loops))
                   (degk--cable-end-touches (caddr entry) (list ent) tol))
            (setq entries (cons entry entries))))
        (setq *degk-title-cache* (cons (cons ent entries) *degk-title-cache*))))
    (while (and entries (not found))
      (setq entry (car entries) entries (cdr entries))
      (if (not (member (cadr entry) loops))
        (setq found (car entry)))))
  found)

(defun degk--source-cable-text (loops name / cable ent key)
  (setq cable (degk--perf-call "Kablo kesiti eslestirme" 'degk--source-cable-text-body (list loops name)))
  (if cable
    (foreach ent loops
      (if (degk--flasher-loop-layer-p (cdr (assoc 8 (entget ent))))
        (progn
          (setq key (strcase (vl-string-right-trim ". " cable)))
          (while (vl-string-search " " key)
            (setq key (vl-string-subst "" " " key)))
          (if (not (assoc key *degk-ups-cable-texts*))
            (setq *degk-ups-cable-texts* (cons (cons key cable) *degk-ups-cable-texts*)))))))
  cable)

(defun degk--source-cable-text-body (loops name / remaining entries entry selected head segment bb h texts cable cb y left right)
  (setq remaining loops)
  (while (and remaining (not selected))
    (setq entries (cdr (assoc (car remaining) *degk-title-cache*)) remaining (cdr remaining))
    (while (and entries (not selected))
      (setq entry (car entries) entries (cdr entries))
      (if (and (nth 3 entry) (nth 4 entry) (not (member (cadr entry) loops)))
        (setq selected entry))))
  (if selected
    (progn
      ;; Read the cable below the already accepted tag; do not match tags again.
      (setq head (nth 3 selected) segment (nth 4 selected)
            bb (cadr head) h (caddr head) y (car segment)
            left (cadr segment) right (nth 2 segment) texts (car *degk-cable-index*))
      (while (and texts (not cable))
        (setq cb (cadar texts))
        (if (and (wcmatch (strcase (caar texts)) "*#*X*#*")
                 (<= (cadadr cb) (+ y (* 0.3 h)))
                 (>= (cadar cb) (- y (* 3.0 h)))
                 (<= (abs (- (caar cb) (caar bb))) (* 2.0 h))
                 (>= (caar cb) (- left h)) (<= (caadr cb) (+ right h)))
          (setq cable (caar texts)))
        (setq texts (cdr texts)))
      cable)
    (degk--source-cable-text-unmatched-body loops name)))

(defun degk--source-cable-text-unmatched-body (loops name / key head leader pts rest a b lineY leftX rightX bb h cable cb candidates found tol)
  (setq key (degk--cable-loop-key name)
        tol (DEG:CFG-TOL-NUM-OR 'DN_BLOCK_TOL 1.0))
  (if (/= key "")
    (foreach head (car *degk-cable-index*)
      (if (= key (nth 3 head))
        (foreach leader (cadr *degk-cable-index*)
          (setq pts (cadr leader) bb (cadr head) h (caddr head))
          (if (not (member (car leader) loops))
            (progn
              (setq rest pts)
              (while (cdr rest)
                (setq a (car rest) b (cadr rest) rest (cdr rest)
                      lineY (cadr a) leftX (min (car a) (car b)) rightX (max (car a) (car b)))
                (if (and (<= (abs (- lineY (cadr b))) tol)
                         (> (- rightX leftX) h)
                         (>= (car (car bb)) (- leftX h)) (<= (car (cadr bb)) (+ rightX h))
                         (>= (- (cadr (car bb)) lineY) (* -0.3 h))
                         (<= (- (cadr (car bb)) lineY) (* 2.0 h))
                         (degk--cable-end-touches pts loops tol))
                  (foreach cable (car *degk-cable-index*)
                    (setq cb (cadr cable))
                    (if (and (wcmatch (strcase (car cable)) "*#*X*#*")
                             (<= (cadr (cadr cb)) (+ lineY (* 0.3 h)))
                             (>= (cadr (car cb)) (- lineY (* 3.0 h)))
                             (<= (abs (- (car (car cb)) (car (car bb)))) (* 2.0 h))
                             (>= (car (car cb)) (- leftX h))
                             (<= (car (cadr cb)) (+ rightX h)))
                      (if (not (member (car cable) found)) (setq found (cons (car cable) found)))))))))))))
  (if (= (length found) 1) (car found) nil))

(defun degk--add-loop-label (pts loopName singleMark cableText / layer rise run textHeight textXOffset textYMargin shift markerLen upperY lowerY anchor z p1 p2 topPt bottomPt)
  (if (and pts (setq anchor (last pts)))
    (progn
      (setq loopName   (degk--loop-label-with-panel loopName)
            layer      "e_loop_adý"
            rise       (DEG:CFG-DK-NUM-OR 'DK_LOOP_LINE_RISE 50.0)
            run        (DEG:CFG-DK-NUM-OR 'DK_LOOP_LINE_RUN 300.0)
            textHeight (DEG:CFG-DK-NUM-OR 'DK_LOOP_TEXT_HEIGHT 13.0)
            textXOffset (DEG:CFG-DK-NUM-OR 'DK_LOOP_TEXT_X_OFFSET 15.0)
            textYMargin (DEG:CFG-DK-NUM-OR 'DK_LOOP_TEXT_Y_MARGIN 5.0)
            markerLen  (DEG:CFG-DK-NUM-OR 'DK_LOOP_MARK_LENGTH 10.0)
            shift      (DEG:CFG-DK-NUM-OR 'DK_LOOP_LINE_SHIFT_X 30.0)
            upperY     (cadr (car pts))
            lowerY     (cadr anchor)
            z          (if (and (caddr anchor) (numberp (caddr anchor)))
                         (caddr anchor)
                         0.0)
            anchor     (list (+ (car anchor) shift) (cadr anchor) z)
            p1         (list (car anchor) (+ (cadr anchor) rise) z)
            p2         (list (+ (car p1) run) (cadr p1) z)
            topPt      (list (+ (car p1) textXOffset) (+ (cadr p1) textYMargin) z)
            bottomPt   (list (+ (car p1) textXOffset)
                             (- (cadr p1) textHeight textYMargin)
                             z))
      (degk--ensure-loop-layer layer)
      (degk--entmake-lwpoly (list anchor p1 p2) layer nil)
      (if (not singleMark)
        (degk--add-loop-intersection-mark
          (list (car anchor) upperY z)
          markerLen
          layer)
      )
      (degk--add-loop-intersection-mark
        (list (car anchor) lowerY z)
        markerLen
        layer)
      (degk--add-loop-text topPt loopName layer textHeight)
      (degk--add-loop-text
        bottomPt
        cableText
        layer
        textHeight)
    )
  )
)

(defun degk--under-top-pt (basePt / pts)
  (setq pts
    (degk--under-pts basePt
      (DEG:CFG-DK-NUM-OR 'DK_UNDER_X1 10.0)
      (DEG:CFG-DK-NUM-OR 'DK_UNDER_X2 10.0)
      (DEG:CFG-DK-NUM-OR 'DK_UNDER_W 70.0)
      (DEG:CFG-DK-NUM-OR 'DK_UNDER_H 60.0)
    )
  )
  (if (and pts (cadr pts)) (cadr pts) basePt)
)

(defun degk--rgb-string->420 (s / parts r g b)
  (if (and (= (type s) 'STR) (vl-string-search "," s))
    (progn
      (setq parts (degk--split-commas s))
      (if (= (length parts) 3)
        (progn
          (setq r (fix (atof (nth 0 parts))))
          (setq g (fix (atof (nth 1 parts))))
          (setq b (fix (atof (nth 2 parts))))
          (if (and (<= 0 r) (<= r 255) (<= 0 g) (<= g 255) (<= 0 b) (<= b 255))
            (+ (* r 65536) (* g 256) b)
          )
        )
      )
    )
  )
)

(defun degk--color-dxfs-from-layer (lay / rec c420 c62 aci)
  (setq rec (if (and lay (= (type lay) 'STR) (/= lay "")) (tblsearch "LAYER" lay)))
  (cond
    ((and rec (setq c420 (assoc 420 rec)))
      (setq c62 (assoc 62 rec))
      (setq aci (if c62 (abs (cdr c62)) 256))
      (list (cons 62 aci) c420)
    )
    ((and rec (setq c62 (assoc 62 rec)))
      (list (cons 62 (abs (cdr c62))))
    )
    (T '((62 . 256)))
  )
)

(defun degk--color-dxfs-from-entity (ent lay / ed c420 c62 aci)
  (setq ed (if ent (entget ent)))
  (cond
    ((and ed (setq c420 (assoc 420 ed)))
      (setq c62 (assoc 62 ed))
      (setq aci (if c62 (cdr c62) 256))
      (list (cons 62 aci) c420)
    )
    ((and ed (setq c62 (assoc 62 ed)))
      (setq aci (cdr c62))
      (if (or (null aci) (= aci 256) (= aci 0))
        (degk--color-dxfs-from-layer lay)
        (list (cons 62 aci))
      )
    )
    (T (degk--color-dxfs-from-layer lay))
  )
)

(defun degk--normalize-color-dxfs (color / rgb)
  (cond
    ((and color (listp color) (listp (car color))) color)
    ((setq rgb (degk--rgb-string->420 color)) (list '(62 . 256) (cons 420 rgb)))
    ((numberp color) (list (cons 62 (fix color))))
    (T '((62 . 256)))
  )
)

(defun degk--entmake-lwpoly (pts layer color / data colorData)
  (setq colorData (degk--normalize-color-dxfs color))
  (setq data
    (append
      (list
        '(0 . "LWPOLYLINE")
        '(100 . "AcDbEntity")
        (cons 8 layer)
      )
      colorData
      (list
        '(100 . "AcDbPolyline")
        (cons 90 (length pts))
        (cons 70 0)
      )
      (mapcar (function (lambda (p) (cons 10 (list (car p) (cadr p))))) pts)
    )
  )
  (entmake data)
)

(defun degk--entmake-lwpoly-bulges (pts bulges layer color / data colorData i p b)
  (setq colorData (degk--normalize-color-dxfs color)
        data
          (append
            (list
              '(0 . "LWPOLYLINE")
              '(100 . "AcDbEntity")
              (cons 8 layer))
            colorData
            (list
              '(100 . "AcDbPolyline")
              (cons 90 (length pts))
              (cons 70 0)))
        i 0)
  (foreach p pts
    (setq b (if (and bulges (numberp (nth i bulges))) (nth i bulges) 0.0)
          data
            (append data
              (list
                (cons 10 (list (car p) (cadr p)))
                (cons 42 b)))
          i (1+ i)))
  (entmake data)
)

(defun degk--ensure-layer (layName / doc lays lay)
  (setq doc  (vla-get-ActiveDocument (vlax-get-acad-object)))
  (setq lays (vla-get-Layers doc))
  (setq lay (vl-catch-all-apply 'vla-Item (list lays layName)))
  (if (vl-catch-all-error-p lay)
    (vla-Add lays layName)
  )
  layName
)



(defun degk--safe-layer-object (layName / doc lays lay)
  (if (and layName (= (type layName) 'STR) (/= layName ""))
    (progn
      (setq doc  (vla-get-ActiveDocument (vlax-get-acad-object)))
      (setq lays (vla-get-Layers doc))
      (setq lay (vl-catch-all-apply 'vla-Item (list lays layName)))
      (if (vl-catch-all-error-p lay)
        (setq lay (vl-catch-all-apply 'vla-Add (list lays layName)))
      )
      (if (vl-catch-all-error-p lay) nil lay)
    )
  )
)

(defun degk--ensure-layer-editable (layName / lay)
  (setq lay (degk--safe-layer-object layName))
  (if lay
    (progn
      (vl-catch-all-apply 'vla-put-LayerOn (list lay :vlax-true))
      (vl-catch-all-apply 'vla-put-Freeze  (list lay :vlax-false))
      (vl-catch-all-apply 'vla-put-Lock    (list lay :vlax-false))
    )
  )
  layName
)

(defun degk--safe-put-layer (obj layName / res)
  (if (and obj layName (/= layName ""))
    (progn
      (degk--ensure-layer-editable layName)
      (setq res (vl-catch-all-apply 'vla-put-Layer (list obj layName)))
      (not (vl-catch-all-error-p res))
    )
  )
)

(defun degk--att-list (blkObj / raw hv)
  (setq raw nil)
  (if (and blkObj (= (type blkObj) 'VLA-OBJECT)
           (vlax-method-applicable-p blkObj 'GetAttributes))
    (progn
      (setq hv (vl-catch-all-apply 'vla-get-HasAttributes (list blkObj)))
      (if (and (not (vl-catch-all-error-p hv)) (= hv :vlax-true))
        (setq raw (vl-catch-all-apply 'vlax-invoke (list blkObj 'GetAttributes)))
      )
    )
  )
  (cond
    ((vl-catch-all-error-p raw) nil)
    ((= (type raw) 'VARIANT)  (degk--sa->list (vlax-variant-value raw)))
    ((= (type raw) 'SAFEARRAY) (vlax-safearray->list raw))
    ((listp raw) raw)
    (T nil)
  )
)

(defun degk--make-object-and-atts-editable (obj / lay atts a)
  (if (and obj (= (type obj) 'VLA-OBJECT))
    (progn
      (setq lay (vl-catch-all-apply 'vla-get-Layer (list obj)))
      (if (not (vl-catch-all-error-p lay))
        (degk--ensure-layer-editable lay)
      )
      (setq atts (degk--att-list obj))
      (foreach a atts
        (setq lay (vl-catch-all-apply 'vla-get-Layer (list a)))
        (if (not (vl-catch-all-error-p lay))
          (degk--ensure-layer-editable lay)
        )
      )
    )
  )
  obj
)

(defun degk--clean-text (s /)
  (if (null s) (setq s ""))
  (if (/= (type s) 'STR) (setq s (vl-princ-to-string s)))
  (while (vl-string-search "\\P" s) (setq s (vl-string-subst " " "\\P" s)))
  (while (vl-string-search "\\p" s) (setq s (vl-string-subst " " "\\p" s)))
  (while (vl-string-search (chr 13) s) (setq s (vl-string-subst " " (chr 13) s)))
  (while (vl-string-search (chr 10) s) (setq s (vl-string-subst " " (chr 10) s)))
  (while (vl-string-search (chr 9) s)  (setq s (vl-string-subst " " (chr 9) s)))
  (while (vl-string-search "  " s) (setq s (vl-string-subst " " "  " s)))
  (vl-string-trim " " s)
)

(defun degk--first-n (lst n / out i)
  (setq out nil i 0)
  (while (and lst (< i n))
    (setq out (cons (car lst) out))
    (setq lst (cdr lst))
    (setq i (1+ i))
  )
  (reverse out)
)

(defun degk--limit-sira-list (lst / maxN)
  (setq maxN (fix (DEG:CFG-NUM-OR 'DK_MAX_SIRA_EXPAND 1000.0)))
  (if (< maxN 1) (setq maxN 1000))
  (if (and lst (> (length lst) maxN))
    (progn
      (princ (strcat "\nDK: SIRA_NO seri acilimi " (itoa (length lst)) " adet. Ilk " (itoa maxN) " kopya alinacak."))
      (degk--first-n lst maxN)
    )
    lst
  )
)

(defun degk--make-scale-positive (blk / prop value)
  (if (and blk (= (type blk) 'VLA-OBJECT))
    (foreach prop '(XScaleFactor YScaleFactor ZScaleFactor)
      (if (vlax-property-available-p blk prop T)
        (progn
          (setq value (vl-catch-all-apply 'vlax-get-property (list blk prop)))
          (if (and (not (vl-catch-all-error-p value)) (numberp value))
            (vl-catch-all-apply 'vlax-put-property (list blk prop (abs value)))
          )
        )
      )
    )
  )
  blk
)

(defun degk--scale-room-block (blk factor / prop value)
  ;; AutoCAD SCALE factoru gibi mevcut mutlak X/Y/Z olceklerini carp.
  (if (and blk (= (type blk) 'VLA-OBJECT)
           (numberp factor) (> factor 0.0))
    (foreach prop '(XScaleFactor YScaleFactor ZScaleFactor)
      (if (vlax-property-available-p blk prop T)
        (progn
          (setq value (vl-catch-all-apply 'vlax-get-property (list blk prop)))
          (if (and (not (vl-catch-all-error-p value)) (numberp value))
            (vl-catch-all-apply
              'vlax-put-property
              (list blk prop (* factor (abs value)))))))))
  blk
)

(defun degk--copy-room-block-safe (sourceEnt targetPt / sourceObj copyObj fromPt res)
  ;; Elektrik odasi kopyasinda kaynak layer ve attribute degerleri korunur.
  (setq copyObj nil)
  (if (and sourceEnt targetPt)
    (progn
      (setq sourceObj
        (vl-catch-all-apply 'vlax-ename->vla-object (list sourceEnt)))
      (if (not (vl-catch-all-error-p sourceObj))
        (progn
          (setq res
            (vl-catch-all-apply
              (function
                (lambda ()
                  (degk--make-object-and-atts-editable sourceObj)
                  (setq copyObj (vla-Copy sourceObj))
                  (degk--scale-room-block copyObj 2.0)
                  (degk--make-object-and-atts-editable copyObj)
                  (setq fromPt (deg-get-inspt copyObj))
                  (if fromPt
                    (vla-Move
                      copyObj
                      (vlax-3d-point fromPt)
                      (vlax-3d-point targetPt))
                    (error "Elektrik odasi block insertion noktasi okunamadi."))
                  (if (vlax-property-available-p copyObj 'Rotation T)
                    (vla-put-Rotation copyObj 0.0))
                  copyObj))
              '()))
          (if (vl-catch-all-error-p res)
            (progn
              (if copyObj
                (vl-catch-all-apply 'vla-Delete (list copyObj)))
              (setq copyObj nil)))))))
  copyObj
)

(defun degk--copy-dk-block-safe (blkObj baseW siraOne / res msg copyObj copyE fromPt textBase dY safeSira nm)
  (setq *DEG_DK_LAST_COPY_OBJ* nil)
  (setq safeSira (degk--clean-text siraOne))
  (setq res
    (vl-catch-all-apply
      (function
        (lambda ()
          (degk--make-object-and-atts-editable blkObj)
          (setq copyObj (vla-Copy blkObj))
          (degk--make-scale-positive copyObj)
          (degk--safe-put-layer copyObj (DEG:VAL 'O2))
          (degk--make-object-and-atts-editable copyObj)
          (setq fromPt (deg-get-inspt copyObj))
          (if fromPt
            (vla-Move copyObj (vlax-3d-point fromPt) (vlax-3d-point baseW))
          )
          (if (vlax-property-available-p copyObj 'Rotation)
            (vl-catch-all-apply 'vla-put-Rotation (list copyObj 0.0))
          )
          (setq copyE (vlax-vla-object->ename copyObj))
          (degk--reset-insert-attrs copyE)
          (degk--make-object-and-atts-editable copyObj)
          (if (/= safeSira "")
            (degk--set-att copyObj "SIRA_NO" safeSira)
          )
          (degk--set-att copyObj "ADET" "")
          (setq dY (degk--calc-dy-to-touch-underline copyObj baseW))
          (if (/= dY 0.0)
            (vla-Move copyObj (vlax-3d-point '(0 0 0)) (vlax-3d-point (list 0.0 dY 0.0)))
          )
          (if (not (degkk--active-p))
            (progn
              (setq textBase (degk--under-top-pt baseW))
              (degk--add-text textBase safeSira (DEG:VAL 'O1))
            )
          )
          (degk--set-att copyObj "SIRA_NO" "")
          (setq *DEG_DK_LAST_COPY_OBJ* copyObj)
          T
        )
      )
      '()
    )
  )
  (if (vl-catch-all-error-p res)
    (progn
      (if (and copyObj (= (type copyObj) 'VLA-OBJECT))
        (vl-catch-all-apply 'vla-Delete (list copyObj))
      )
      (setq *DEG_DK_LAST_COPY_OBJ* nil)
      (setq msg (vl-catch-all-error-message res))
      (setq nm (degk--blockname blkObj))
      (if (null nm) (setq nm "<BLOCK>"))
      (princ (strcat "\nDK: " nm " atlandi. Sebep: " msg))
      nil
    )
    T
  )
)

(defun degk--ensure-textstyle (styName fontFile / rec en ed)
  (if (and styName fontFile)
    (progn
      (setq rec (tblsearch "STYLE" styName))
      (if (not rec)
        (entmake
          (list
            (cons 0 "STYLE")
            (cons 2 styName)
            (cons 70 0)
            (cons 40 0.0)
            (cons 41 1.0)
            (cons 50 0.0)
            (cons 71 0)
            (cons 42 0.0)
            (cons 3 fontFile)
            (cons 4 "")
          )
        )
        ;; style varsa ama font farkliysa guncelle
        (progn
          (setq en (tblobjname "STYLE" styName))
          (if en
            (progn
              (setq ed (entget en))
              (if (and ed (assoc 3 ed) (/= (cdr (assoc 3 ed)) fontFile))
                (progn
                  (setq ed (subst (cons 3 fontFile) (assoc 3 ed) ed))
                  (entmod ed)
                  (entupd en)
                )
              )
            )
          )
        )
      )
    )
  )
  styName
)


(defun degk--layer-visible-p (doc layName / lays lay)
  (setq lays (vla-get-Layers doc))
  (setq lay  (vl-catch-all-apply 'vla-Item (list lays layName)))
  (if (vl-catch-all-error-p lay)
    T
    (and (= :vlax-false (vla-get-Freeze lay))
         (= :vlax-true  (vla-get-LayerOn lay)))
  )
)

(defun degk--bbox-include-obj-p (obj / n)
  (setq n (vla-get-ObjectName obj))
  (not (member n '("AcDbText" "AcDbMText" "AcDbAttribute" "AcDbAttributeDefinition")))
)

(defun degk--min (a b) (if (< a b) a b))
(defun degk--max (a b) (if (> a b) a b))

(defun degk--bbox-union (bb1 bb2 / a1 b1 a2 b2)
  (if (null bb1) bb2
    (if (null bb2) bb1
      (progn
        (setq a1 (car bb1) b1 (cadr bb1))
        (setq a2 (car bb2) b2 (cadr bb2))
        (list
          (list (degk--min (car a1) (car a2))
                (degk--min (cadr a1) (cadr a2))
                (degk--min (caddr a1) (caddr a2)))
          (list (degk--max (car b1) (car b2))
                (degk--max (cadr b1) (cadr b2))
                (degk--max (caddr b1) (caddr b2)))
        )
      )
    )
  )
)

(defun degk--sa->list (x)
  (cond
    ((= (type x) 'VARIANT)  (degk--sa->list (vlax-variant-value x)))
    ((= (type x) 'SAFEARRAY) (vlax-safearray->list x))
    ((listp x) x)
    (t nil)
  )
)

(defun degk--ent-bbox (vlaEnt / vmin vmax minL maxL)
  (setq vmin nil vmax nil)
  (if (not (vl-catch-all-error-p (vl-catch-all-apply 'vla-GetBoundingBox (list vlaEnt 'vmin 'vmax))))
    (progn
      (setq minL (degk--sa->list vmin))
      (setq maxL (degk--sa->list vmax))
      (if (and minL maxL)
        (list
          (list (car minL) (cadr minL) (if (caddr minL) (caddr minL) 0.0))
          (list (car maxL) (cadr maxL) (if (caddr maxL) (caddr maxL) 0.0))
        )
        nil
      )
    )
    nil
  )
)


(defun degk--bbox-from-pts (pts / bb p z)
  (setq bb nil)
  (foreach p pts
    (if p
      (progn
        (setq z (if (caddr p) (caddr p) 0.0))
        (setq bb
          (degk--bbox-union
            bb
            (list (list (car p) (cadr p) z)
                  (list (car p) (cadr p) z))
          )
        )
      )
    )
  )
  bb
)

(defun degk--bbox-transform (bb ip sx sy sz rot / a b)
  (if (and bb ip)
    (progn
      (setq a (car bb))
      (setq b (cadr bb))
      (degk--bbox-from-pts
        (list
          (degk--xf-pt (list (car a) (cadr a) (caddr a)) ip sx sy sz rot)
          (degk--xf-pt (list (car b) (cadr a) (caddr a)) ip sx sy sz rot)
          (degk--xf-pt (list (car b) (cadr b) (caddr b)) ip sx sy sz rot)
          (degk--xf-pt (list (car a) (cadr b) (caddr b)) ip sx sy sz rot)
        )
      )
    )
  )
)

(defun degk--get-bbox-visible-by-blockdef (blkRef / doc insE insD blkName ip rot sx sy sz btr e d obj bb bbO bbW)
  (setq doc (vla-get-ActiveDocument (vlax-get-acad-object)))
  (setq insE
    (cond
      ((= (type blkRef) 'ENAME) blkRef)
      ((= (type blkRef) 'VLA-OBJECT)
        (vl-catch-all-apply 'vlax-vla-object->ename (list blkRef))
      )
    )
  )
  (if (vl-catch-all-error-p insE) (setq insE nil))
  (if (and insE (setq insD (entget insE)) (= (cdr (assoc 0 insD)) "INSERT"))
    (progn
      (setq blkName (cdr (assoc 2 insD)))
      (setq ip  (cdr (assoc 10 insD)))
      (setq rot (cdr (assoc 50 insD))) (if (null rot) (setq rot 0.0))
      (setq sx  (cdr (assoc 41 insD))) (if (null sx) (setq sx 1.0))
      (setq sy  (cdr (assoc 42 insD))) (if (null sy) (setq sy sx))
      (setq sz  (cdr (assoc 43 insD))) (if (null sz) (setq sz 1.0))
      (setq btr (tblobjname "BLOCK" blkName))
      (if (null btr)
        (progn
          (setq obj (vl-catch-all-apply 'vlax-ename->vla-object (list insE)))
          (if (not (vl-catch-all-error-p obj))
            (progn
              (setq blkName (degk--blockname obj))
              (if blkName (setq btr (tblobjname "BLOCK" blkName)))
            )
          )
        )
      )
      (if btr
        (progn
          (setq bb nil)
          (setq e (entnext btr))
          (while (and e (/= (cdr (assoc 0 (entget e))) "ENDBLK"))
            (setq d (entget e))
            (setq obj (vl-catch-all-apply 'vlax-ename->vla-object (list e)))
            (if (and (not (vl-catch-all-error-p obj))
                     (degk--layer-visible-p doc (cdr (assoc 8 d)))
                     (degk--bbox-include-obj-p obj))
              (progn
                (setq bbO (degk--ent-bbox obj))
                (setq bbW (degk--bbox-transform bbO ip sx sy sz rot))
                (if bbW (setq bb (degk--bbox-union bb bbW)))
              )
            )
            (setq e (entnext e))
          )
          bb
        )
      )
    )
  )
)

(defun degk--get-bbox-visible-by-explode (blkRef / doc arr lst bb o bbO)
  (setq doc (vla-get-ActiveDocument (vlax-get-acad-object)))
  (setq arr (vl-catch-all-apply 'vla-Explode (list blkRef)))
  (if (vl-catch-all-error-p arr)
    nil
    (progn
      (setq lst (vlax-safearray->list (vlax-variant-value arr)))
      (setq bb nil)
      (foreach o lst
        (if (and (degk--layer-visible-p doc (vla-get-Layer o))
                 (degk--bbox-include-obj-p o))
          (progn
            (setq bbO (degk--ent-bbox o))
            (if bbO (setq bb (degk--bbox-union bb bbO)))
          )
        )
      )
      (foreach o lst (vl-catch-all-apply 'vla-Delete (list o)))
      bb
    )
  )
)

(defun degk--monitor-plan-primitive-p (obj / n)
  ;; Kolon semasi baglantisinda yalniz plan sembolunu olusturan gercek
  ;; cizgisel geometriler sinira katilir. POINT, TEXT, ATTRIB, HATCH ve
  ;; yardimci/proxy nesneler hedef kenarini degistiremez.
  (setq n (vl-catch-all-apply 'vla-get-ObjectName (list obj)))
  (and
    (not (vl-catch-all-error-p n))
    (member n
      '("AcDbLine"
        "AcDbPolyline"
        "AcDb2dPolyline"
        "AcDb3dPolyline"
        "AcDbArc"
        "AcDbCircle"
        "AcDbEllipse"
        "AcDbSpline"
        "AcDbRegion"
        "AcDbSolid"
        "AcDbTrace"
        "AcDbFace")))
)

(defun degk--monitor-plan-bbox-from-object
  (obj doc depth / n lay bb mn mx dx dy arr lst child childBB)
  (setq n (vl-catch-all-apply 'vla-get-ObjectName (list obj)))
  (if (vl-catch-all-error-p n) (setq n ""))
  (cond
    ((degk--monitor-plan-primitive-p obj)
      (setq lay (vl-catch-all-apply 'vla-get-Layer (list obj)))
      (if (and (not (vl-catch-all-error-p lay))
               (degk--layer-visible-p doc lay))
        (progn
          (setq bb (degk--ent-bbox obj))
          ;; Sifir boyutlu yardimci LINE/POINT benzeri kayitlari da ele.
          (if bb
            (progn
              (setq mn (car bb)
                    mx (cadr bb)
                    dx (abs (- (car mx) (car mn)))
                    dy (abs (- (cadr mx) (cadr mn))))
              (if (> (+ dx dy) 1.0e-8) bb nil))
            nil))
        nil))
    ((and (= n "AcDbBlockReference") (< depth 6))
      ;; Ic ice sembollerde de yazilari degil, alt blocklarin plan
      ;; geometrisini hesaba kat.
      (setq arr (vl-catch-all-apply 'vla-Explode (list obj)))
      (if (vl-catch-all-error-p arr)
        nil
        (progn
          (setq lst (degk--sa->list arr)
                bb nil)
          (foreach child lst
            (setq childBB
              (degk--monitor-plan-bbox-from-object
                child doc (1+ depth)))
            (if childBB (setq bb (degk--bbox-union bb childBB))))
          (foreach child lst
            (vl-catch-all-apply 'vla-Delete (list child)))
          bb)))
    (t nil))
)

(defun degk--get-monitor-plan-bbox-by-explode
  (blkRef / doc arr lst bb obj objBB)
  ;; Gercek yapistirilmis block kopyasini acarak WCS plan sinirini bulur.
  (setq doc (vla-get-ActiveDocument (vlax-get-acad-object))
        arr (vl-catch-all-apply 'vla-Explode (list blkRef)))
  (if (vl-catch-all-error-p arr)
    nil
    (progn
      (setq lst (degk--sa->list arr)
            bb nil)
      (foreach obj lst
        (setq objBB (degk--monitor-plan-bbox-from-object obj doc 0))
        (if objBB (setq bb (degk--bbox-union bb objBB))))
      (foreach obj lst
        (vl-catch-all-apply 'vla-Delete (list obj)))
      bb))
)

(defun degk--get-monitor-plan-bbox-by-blockdef
  (blkRef / doc insE insD blkName ip rot sx sy sz btr ent data obj bb bbO bbW mn mx dx dy)
  ;; EXPLODE korumali/dinamik blockta kullanilamazsa ayni kati filtreyi
  ;; block tanimina uygula. Genel INSERT bbox'ina geri donulmez; cunku base
  ;; noktasindaki POINT/yardimci nesne hedef kenarini yanlis gosterebilir.
  (setq doc (vla-get-ActiveDocument (vlax-get-acad-object))
        insE
          (cond
            ((= (type blkRef) 'ENAME) blkRef)
            ((= (type blkRef) 'VLA-OBJECT)
              (setq obj
                (vl-catch-all-apply
                  'vlax-vla-object->ename (list blkRef)))
              (if (vl-catch-all-error-p obj) nil obj))
            (t nil))
        insD (if insE (entget insE) nil))
  (if (and insD (= (cdr (assoc 0 insD)) "INSERT"))
    (progn
      (setq blkName (cdr (assoc 2 insD))
            ip      (cdr (assoc 10 insD))
            rot     (cdr (assoc 50 insD))
            sx      (cdr (assoc 41 insD))
            sy      (cdr (assoc 42 insD))
            sz      (cdr (assoc 43 insD)))
      (if (null rot) (setq rot 0.0))
      (if (null sx)  (setq sx 1.0))
      (if (null sy)  (setq sy sx))
      (if (null sz)  (setq sz 1.0))
      (setq btr (if blkName (tblobjname "BLOCK" blkName) nil))
      (if btr
        (progn
          (setq bb nil
                ent (entnext btr))
          (while (and ent
                      (/= (cdr (assoc 0 (entget ent))) "ENDBLK"))
            (setq data (entget ent)
                  obj
                    (vl-catch-all-apply
                      'vlax-ename->vla-object (list ent)))
            (if (and (not (vl-catch-all-error-p obj))
                     (degk--layer-visible-p doc (cdr (assoc 8 data)))
                     (degk--monitor-plan-primitive-p obj))
              (progn
                (setq bbO (degk--ent-bbox obj))
                (if bbO
                  (progn
                    (setq mn (car bbO)
                          mx (cadr bbO)
                          dx (abs (- (car mx) (car mn)))
                          dy (abs (- (cadr mx) (cadr mn))))
                    (if (> (+ dx dy) 1.0e-8)
                      (progn
                        (setq bbW
                          (degk--bbox-transform
                            bbO ip sx sy sz rot))
                        (if bbW
                          (setq bb (degk--bbox-union bb bbW))))))))
            )
            (setq ent (entnext ent)))
          bb)
        nil))
    nil)
)

(defun degk--calc-dy-to-touch-underline (blkObj baseW / bb minp minY targetY)
  (setq bb (degk--get-bbox-visible-by-blockdef blkObj))
  (if (null bb)
    (setq bb (degk--ent-bbox blkObj))
  )
  (if (null bb)
    0.0
    (progn
      (setq minp (car bb))
      (setq minY (cadr minp))
      (setq targetY
        (- (cadr baseW) (* 20.0 (DEG:PLAN-UNIT-SCALE))))
      (- targetY minY)
    )
  )
)


(defun degk--add-text (insPt txt lay / doc ms p tx z res)
  (vl-load-com)
  (setq txt (degk--clean-text txt))
  (if (and insPt txt (/= txt ""))
    (progn
      (setq doc (vla-get-ActiveDocument (vlax-get-acad-object)))
      (setq ms  (vla-get-ModelSpace doc))

      (degk--ensure-textstyle "STANDARD" "arial.ttf")
      (if lay (degk--ensure-layer-editable lay))

      (setq z (if (caddr insPt) (caddr insPt) 0.0))
      (setq p (list (car insPt) (+ (cadr insPt) (DEG:CFG-DK-NUM-OR 'DK_TEXT_OFFSET_Y 90.0)) z))

      (setq res (vl-catch-all-apply 'vla-AddText (list ms txt (vlax-3d-point p) (DEG:CFG-DK-NUM-OR 'DK_TEXT_HEIGHT 25.0))))
      (if (vl-catch-all-error-p res)
        (progn
          (princ (strcat "\nDK: SIRA_NO texti yazilamadi. Sebep: " (vl-catch-all-error-message res)))
          nil
        )
        (progn
          (setq tx res)
          (if lay (vl-catch-all-apply 'vla-put-Layer (list tx lay)))
          (if (vlax-property-available-p tx 'StyleName)
            (vl-catch-all-apply 'vla-put-StyleName (list tx "STANDARD"))
          )
          (if (vlax-property-available-p tx 'Rotation)
            (vl-catch-all-apply 'vla-put-Rotation (list tx (/ pi 2.0)))
          )
          (if (vlax-property-available-p tx 'Alignment)
            (progn
              (vl-catch-all-apply 'vla-put-Alignment (list tx acAlignmentMiddleLeft))
              (vl-catch-all-apply 'vla-put-TextAlignmentPoint (list tx (vlax-3d-point p)))
            )
          )
          tx
        )
      )
    )
  )
)

(defun degk--normal-area-layer-p (layer / dkAreaHit dkAreaPattern)
  (setq dkAreaHit nil)
  (foreach dkAreaPattern (DEG:CFG-LIST 'DK_NORMAL_AREA_LAYERS)
    (if (and dkAreaPattern (/= dkAreaPattern "") (deg-wcmatch layer dkAreaPattern))
      (setq dkAreaHit T)
    )
  )
  dkAreaHit
)

(defun degk--fire-line-layer-p (layer)
  (and layer
       (or (deg-wcmatch layer "*FIRE*LINE*")
           (deg-wcmatch layer "*YANGIN*HAT*")))
)

(defun degk--curve-length-safe (ent / endParam curveLen)
  (setq endParam
    (vl-catch-all-apply 'vlax-curve-getEndParam (list ent)))
  (if (vl-catch-all-error-p endParam)
    nil
    (progn
      (setq curveLen
        (vl-catch-all-apply
          'vlax-curve-getDistAtParam
          (list ent endParam)))
      (if (or (vl-catch-all-error-p curveLen)
              (not (numberp curveLen)))
        nil
        curveLen)
    )
  )
)

(defun degk--normal-area-fire-length-ok-p (ent layer / curveLen minLen)
  (if (not (degk--fire-line-layer-p layer))
    T
    (progn
      ;; Ayar tabani cm'dir: 10000 mm = 1000 cm.
      (setq curveLen (degk--curve-length-safe ent)
            minLen   (* 1000.0 (DEG:PLAN-UNIT-SCALE)))
      (and (numberp curveLen) (> curveLen minLen))
    )
  )
)

(defun degk--normal-area-loop-entity-p (ent / ed entType layer)
  (setq ed      (if ent (entget ent) nil)
        entType (if ed (cdr (assoc 0 ed)) nil)
        layer   (if ed (cdr (assoc 8 ed)) nil))
  (and layer
       (or (= entType "LWPOLYLINE") (= entType "POLYLINE"))
       (degk--normal-area-layer-p layer)
       (degk--normal-area-fire-length-ok-p ent layer))
)

(defun degk--monitor-link-blocks (plEnt tol / plObj bb mn mx pad p1 p2 ss i ent blkObj out)
  ;; Butun plandaki INSERT'leri VLA nesnesine cevirmek buyuk cizimlerde ilk
  ;; DK calismasinda ActiveX bellegini zorlayabiliyor. Yalniz bu yardimci
  ;; polyline'in gorunur cevresindeki blocklari tara.
  (setq plObj
    (cond
      ((= (type plEnt) 'VLA-OBJECT) plEnt)
      ((= (type plEnt) 'ENAME)
        (setq plObj
          (vl-catch-all-apply 'vlax-ename->vla-object (list plEnt)))
        (if (vl-catch-all-error-p plObj) nil plObj))
      (T nil)))
  (if (not (numberp tol)) (setq tol 0.0))
  (setq bb (if plObj (degk--ent-bbox plObj) nil)
        pad (max (abs tol) (* 5.0 (DEG:PLAN-UNIT-SCALE))))
  (if bb
    (progn
      (setq mn (car bb)
            mx (cadr bb)
            p1 (list (- (car mn) pad) (- (cadr mn) pad))
            p2 (list (+ (car mx) pad) (+ (cadr mx) pad))
            ss (ssget "_C" p1 p2 '((0 . "INSERT")))))
  )
  (setq i 0)
  (if ss
    (while (< i (sslength ss))
      (setq ent    (ssname ss i)
            blkObj (if ent
                     (vl-catch-all-apply
                       'vlax-ename->vla-object (list ent))
                     nil))
      (if (and blkObj
               (not (vl-catch-all-error-p blkObj))
               (not (DEG:IGNORE-BLOCK-OBJ? blkObj)))
        (setq out (cons blkObj out)))
      (setq i (1+ i)))
  )
  (reverse out)
)

(defun degk--monitor-source-on-aux-polyline
  (plEnt blockObjs tol / blkObj score best bestScore)
  ;; Ayni yardimci hatta yakin birden fazla monitor varsa gercek hat ucuna
  ;; en iyi temas eden monitor kaynak kabul edilir.
  (foreach blkObj blockObjs
    (if (degk--monitor-module-p blkObj)
      (progn
        (setq score
          (degk--flasher-terminal-endpoint-score plEnt blkObj tol))
        (if (and (numberp score)
                 (or (null bestScore) (< score bestScore)))
          (setq best blkObj
                bestScore score)))))
  best
)

(defun degk--monitor-endpoint-block-score
  (plEnt blkObj targetPt / exactTol bb plObj res lst p gap ins score best exploded obj cp)
  ;; Bbox yalniz hizli on elemedir. Kabul icin polyline'in hedef ucu blok
  ;; geometrisiyle gercekten kesismeli veya patlatilmis egriye oturmalidir.
  (setq exactTol
          (max 0.000001 (* 0.01 (DEG:PLAN-UNIT-SCALE)))
        bb (degk--get-bbox-visible-by-blockdef blkObj))
  (if (null bb) (setq bb (degk--ent-bbox blkObj)))
  (if (and targetPt
           bb
           (degk--point-in-bbox-tol-p targetPt bb exactTol))
    (progn
      (setq plObj
        (cond
          ((= (type plEnt) 'VLA-OBJECT) plEnt)
          ((= (type plEnt) 'ENAME)
            (setq res
              (vl-catch-all-apply
                'vlax-ename->vla-object (list plEnt)))
            (if (vl-catch-all-error-p res) nil res))
          (T nil)))
      ;; Once blok referansi ile gercek IntersectWith noktalarinin tamamini
      ;; tara; hattin ortasindaki kesisimler hedef uca uzak oldugu icin elenir.
      (if plObj
        (progn
          (setq res
            (vl-catch-all-apply
              'vlax-invoke
              (list plObj 'IntersectWith blkObj 0)))
          (if (not (vl-catch-all-error-p res))
            (progn
              (setq lst (vl-catch-all-apply 'DEG:PT->LIST (list res)))
              (if (vl-catch-all-error-p lst) (setq lst nil))
              (while (and (listp lst) (>= (length lst) 2))
                (setq p
                  (list
                    (nth 0 lst)
                    (nth 1 lst)
                    (if (and (>= (length lst) 3)
                             (numberp (nth 2 lst)))
                      (nth 2 lst)
                      (if (caddr targetPt) (caddr targetPt) 0.0)))
                  gap (distance targetPt p))
                (if (<= gap exactTol)
                  (setq best gap))
                (setq lst
                  (if (>= (length lst) 3) (cdddr lst) nil)))))))
      ;; GstarCAD blok referansi IntersectWith desteklemiyorsa, yalniz bbox
      ;; adayini gecici patlatip ucun gercek egriye oturdugunu dogrula.
      (if (null best)
        (progn
          (setq exploded (degw-explode->list blkObj))
          (foreach obj exploded
            (if (degw-entity-eligible-for-bbox-p obj)
              (progn
                (setq cp
                  (vl-catch-all-apply
                    'vlax-curve-getClosestPointTo
                    (list obj targetPt)))
                (if (not (vl-catch-all-error-p cp))
                  (progn
                    (setq gap (distance targetPt cp))
                    (if (and (<= gap exactTol)
                             (or (null best) (< gap best)))
                      (setq best gap)))))))
          (degw-delete-objects exploded)))
      (if (numberp best)
        (progn
          (setq ins (deg-get-inspt blkObj)
                score
                  (+ best
                     (if ins
                       (* 1.0e-6 (distance targetPt ins))
                       0.0)))
          score)
        nil))
    nil)
)

(defun degk--monitor-target-on-aux-polyline
  (plEnt monitorObj blockObjs tol / sourcePt sourceDist totalLen sp ep targetPt blkObj score best bestScore)
  ;; Hattin ortasinda kesistigi blocklar hedef degildir. Monitor temasinin
  ;; karsisindaki gercek polyline ucuna degmis tek block hedef kabul edilir.
  (setq sourcePt
    (degk--flasher-terminal-contact-point plEnt monitorObj tol))
  (if sourcePt
    (progn
      (setq sourceDist (degk--dist-along plEnt sourcePt)
            totalLen
              (vl-catch-all-apply
                'vlax-curve-getDistAtParam
                (list plEnt (vlax-curve-getEndParam plEnt)))
            sp (vl-catch-all-apply 'vlax-curve-getStartPoint (list plEnt))
            ep (vl-catch-all-apply 'vlax-curve-getEndPoint (list plEnt)))
      (if (vl-catch-all-error-p totalLen) (setq totalLen nil))
      (if (vl-catch-all-error-p sp) (setq sp nil))
      (if (vl-catch-all-error-p ep) (setq ep nil))
      ;; Monitor hangi uca daha yakinsa hedef bunun karsisindaki uctur.
      (if (and (numberp sourceDist) (numberp totalLen) sp ep)
        (setq targetPt
          (if (<= sourceDist (* 0.5 totalLen)) ep sp)))
      (if targetPt
        (foreach blkObj blockObjs
          (if (and (not (degk--same-block-p monitorObj blkObj))
                   (setq score
                     (degk--monitor-endpoint-block-score
                       plEnt blkObj targetPt)))
            (if (or (null bestScore) (< score bestScore))
              (setq best blkObj
                    bestScore score)))))))
  best
)

(defun degk--monitor-link-records
  (rawPickset / tol blockObjs i ent ed entType sourceObj targetObj sourceHandle used out)
  ;; Yalniz alan seciminde bulunan fakat normal DK/DKK loop filtresine
  ;; girmeyen polyline'lar monitor yardimci hatti olabilir.
  (setq tol (DEG:CFG-TOL-NUM-OR 'DN_BLOCK_TOL 1.0)
        i   0)
  (if (and rawPickset (= (type rawPickset) 'PICKSET))
    (while (< i (sslength rawPickset))
      (setq ent     (ssname rawPickset i)
            ed      (if ent (entget ent) nil)
            entType (if ed (cdr (assoc 0 ed)) nil))
      (if (and ent
               (or (= entType "LWPOLYLINE") (= entType "POLYLINE"))
               (degk--curve-ok? ent)
               (not (degk--normal-area-loop-entity-p ent)))
        (progn
          (setq blockObjs (degk--monitor-link-blocks ent tol))
          (setq sourceObj
            (degk--monitor-source-on-aux-polyline
              ent blockObjs tol))
          (if sourceObj
            (progn
              (setq targetObj
                      (degk--monitor-target-on-aux-polyline
                        ent sourceObj blockObjs tol)
                    sourceHandle
                      (strcase (degkk--object-handle sourceObj)))
              (if (and targetObj
                       (/= sourceHandle "")
                       (not (member sourceHandle used)))
                (setq out  (cons (list sourceObj targetObj ent) out)
                      used (cons sourceHandle used)))))))
      (setq i (1+ i)))
  )
  (reverse out)
)

(defun degk--base-from-under-top-anchor (anchorPt / yOff len1 fixedLen z)
  ;; degk--under-top-pt hesabinin tersi: kolon grubunun gercek baseW noktasi.
  (if anchorPt
    (progn
      (setq yOff    (DEG:CFG-DK-SIGNED-NUM-OR 'DK_UNDER_Y_OFFSET 0.0)
            len1   (DEG:CFG-DK-NUM-OR 'DK_UNDER_W 70.0)
            fixedLen (* 90.0 (DEG:PLAN-UNIT-SCALE))
            z    (if (and (caddr anchorPt) (numberp (caddr anchorPt)))
                   (caddr anchorPt)
                   0.0))
      (list (car anchorPt)
            (+ (cadr anchorPt) fixedLen (- yOff) (- len1))
            z))
    nil)
)

(defun degk--monitor-linked-source-handles (links / out rec sourceObj handle)
  ;; Yardimci hatti olan monitorleri DK:BASE icindeki sembol dizilimine aktar.
  ;; Bu handle listesi, monitorun saginda ek cihaz icin tek bir normal aralik
  ;; daha ayrilmasini saglar.
  (foreach rec links
    (setq sourceObj (car rec)
          handle
            (if sourceObj
              (strcase (degkk--object-handle sourceObj))
              ""))
    (if (and (/= handle "") (not (member handle out)))
      (setq out (cons handle out))))
  out
)

(defun degk--copy-monitor-linked-block-safe
  (blkObj targetIns siraOne / res msg copyObj copyE fromPt safeSira dY textBase textBaseRoot nm)
  ;; Monitorun yanindaki cihaz kendi geometrisine gore Y kaydirilmaz; INSERT
  ;; noktasi monitor kopyasiyla ayni yatay hizada kalir.
  (setq *DEG_DK_LAST_COPY_OBJ* nil
        safeSira (degk--clean-text siraOne))
  (setq res
    (vl-catch-all-apply
      (function
        (lambda ()
          (degk--make-object-and-atts-editable blkObj)
          (setq copyObj (vla-Copy blkObj))
          (degk--make-scale-positive copyObj)
          (degk--safe-put-layer copyObj (DEG:VAL 'O2))
          (degk--make-object-and-atts-editable copyObj)
          (setq fromPt (deg-get-inspt copyObj))
          (if fromPt
            (vla-Move
              copyObj
              (vlax-3d-point fromPt)
              (vlax-3d-point targetIns)))
          (if (vlax-property-available-p copyObj 'Rotation)
            (vl-catch-all-apply 'vla-put-Rotation (list copyObj 0.0)))
          (setq copyE (vlax-vla-object->ename copyObj))
          (degk--reset-insert-attrs copyE)
          (degk--make-object-and-atts-editable copyObj)
          (if (/= safeSira "")
            (degk--set-att copyObj "SIRA_NO" safeSira))
          (degk--set-att copyObj "ADET" "")
          ;; Standart DK metninin mevcut konum mantigini koru; sadece block
          ;; insertion noktasi monitorun Y hizasindan ayrilmasin.
          (if (not (degkk--active-p))
            (progn
              (setq dY (degk--calc-dy-to-touch-underline copyObj targetIns)
                    textBaseRoot
                      (list
                        (car targetIns)
                        (- (cadr targetIns) dY)
                        (if (caddr targetIns) (caddr targetIns) 0.0))
                    textBase (degk--under-top-pt textBaseRoot))
              (degk--add-text textBase safeSira (DEG:VAL 'O1))))
          (degk--set-att copyObj "SIRA_NO" "")
          (setq *DEG_DK_LAST_COPY_OBJ* copyObj)
          T))
      '()))
  (if (vl-catch-all-error-p res)
    (progn
      (if (and copyObj (= (type copyObj) 'VLA-OBJECT))
        (vl-catch-all-apply 'vla-Delete (list copyObj)))
      (setq *DEG_DK_LAST_COPY_OBJ* nil
            msg (vl-catch-all-error-message res)
            nm (degk--blockname blkObj))
      (if (null nm) (setq nm "<BLOCK>"))
      (princ (strcat "\nDK: " nm " atlandi. Sebep: " msg))
      nil)
    T)
)

(defun degk--monitor-column-link-bbox-pts
  (monitorCopy targetCopy / monitorIns targetIns monitorBB targetBB monitorMin monitorMax targetMin targetMax yLow yHigh yCommon y1 y2 x1 x2 midX z)
  ;; Kolon semasinda cizgi blocklarin icinden degil, birbirine bakan gorunur
  ;; kenarlarindan baslayip bitsin. Dikey alanlar cakisirsa tek yatay hiza kullan.
  (setq monitorIns (if monitorCopy (deg-get-inspt monitorCopy) nil)
        targetIns  (if targetCopy (deg-get-inspt targetCopy) nil)
        ;; Gercek kopyayi gecici acarak yalniz plan sembol geometrisini kullan.
        ;; TEXT/MTEXT/ATTRIB sinirlari baglanti kenarini degistirmesin.
        monitorBB  (if monitorCopy
                     (degk--get-monitor-plan-bbox-by-explode monitorCopy)
                     nil)
        targetBB   (if targetCopy
                     (degk--get-monitor-plan-bbox-by-explode targetCopy)
                     nil))
  (if (and monitorCopy (null monitorBB))
    (setq monitorBB
      (degk--get-monitor-plan-bbox-by-blockdef monitorCopy)))
  (if (and targetCopy (null targetBB))
    (setq targetBB
      (degk--get-monitor-plan-bbox-by-blockdef targetCopy)))
  (if (and monitorIns targetIns monitorBB targetBB)
    (progn
      (setq monitorMin (car monitorBB)
            monitorMax (cadr monitorBB)
            targetMin  (car targetBB)
            targetMax  (cadr targetBB)
            yLow       (max (cadr monitorMin) (cadr targetMin))
            yHigh      (min (cadr monitorMax) (cadr targetMax))
            z          (if (caddr monitorIns) (caddr monitorIns) 0.0))
      (setq x1 (car monitorMax)
            x2 (car targetMin))
      (if (<= yLow yHigh)
        (progn
          ;; Base/INSERT Y'sini kullanma. Iki plan sembolunun ortak gorunen
          ;; yuksekliginin ortasindan tek yatay baglanti kur.
          (setq yCommon (/ (+ yLow yHigh) 2.0)
                y1 yCommon
                y2 yCommon)
          (list
            (list x1 y1 z)
            (list x2 y2 z)))
        (progn
          (setq y1 (max (cadr monitorMin)
                        (min (cadr monitorIns) (cadr monitorMax)))
                y2 (max (cadr targetMin)
                        (min (cadr targetIns) (cadr targetMax)))
                midX (/ (+ x1 x2) 2.0))
          ;; Ortak Y araligi olmayan eski blocklarda da kirilma uretme;
          ;; iki gorunen kenari tek dogru parcasi ile bagla.
          (list
            (list x1 y1 z)
            (list x2 y2 z)))))
    nil)
)

(defun degk--monitor-aux-contact-points
  (plEnt monitorObj tol / sourcePt sourceDist totalLen sp ep targetPt)
  ;; Monitoru bulmak icin kullanilan gercek plan hattinin iki temas ucunu
  ;; dondurur: (monitor-temasi hedef-block-temasi).
  (setq sourcePt
    (degk--flasher-terminal-contact-point plEnt monitorObj tol))
  (if sourcePt
    (progn
      (setq sourceDist (degk--dist-along plEnt sourcePt)
            totalLen
              (vl-catch-all-apply
                'vlax-curve-getDistAtParam
                (list plEnt (vlax-curve-getEndParam plEnt)))
            sp (vl-catch-all-apply 'vlax-curve-getStartPoint (list plEnt))
            ep (vl-catch-all-apply 'vlax-curve-getEndPoint (list plEnt)))
      (if (vl-catch-all-error-p totalLen) (setq totalLen nil))
      (if (vl-catch-all-error-p sp) (setq sp nil))
      (if (vl-catch-all-error-p ep) (setq ep nil))
      (if (and (numberp sourceDist) (numberp totalLen) sp ep)
        (setq targetPt
          (if (<= sourceDist (* 0.5 totalLen)) ep sp)))
      (if targetPt (list sourcePt targetPt) nil))
    nil)
)

(defun degk--monitor-map-contact-to-copy
  (sourceBlk copyBlk sourcePt / sourceE copyE sourceD copyD sourceIns copyIns sourceRot copyRot sourceSX sourceSY copySX copySY dx dy localX localY scaledX scaledY c s z)
  ;; Plandaki gercek block temasini block-local koordinata cevirip kolon
  ;; semasindaki kopyaya tasir. Block icindeki bbox/base yardimcilari kullanilmaz.
  (setq sourceE
    (cond
      ((= (type sourceBlk) 'ENAME) sourceBlk)
      ((= (type sourceBlk) 'VLA-OBJECT)
        (setq sourceE
          (vl-catch-all-apply
            'vlax-vla-object->ename (list sourceBlk)))
        (if (vl-catch-all-error-p sourceE) nil sourceE))
      (t nil))
    copyE
      (cond
        ((= (type copyBlk) 'ENAME) copyBlk)
        ((= (type copyBlk) 'VLA-OBJECT)
          (setq copyE
            (vl-catch-all-apply
              'vlax-vla-object->ename (list copyBlk)))
          (if (vl-catch-all-error-p copyE) nil copyE))
        (t nil))
    sourceD (if sourceE (entget sourceE) nil)
    copyD   (if copyE (entget copyE) nil))
  (if (and sourcePt sourceD copyD
           (= (cdr (assoc 0 sourceD)) "INSERT")
           (= (cdr (assoc 0 copyD)) "INSERT"))
    (progn
      (setq sourceIns (cdr (assoc 10 sourceD))
            copyIns   (cdr (assoc 10 copyD))
            sourceRot (cdr (assoc 50 sourceD))
            copyRot   (cdr (assoc 50 copyD))
            sourceSX  (cdr (assoc 41 sourceD))
            sourceSY  (cdr (assoc 42 sourceD))
            copySX    (cdr (assoc 41 copyD))
            copySY    (cdr (assoc 42 copyD)))
      (if (null sourceRot) (setq sourceRot 0.0))
      (if (null copyRot)   (setq copyRot 0.0))
      (if (or (null sourceSX) (< (abs sourceSX) 1.0e-12))
        (setq sourceSX 1.0))
      (if (or (null sourceSY) (< (abs sourceSY) 1.0e-12))
        (setq sourceSY sourceSX))
      (if (or (null copySX) (< (abs copySX) 1.0e-12))
        (setq copySX 1.0))
      (if (or (null copySY) (< (abs copySY) 1.0e-12))
        (setq copySY copySX))
      (setq dx (- (car sourcePt) (car sourceIns))
            dy (- (cadr sourcePt) (cadr sourceIns))
            c  (cos sourceRot)
            s  (sin sourceRot)
            localX (/ (+ (* c dx) (* s dy)) sourceSX)
            localY (/ (+ (* (- s) dx) (* c dy)) sourceSY)
            scaledX (* localX copySX)
            scaledY (* localY copySY)
            c (cos copyRot)
            s (sin copyRot)
            z (if (caddr copyIns) (caddr copyIns) 0.0))
      (list
        (+ (car copyIns) (- (* c scaledX) (* s scaledY)))
        (+ (cadr copyIns) (+ (* s scaledX) (* c scaledY)))
        z))
    nil)
)

(defun degk--monitor-contact-route-pts (p1 p2 / tol y midX z)
  (if (and p1 p2)
    (progn
      (setq tol (max 1.0e-8 (* 0.01 (DEG:PLAN-UNIT-SCALE)))
            z   (if (caddr p1) (caddr p1) 0.0))
      (if (<= (abs (- (cadr p1) (cadr p2))) tol)
        (progn
          (setq y (/ (+ (cadr p1) (cadr p2)) 2.0))
          (list (list (car p1) y z) (list (car p2) y z)))
        (progn
          (setq midX (/ (+ (car p1) (car p2)) 2.0))
          (list
            p1
            (list midX (cadr p1) z)
            (list midX (cadr p2) z)
            p2))))
    nil)
)

(defun degk--monitor-intersection-points (res / flat out)
  (setq flat (vl-catch-all-apply 'DEG:PT->LIST (list res)))
  (if (vl-catch-all-error-p flat) (setq flat nil))
  (while (and (listp flat) (>= (length flat) 3))
    (setq out
      (cons
        (list (nth 0 flat) (nth 1 flat) (nth 2 flat))
        out)
      flat (cdddr flat)))
  (reverse out)
)

(defun degk--monitor-ray-object-hits (rayObj obj / res)
  (setq res
    (vl-catch-all-apply
      'vlax-invoke
      (list rayObj 'IntersectWith obj 0)))
  (if (vl-catch-all-error-p res)
    nil
    (degk--monitor-intersection-points res))
)

(defun degk--monitor-ray-block-hits
  (rayObj blkObj / exploded obj objName hits directHits)
  ;; Once gercek kopyayi acip yalniz gorunur plan cizgileriyle kesistir.
  ;; Boylece block base POINT'i veya gorunmez dinamik geometri aday olamaz.
  (setq exploded (degw-explode->list blkObj)
        hits nil)
  (foreach obj exploded
    (setq objName
      (vl-catch-all-apply 'vla-get-ObjectName (list obj)))
    (if (and (not (vl-catch-all-error-p objName))
             (degw-entity-eligible-for-bbox-p obj)
             (or (degk--monitor-plan-primitive-p obj)
                 (= objName "AcDbBlockReference")))
      (setq hits
        (append hits (degk--monitor-ray-object-hits rayObj obj)))))
  (degw-delete-objects exploded)
  ;; Korumali block patlatilamiyorsa son yedek gercek IntersectWith'tir;
  ;; bbox veya INSERT/base noktasi bu akista hic kullanilmaz.
  (if (null hits)
    (setq hits (degk--monitor-ray-object-hits rayObj blkObj)))
  hits
)

(defun degk--monitor-leftmost-point (pts / best p)
  (foreach p pts
    (if (or (null best) (< (car p) (car best)))
      (setq best p)))
  best
)

(defun degk--monitor-rightmost-point (pts / best p)
  (foreach p pts
    (if (or (null best) (> (car p) (car best)))
      (setq best p)))
  best
)

(defun degk--monitor-column-link-ray-pts
  (monitorCopy targetCopy / doc ms monitorIns targetIns y z span pad xMin xMax rayObj monitorHits targetHits p1 p2)
  (setq monitorIns (if monitorCopy (deg-get-inspt monitorCopy) nil)
        targetIns  (if targetCopy (deg-get-inspt targetCopy) nil))
  (if (and monitorIns targetIns)
    (progn
      ;; Kopyalar ayni yatay hizada yerlestirilir. Isin bu hizanin fiziksel
      ;; 150 mm ustunden gecerek iki blockun gorunen kenarlarini keser.
      (setq y    (+ (/ (+ (cadr monitorIns) (cadr targetIns)) 2.0)
                     (* 15.0 (DEG:PLAN-UNIT-SCALE)))
            z    (if (caddr monitorIns) (caddr monitorIns) 0.0)
            span (abs (- (car targetIns) (car monitorIns)))
            pad  (max span (* 100.0 (DEG:PLAN-UNIT-SCALE)) 1.0)
            xMin (- (min (car monitorIns) (car targetIns)) pad)
            xMax (+ (max (car monitorIns) (car targetIns)) pad)
            doc  (vla-get-ActiveDocument (vlax-get-acad-object))
            ms   (vla-get-ModelSpace doc)
            rayObj
              (vl-catch-all-apply
                'vla-AddLine
                (list ms
                      (vlax-3d-point (list xMin y z))
                      (vlax-3d-point (list xMax y z)))))
      (if (vl-catch-all-error-p rayObj)
        nil
        (progn
          (setq monitorHits
                  (degk--monitor-ray-block-hits
                    rayObj monitorCopy)
                targetHits
                  (degk--monitor-ray-block-hits
                    rayObj targetCopy))
          (vl-catch-all-apply 'vla-Delete (list rayObj))
          (if (< (car monitorIns) (car targetIns))
            (setq p1 (degk--monitor-rightmost-point monitorHits)
                  p2 (degk--monitor-leftmost-point targetHits))
            (setq p1 (degk--monitor-leftmost-point monitorHits)
                  p2 (degk--monitor-rightmost-point targetHits)))
          (if (and p1 p2)
            ;; Son polyline kesinlikle tek yatay parca ve iki vertexlidir.
            (list (list (car p1) y z)
                  (list (car p2) y z))
            nil))))
    nil)
)

(defun degk--monitor-column-link-pts
  (monitorObj monitorCopy targetObj targetCopy sourceEnt / tol contacts p1 p2)
  ;; Kolon semasinda yon sabittir: monitorun metinsiz plan sinirinin sag
  ;; kenarindan hedef blockun metinsiz plan sinirinin sol kenarina. Kaynak
  ;; plan temas yonu ve iki blockun base noktasi bu cizgiyi etkileyemez.
  (setq p1
    (degk--monitor-column-link-ray-pts monitorCopy targetCopy))
  (if p1
    p1
    (progn
      (princ
        "\nDK: Monitor baglantisi icin gercek block kenari bulunamadi; base noktasina baglanmadi.")
      nil))
)

(defun degk--draw-monitor-column-link
  (monitorObj monitorCopy targetObj targetCopy sourceEnt / ed layer color pts)
  ;; Plan yardimci hattinin layer ve ACI/true-color bilgisini kolon semasindaki
  ;; yeni iki-noktali polyline'a aynen tasir.
  (setq ed    (if sourceEnt (entget sourceEnt) nil)
        layer (if ed (cdr (assoc 8 ed)) nil)
        color (if layer
                (degk--color-dxfs-from-entity sourceEnt layer)
                nil)
        pts
          (degk--monitor-column-link-pts
            monitorObj monitorCopy targetObj targetCopy sourceEnt))
  (if (and layer (/= layer "") pts (>= (length pts) 2))
    (degk--entmake-lwpoly pts layer color)
    nil)
)

(defun degk--place-monitor-linked-blocks
  (links / offset rec monitorObj targetObj sourceEnt copyRec copyObj targetCopy monitorIns targetIns key placed sira count)
  ;; 1000 mm = 100 cm fiziksel mesafe; PLAN mm/cm/m secimine gore cevrilir.
  (setq offset (* 100.0 (DEG:PLAN-UNIT-SCALE))
        count 0)
  (foreach rec links
    (setq monitorObj (car rec)
          targetObj  (cadr rec)
          sourceEnt  (nth 2 rec)
          copyRec    (degk--area-module-copy-get monitorObj nil)
          copyObj    (if copyRec (car copyRec) nil)
          monitorIns (if copyObj (deg-get-inspt copyObj) nil)
          key
            (strcat
              (if copyObj (strcase (degkk--object-handle copyObj)) "")
              "|"
              (if targetObj (strcase (degkk--object-handle targetObj)) "")))
    (if (and copyObj
             (= (type copyObj) 'VLA-OBJECT)
             monitorIns
             (/= key "|")
             (not (member key placed)))
      (progn
        (setq targetIns
                (list (+ (car monitorIns) offset)
                      (cadr monitorIns)
                      (if (caddr monitorIns) (caddr monitorIns) 0.0))
              sira (degk--clean-text (degk--get-att targetObj "SIRA_NO")))
        (if (degk--copy-monitor-linked-block-safe
              targetObj targetIns sira)
          (progn
            (setq targetCopy *DEG_DK_LAST_COPY_OBJ*)
            (degk--draw-monitor-column-link
              monitorObj copyObj targetObj targetCopy sourceEnt)
            (setq count  (1+ count)
                  placed (cons key placed))
            (degk--attsync-add targetObj))))))
  (if (> count 0) (degk--attsync-run))
  count
)

(defun degk--normal-area-polylines (dkAreaPickset / dkAreaResult dkAreaIndex dkAreaEnt dkAreaData dkAreaLayer dkAreaType dkAreaMatch)
  (setq dkAreaResult (ssadd))
  (if (and dkAreaPickset (= (type dkAreaPickset) 'PICKSET))
    (progn
      (setq dkAreaIndex 0)
      (while (< dkAreaIndex (sslength dkAreaPickset))
        (setq dkAreaEnt (ssname dkAreaPickset dkAreaIndex)
              dkAreaData (if dkAreaEnt (entget dkAreaEnt) nil)
              dkAreaLayer (if dkAreaData (cdr (assoc 8 dkAreaData)) nil)
              dkAreaType (if dkAreaData (cdr (assoc 0 dkAreaData)) nil)
              dkAreaMatch nil)
        (if (and dkAreaLayer
                 (or (= dkAreaType "LWPOLYLINE") (= dkAreaType "POLYLINE")))
          (setq dkAreaMatch (degk--normal-area-layer-p dkAreaLayer))
        )
        (if (and dkAreaMatch
                 (degk--normal-area-fire-length-ok-p
                   dkAreaEnt dkAreaLayer))
          (ssadd dkAreaEnt dkAreaResult)
        )
        (setq dkAreaIndex (1+ dkAreaIndex))
      )
    )
  )
  dkAreaResult
)

(defun degk--column-frame-new-entities (afterEnt / doc space owner ent data out)
  (setq doc (vla-get-ActiveDocument (vlax-get-acad-object))
        space
          (if (= (getvar "CVPORT") 1)
            (vla-get-PaperSpace doc)
            (vla-get-ModelSpace doc))
        owner (vlax-vla-object->ename space)
        ent (if afterEnt (entnext afterEnt) (entnext))
        out nil)
  (while ent
    (setq data (entget ent))
    (if (and data (eq owner (cdr (assoc 330 data))))
      (setq out (cons ent out)))
    (setq ent (entnext ent)))
  (reverse out)
)

(defun degk--column-frame-visible-curve-y-range (ent / endParam i p q dx tol lo hi)
  (if (and ent (degk--curve-ok? ent))
    (progn
      (setq endParam
        (vl-catch-all-apply 'vlax-curve-getEndParam (list ent)))
      (if (not (vl-catch-all-error-p endParam))
        (progn
          (setq i 0)
          (while (< i endParam)
            (setq p (vl-catch-all-apply 'vlax-curve-getPointAtParam (list ent i))
                  q (vl-catch-all-apply 'vlax-curve-getPointAtParam (list ent (1+ i))))
            (if (and (not (vl-catch-all-error-p p))
                     (not (vl-catch-all-error-p q))
                     p q)
              (progn
                (setq dx (- (car q) (car p))
                      tol (max 1e-6 (* 1e-6 (distance p q))))
                ;; Dikey kuyruklar cerceveyi buyutmesin; gorunen yatay/egik
                ;; parcalarin iki ucunu de gercek icerik sinirina dahil et.
                (if (> (abs dx) tol)
                  (progn
                    (if (or (null lo) (< (cadr p) lo)) (setq lo (cadr p)))
                    (if (or (null lo) (< (cadr q) lo)) (setq lo (cadr q)))
                    (if (or (null hi) (> (cadr p) hi)) (setq hi (cadr p)))
                    (if (or (null hi) (> (cadr q) hi)) (setq hi (cadr q)))))))
            (setq i (1+ i)))))))
  (if (and (numberp lo) (numberp hi)) (list lo hi) nil)
)

(defun degk--block-ocs-bbox (bb ent / lo hi x y z pts)
  ;; INSERT'in DXF 10 noktasi OCS'dedir; egik normalde WCS'ye donustur.
  (if bb
    (progn
      (setq lo (car bb) hi (cadr bb))
      (foreach x (list (car lo) (car hi))
        (foreach y (list (cadr lo) (cadr hi))
          (foreach z (list (caddr lo) (caddr hi))
            (setq pts (cons (trans (list x y z) ent 0) pts)))))
      (degk--bbox-from-pts pts))))

(defun degk--column-frame-block-local-bbox
  (blkName doc depth seen / key btr ent data typ obj one childBB childName ip rot sx sy sz bb)
  (setq key (if blkName (strcase blkName) ""))
  (if (and (/= key "")
           (< depth 8)
           (not (member key seen))
           (setq btr (tblobjname "BLOCK" blkName)))
    (progn
      (setq bb nil
            ent (entnext btr)
            seen (cons key seen))
      (while (and ent (/= (cdr (assoc 0 (entget ent))) "ENDBLK"))
        (setq data (entget ent)
              typ (cdr (assoc 0 data)))
        (cond
          ((= typ "INSERT")
            (setq childName (cdr (assoc 2 data))
                  childBB
                    (degk--column-frame-block-local-bbox
                      childName doc (1+ depth) seen))
            (if childBB
              (progn
                (setq ip (cdr (assoc 10 data))
                      rot (cdr (assoc 50 data))
                      sx (cdr (assoc 41 data))
                      sy (cdr (assoc 42 data))
                      sz (cdr (assoc 43 data)))
                (if (null ip) (setq ip '(0.0 0.0 0.0)))
                (if (null rot) (setq rot 0.0))
                (if (null sx) (setq sx 1.0))
                (if (null sy) (setq sy sx))
                (if (null sz) (setq sz 1.0))
                (setq one (degk--block-ocs-bbox
                            (degk--bbox-transform childBB ip sx sy sz rot) ent))
                (if one (setq bb (degk--bbox-union bb one))))))
          (T
            (setq obj (vl-catch-all-apply 'vlax-ename->vla-object (list ent)))
            (if (and (not (vl-catch-all-error-p obj))
                     (degk--layer-visible-p doc (cdr (assoc 8 data)))
                     (degk--monitor-plan-primitive-p obj))
              (progn
                (setq one (degk--ent-bbox obj))
                (if one (setq bb (degk--bbox-union bb one)))))))
        (setq ent (entnext ent)))
      bb)
    nil)
)

(defun degk--column-frame-block-visible-bbox (ent / data obj blkName ip rot sx sy sz localBB)
  (setq data (if ent (entget ent) nil))
  (if (and data (= (cdr (assoc 0 data)) "INSERT"))
    (progn
      (setq obj (vlax-get-acad-object)
            blkName (cdr (assoc 2 data))
            ip (cdr (assoc 10 data))
            rot (cdr (assoc 50 data))
            sx (cdr (assoc 41 data))
            sy (cdr (assoc 42 data))
            sz (cdr (assoc 43 data)))
      (if (null ip) (setq ip '(0.0 0.0 0.0)))
      (if (null rot) (setq rot 0.0))
      (if (null sx) (setq sx 1.0))
      (if (null sy) (setq sy sx))
      (if (null sz) (setq sz 1.0))
      (setq localBB
        (degk--column-frame-block-local-bbox
          blkName
          (vla-get-ActiveDocument obj)
          0
          nil))
      (if localBB
        (degk--block-ocs-bbox
          (degk--bbox-transform localBB ip sx sy sz rot) ent)
        nil))
    nil)
)

(defun degk--column-frame-bbox (entities / bb ent obj objName one frameOne yr contentMinY contentMaxY mn mx)
  (setq bb nil
        contentMinY nil
        contentMaxY nil)
  (foreach ent entities
    (if (and ent (entget ent))
      (progn
        (setq obj (vlax-ename->vla-object ent)
              objName (vla-get-ObjectName obj)
              one (degk--ent-bbox obj))
        (setq frameOne
          (if (= objName "AcDbBlockReference")
            (degk--column-frame-block-visible-bbox ent)
            one))
        (if frameOne (setq bb (degk--bbox-union bb frameOne)))
        (cond
          ((= objName "AcDbBlockReference")
            (if frameOne
              (progn
                (if (or (null contentMinY) (< (cadr (car frameOne)) contentMinY))
                  (setq contentMinY (cadr (car frameOne))))
                (if (or (null contentMaxY) (> (cadr (cadr frameOne)) contentMaxY))
                  (setq contentMaxY (cadr (cadr frameOne)))))))
          ((member objName '("AcDbText" "AcDbMText"))
            (if one
              (progn
                (if (or (null contentMinY) (< (cadr (car one)) contentMinY))
                  (setq contentMinY (cadr (car one))))
                (if (or (null contentMaxY) (> (cadr (cadr one)) contentMaxY))
                  (setq contentMaxY (cadr (cadr one)))))))
          ((setq yr (degk--column-frame-visible-curve-y-range ent))
            (if (or (null contentMinY) (< (car yr) contentMinY))
              (setq contentMinY (car yr)))
            (if (or (null contentMaxY) (> (cadr yr) contentMaxY))
              (setq contentMaxY (cadr yr))))))))
  (if bb
    (progn
      (setq mn (car bb)
            mx (cadr bb))
      (if (null contentMinY) (setq contentMinY (cadr mn)))
      (if (null contentMaxY) (setq contentMaxY (cadr mx)))
      (list
        (list (car mn) contentMinY (if (caddr mn) (caddr mn) 0.0))
        (list (car mx) contentMaxY (if (caddr mx) (caddr mx) 0.0))))
    nil)
)

(defun degk--column-frame-polyline (pts layer closed / data)
  (setq data
    (append
      (list
        '(0 . "LWPOLYLINE")
        '(100 . "AcDbEntity")
        (cons 8 layer)
        '(62 . 256)
        '(100 . "AcDbPolyline")
        (cons 90 (length pts))
        (cons 70 (if closed 1 0)))
      (mapcar
        (function (lambda (p) (cons 10 (list (car p) (cadr p)))))
        pts)))
  (entmakex data)
)

(defun degk--riser-limits-above-horizontal-p
  (riserLimits upperY lowerY / leftBottom rightBottom leftTop rightTop leftMinY leftMaxY rightMinY rightMaxY riserMidY horizontalMidY)
  (if (and (listp riserLimits)
           (>= (length riserLimits) 4)
           (listp (nth 0 riserLimits))
           (listp (nth 1 riserLimits))
           (listp (nth 2 riserLimits))
           (listp (nth 3 riserLimits)))
    (progn
      (setq leftBottom (nth 0 riserLimits)
            rightBottom (nth 1 riserLimits)
            leftTop (nth 2 riserLimits)
            rightTop (nth 3 riserLimits)
            leftMinY (min (cadr leftBottom) (cadr leftTop))
            leftMaxY (max (cadr leftBottom) (cadr leftTop))
            rightMinY (min (cadr rightBottom) (cadr rightTop))
            rightMaxY (max (cadr rightBottom) (cadr rightTop))
            horizontalMidY (/ (+ upperY lowerY) 2.0)
            riserMidY
              (/ (+ leftMinY leftMaxY rightMinY rightMaxY) 4.0))
      (cond
        ((and (> leftMinY upperY) (> rightMinY upperY)) T)
        ((and (< leftMaxY lowerY) (< rightMaxY lowerY)) nil)
        (T (> riserMidY horizontalMidY))))
    nil)
)

(defun degk--panel-riser-fillet-y
  (turnY minY maxY preferAbove radius / lo hi r candidate)
  ;; Yatay kol dik riserin disindaysa en yakin uca, icindeyse tercih edilen
  ;; yone dogru bir fillet yaricapi kadar ilerideki noktaya baglan.
  (setq lo (min minY maxY)
        hi (max minY maxY)
        r  (abs radius))
  (cond
    ((< turnY lo) lo)
    ((> turnY hi) hi)
    (preferAbove
      (setq candidate (min hi (+ turnY r)))
      (if (> candidate (+ turnY 1e-9))
        candidate
        (max lo (- turnY r))))
    (T
      (setq candidate (max lo (- turnY r)))
      (if (< candidate (- turnY 1e-9))
        candidate
        (min hi (+ turnY r)))))
)

(defun degk--make-panel-filleted-run
  (startX startY turnY targetX targetY z radius layer targetFilletP
   / xDir yDir targetYDir verticalLen targetVerticalLen horizontalLen
     firstRadius secondRadius tangentY firstArcX secondTanX secondArcY
     pts bulges beforeEnt result ent)
  ;; Panel donusunu, istenirse GF riser tarafindaki donusu da ayni
  ;; LWPOLYLINE icinde gercek 90 derece yay olarak kurar.
  (setq xDir (if (>= targetX startX) 1.0 -1.0)
        yDir (if (>= turnY startY) 1.0 -1.0)
        targetYDir (if (>= targetY turnY) 1.0 -1.0)
        verticalLen (abs (- turnY startY))
        targetVerticalLen (abs (- targetY turnY))
        horizontalLen (abs (- targetX startX))
        firstRadius
          (min (abs radius) verticalLen (/ horizontalLen 2.0))
        secondRadius
          (if targetFilletP
            (min (abs radius)
                 targetVerticalLen
                 (max 0.0 (- horizontalLen firstRadius)))
            0.0))
  (cond
    ((and (> firstRadius 1e-9) (> secondRadius 1e-9))
      (setq tangentY  (- turnY (* yDir firstRadius))
            firstArcX (+ startX (* xDir firstRadius))
            secondTanX (- targetX (* xDir secondRadius))
            secondArcY (+ turnY (* targetYDir secondRadius))
            pts
              (list
                (list startX startY z)
                (list startX tangentY z)
                (list firstArcX turnY z)
                (list secondTanX turnY z)
                (list targetX secondArcY z))
            bulges
              (list
                0.0
                (* -1.0 xDir yDir 0.414213562373095)
                0.0
                (* xDir targetYDir 0.414213562373095)
                0.0))
      (if (> (abs (- targetY secondArcY)) 1e-9)
        (setq pts (append pts (list (list targetX targetY z)))
              bulges (append bulges (list 0.0)))))
    ((> firstRadius 1e-9)
      (setq tangentY  (- turnY (* yDir firstRadius))
            firstArcX (+ startX (* xDir firstRadius))
            pts
              (list
                (list startX startY z)
                (list startX tangentY z)
                (list firstArcX turnY z)
                (list targetX turnY z))
            bulges
              (list
                0.0
                (* -1.0 xDir yDir 0.414213562373095)
                0.0 0.0))
      (if (> targetVerticalLen 1e-9)
        (setq pts (append pts (list (list targetX targetY z)))
              bulges (append bulges (list 0.0)))))
    ((> secondRadius 1e-9)
      (setq secondTanX (- targetX (* xDir secondRadius))
            secondArcY (+ turnY (* targetYDir secondRadius))
            pts
              (list
                (list startX startY z)
                (list startX turnY z)
                (list secondTanX turnY z)
                (list targetX secondArcY z))
            bulges
              (list
                0.0 0.0
                (* xDir targetYDir 0.414213562373095)
                0.0))
      (if (> (abs (- targetY secondArcY)) 1e-9)
        (setq pts (append pts (list (list targetX targetY z)))
              bulges (append bulges (list 0.0)))))
    (T
      (setq pts
              (list
                (list startX startY z)
                (list startX turnY z)
                (list targetX turnY z))
            bulges (list 0.0 0.0 0.0))
      (if (> targetVerticalLen 1e-9)
        (setq pts (append pts (list (list targetX targetY z)))
              bulges (append bulges (list 0.0))))))
  (setq beforeEnt (entlast)
        result (degk--entmake-lwpoly-bulges pts bulges layer nil)
        ent (entlast))
  (if (and result ent (not (eq beforeEnt ent))) ent nil)
)

(defun degk--vertical-riser-entity-info (ent / ed pts p x minY maxY z verticalP)
  (setq ed (if (and ent (entget ent)) (entget ent) nil)
        pts
          (if (and ed (= (cdr (assoc 0 ed)) "LWPOLYLINE"))
            (mapcar 'cdr
              (vl-remove-if-not
                (function (lambda (item) (= (car item) 10)))
                ed))
            nil))
  (if pts
    (progn
      (setq x (car (car pts))
            z 0.0
            verticalP T)
      (foreach p pts
        (if (> (abs (- (car p) x)) 1e-6) (setq verticalP nil))
        (if (or (null minY) (< (cadr p) minY)) (setq minY (cadr p)))
        (if (or (null maxY) (> (cadr p) maxY)) (setq maxY (cadr p))))
      (if verticalP (list x minY maxY z ent) nil))
    nil)
)

(defun degk--shaft-riser-infos (entities / ent info infos)
  (foreach ent entities
    (if (setq info (degk--vertical-riser-entity-info ent))
      (setq infos (cons info infos))))
  (vl-sort infos
    (function (lambda (a b) (< (car a) (car b)))))
)

(defun degk--panel-shaft-targets (shaftInfos lowerY / firstInfo secondInfo)
  ;; Her iki saft hatti da panel kollarinin ustunde basliyorsa alt kat yoktur.
  ;; Bu tek yonlu durumda paralel hatlari safta ters sirayla eslestir.
  (setq firstInfo  (car shaftInfos)
        secondInfo (cadr shaftInfos))
  (if (and firstInfo secondInfo
           (numberp lowerY)
           (numberp (cadr firstInfo))
           (numberp (cadr secondInfo))
           (>= (cadr firstInfo) (- lowerY 1e-9))
           (>= (cadr secondInfo) (- lowerY 1e-9)))
    (list secondInfo firstInfo)
    (list firstInfo secondInfo))
)

(defun degk--make-panel-shaft-branch
  (panelX panelTopY turnY shaftInfo z radius layer
   / shaftX shaftMinY shaftMaxY shaftEnt xDir endY horizontalLen verticalLen firstRadius secondRadius firstTanY firstArcX splitX upperTanY lowerTanY pts bulges beforeEnt result firstEnt secondEnt made originalData twoWayP)
  ;; Saft baglanti seviyesinin hem altinda hem ustunde devam ediyorsa yatay
  ;; kolu iki gercek fillet ile iki yone ayir. Alt kol yoksa safta kare don.
  (if (and (listp shaftInfo)
           (>= (length shaftInfo) 3)
           (numberp (car shaftInfo))
           (numberp (cadr shaftInfo))
           (numberp (nth 2 shaftInfo)))
    (progn
      (setq shaftX (car shaftInfo)
            shaftMinY (cadr shaftInfo)
            shaftMaxY (nth 2 shaftInfo)
            shaftEnt (if (> (length shaftInfo) 4) (nth 4 shaftInfo) nil)
            xDir (if (>= shaftX panelX) 1.0 -1.0)
            verticalLen (abs (- turnY panelTopY))
            horizontalLen (abs (- shaftX panelX))
            firstRadius
              (min (abs radius)
                   verticalLen
                   (/ horizontalLen 2.0))
            secondRadius
              (min
                (abs radius)
                (max 0.0 (- turnY shaftMinY))
                (max 0.0 (- shaftMaxY turnY))
                (max 0.0 (- horizontalLen firstRadius)))
            twoWayP
              (and (> firstRadius 1e-9)
                   (> secondRadius 1e-9)
                   (< shaftMinY (- turnY 1e-9))
                   (> shaftMaxY (+ turnY 1e-9))))
      (cond
        ((< turnY shaftMinY)
          (setq endY shaftMinY))
        ((> turnY shaftMaxY)
          (setq endY shaftMaxY))
        (T
          (setq endY turnY)))
      (if (> firstRadius 1e-9)
        (progn
          (setq firstTanY (- turnY firstRadius)
                firstArcX (+ panelX (* xDir firstRadius)))
          (if twoWayP
            (setq pts
                    (list
                      (list panelX firstTanY z)
                      (list firstArcX turnY z)
                      (list (- shaftX (* xDir secondRadius)) turnY z)
                      (list shaftX (+ turnY secondRadius) z)
                      (list shaftX shaftMaxY z))
                  bulges
                    (list
                      (* -1.0 xDir 0.414213562373095)
                      0.0
                      (* xDir 0.414213562373095)
                      0.0 0.0)
                  beforeEnt (entlast)
                  result (degk--entmake-lwpoly-bulges pts bulges layer nil)
                  firstEnt (entlast))
            (setq pts
                    (list
                      (list panelX firstTanY z)
                      (list firstArcX turnY z)
                      (list shaftX turnY z))
                  bulges
                    (list
                      (* -1.0 xDir 0.414213562373095)
                      0.0 0.0)
                  beforeEnt (entlast)
                  result (degk--entmake-lwpoly-bulges pts bulges layer nil)
                  firstEnt (entlast)))
          (if (and result firstEnt (not (eq beforeEnt firstEnt)))
            (setq made (list firstEnt))
            (setq made nil))
          (if (and made twoWayP)
            (progn
              (setq splitX (- shaftX (* xDir secondRadius))
                    upperTanY (+ turnY secondRadius)
                    lowerTanY (- turnY secondRadius)
                    beforeEnt (entlast)
                    result
                      (degk--entmake-lwpoly-bulges
                        (list
                          (list splitX turnY z)
                          (list shaftX lowerTanY z)
                          (list shaftX shaftMinY z))
                        (list
                          (* -1.0 xDir 0.414213562373095)
                          0.0 0.0)
                        layer nil)
                    secondEnt (entlast))
              (if (and result secondEnt (not (eq beforeEnt secondEnt)))
                (setq made (append made (list secondEnt)))
                (progn
                  (foreach firstEnt made
                    (vl-catch-all-apply 'entdel (list firstEnt)))
                  (setq made nil)))
              (if made
                (if (and shaftEnt (entget shaftEnt))
                  (progn
                    (setq originalData (entget shaftEnt))
                    (entdel shaftEnt)
                    (if (entget shaftEnt)
                      (progn
                        (foreach firstEnt made
                          (vl-catch-all-apply 'entdel (list firstEnt)))
                        (setq made nil))))))))
          ;; Tek yone devam eden safta baglanti ucunu filletsiz 90 derece tamamla.
          (if (and made (not twoWayP) (> (abs (- endY turnY)) 1e-9))
            (progn
              (setq pts
                (append pts (list (list shaftX endY z))))
              (vl-catch-all-apply 'entdel (list firstEnt))
              (setq beforeEnt (entlast)
                    result (degk--entmake-lwpoly-bulges
                             pts
                             (append bulges (list 0.0))
                             layer nil)
                    firstEnt (entlast)
                    made
                      (if (and result firstEnt (not (eq beforeEnt firstEnt)))
                        (list firstEnt)
                        nil))))
          (if made
            (list made shaftEnt originalData)
            nil))
        nil))
    nil)
)

(defun degk--first-loop-upper-mouth-y
  (loopRecords / rec y firstY firstRec pts firstPt lastPt)
  ;; GF-L01 kolon yerlesiminde geometrik olarak en alttaki ilk looptur.
  ;; YAP +2000 hizasi icin bu loopun ust agiz Y degerini dondur.
  (foreach rec loopRecords
    (setq y (degk--loop-record-mouth-y rec))
    (if (and (numberp y) (or (null firstY) (< y firstY)))
      (setq firstY y
            firstRec rec)))
  (setq pts (if (listp firstRec) (cadr firstRec) nil)
        firstPt (if (and (listp pts) (>= (length pts) 2)) (car pts) nil)
        lastPt (if (and (listp pts) (>= (length pts) 2)) (last pts) nil))
  (if (and (listp firstPt) (listp lastPt)
           (numberp (cadr firstPt)) (numberp (cadr lastPt)))
    (max (cadr firstPt) (cadr lastPt))
    nil)
)

(defun degk--room-first-loop-shift-y (panelTopY loopRecords / loopUpperY)
  (setq loopUpperY (degk--first-loop-upper-mouth-y loopRecords))
  (if (and (numberp panelTopY) (numberp loopUpperY))
    (- (+ panelTopY (* 200.0 (DEG:PLAN-UNIT-SCALE))) loopUpperY)
    nil)
)

(defun degk--entity-reference-y (ent / ed item pt total count)
  ;; Kolon semasinda uretilen INSERT/TEXT/LWPOLYLINE nesnesinin satir Y'si.
  (setq ed (if (and ent (entget ent)) (entget ent) nil)
        total 0.0
        count 0)
  (foreach item ed
    (if (and (= (car item) 10)
             (setq pt (cdr item))
             (listp pt)
             (numberp (cadr pt)))
      (setq total (+ total (cadr pt))
            count (1+ count))))
  (if (> count 0) (/ total count) nil)
)

(defun degk--gf-row-entities
  (entities loopRecords floorSpacing / rec y minY maxY pad ent entY out)
  ;; Tum GF loop satirlarini ve ayni satirlardaki block/yazilari al; komsu
  ;; katlara tasma olmamasi icin yarim kat araligindan kucuk pay kullan.
  (foreach rec loopRecords
    (setq y (degk--loop-record-mouth-y rec))
    (if (numberp y)
      (progn
        (if (or (null minY) (< y minY)) (setq minY y))
        (if (or (null maxY) (> y maxY)) (setq maxY y)))))
  (setq pad
    (if (and (numberp floorSpacing) (> floorSpacing 1e-9))
      (* 0.45 floorSpacing)
      (* 350.0 (DEG:PLAN-UNIT-SCALE))))
  (if (and minY maxY)
    (foreach ent entities
      (setq entY (degk--entity-reference-y ent))
      (if (and (numberp entY)
               (>= entY (- minY pad))
               (<= entY (+ maxY pad))
               (not (member ent out)))
        (setq out (cons ent out)))))
  (reverse out)
)

(defun degk--move-entities-y (entities dy / ent ed layer obj res moved ok)
  (if (and entities (numberp dy) (> (abs dy) 1e-9))
    (progn
      (setq ok T)
      (foreach ent entities
        (if ok
          (progn
            (setq ed (if (and ent (entget ent)) (entget ent) nil)
                  layer (if ed (cdr (assoc 8 ed)) nil))
            (if layer (degk--ensure-layer-editable layer))
            (setq obj
              (if ed
                (vl-catch-all-apply 'vlax-ename->vla-object (list ent))
                nil))
            (if (or (null obj) (vl-catch-all-error-p obj))
              (setq ok nil)
              (progn
                (degk--make-object-and-atts-editable obj)
                (setq res
                  (vl-catch-all-apply
                    'vla-Move
                    (list obj
                          (vlax-3d-point '(0.0 0.0 0.0))
                          (vlax-3d-point (list 0.0 dy 0.0)))))
                (if (vl-catch-all-error-p res)
                  (setq ok nil)
                  (setq moved (cons obj moved))))))))
      (if ok
        T
        (progn
          (foreach obj moved
            (vl-catch-all-apply
              'vla-Move
              (list obj
                    (vlax-3d-point '(0.0 0.0 0.0))
                    (vlax-3d-point (list 0.0 (- dy) 0.0)))))
          nil)))
    nil)
)

(defun degk--shift-point-list-y (pts dy / pt out)
  (foreach pt pts
    (setq out
      (cons
        (if (and (listp pt) (numberp (cadr pt)))
          (list (car pt) (+ (cadr pt) dy)
                (if (and (caddr pt) (numberp (caddr pt))) (caddr pt) 0.0))
          pt)
        out)))
  (reverse out)
)

(defun degk--shift-loop-records-y-data (records dy / rec out)
  (foreach rec records
    (setq out
      (cons
        (list
          (nth 0 rec)
          (degk--shift-point-list-y (nth 1 rec) dy)
          (nth 2 rec)
          (nth 3 rec)
          (nth 4 rec)
          (if (listp (nth 5 rec))
            (degk--shift-point-list-y (nth 5 rec) dy)
            (nth 5 rec))
          (nth 6 rec))
        out)))
  (reverse out)
)

(defun degk--align-gf-combined-to-panel
  (panelObj records limits risers entities floorSpacing excluded
   / panelEnt bb rec raw lowY firstRaw y targetY dy moveEntities ent)
  ;; Dikte ilk loopun ust yatay rayi YAP +2000 mm'de olmalidir.
  ;; Tum GF satirlari ve GF kombinesi ayni delta ile tasinir.
  (setq panelEnt (vlax-vla-object->ename panelObj)
        bb (degk--column-frame-block-visible-bbox panelEnt))
  (if (null bb) (setq bb (degk--ent-bbox panelObj)))
  (foreach rec records
    (setq raw (nth 5 rec)
          y (degk--loop-record-mouth-y rec))
    (if (and raw (numberp y) (or (null lowY) (< y lowY)))
      (setq lowY y firstRaw raw)))
  (if (and bb firstRaw)
    (progn
      (setq targetY (+ (cadr (cadr bb)) (* 200.0 (DEG:PLAN-UNIT-SCALE)))
            dy (- targetY (max (cadr (car firstRaw)) (cadr (last firstRaw)))))
      (if (> (abs dy) 1e-9)
        (progn
          (setq moveEntities (degk--gf-row-entities entities records floorSpacing))
          (foreach ent excluded (setq moveEntities (vl-remove ent moveEntities)))
          (foreach ent (append (mapcar 'car records) risers)
            (if (and ent (entget ent) (not (member ent moveEntities)))
              (setq moveEntities (cons ent moveEntities))))
          (if (degk--move-entities-y moveEntities dy)
            (setq records (degk--shift-loop-records-y-data records dy)
                  limits (degk--shift-point-list-y limits dy)))))))
  (list records limits)
)

(defun degk--align-gf-loops-to-panel
  (panelObj loopRecords entities floorSpacing
   / panelEnt bb panelTopY dy moveEntities)
  ;; YAP sabit kalir. Tum GF satirlari ayni miktarda yukari tasinir;
  ;; loop, block ve yazilarin mevcut satir araliklari korunur.
  (if (and panelObj (= (type panelObj) 'VLA-OBJECT) loopRecords)
    (progn
      (setq panelEnt
        (vl-catch-all-apply 'vlax-vla-object->ename (list panelObj)))
      (if (vl-catch-all-error-p panelEnt) (setq panelEnt nil))
      (setq bb
        (if panelEnt
          (degk--column-frame-block-visible-bbox panelEnt)
          nil))
      (if (null bb) (setq bb (degk--ent-bbox panelObj)))
      (setq panelTopY (if bb (cadr (cadr bb)) nil)
            dy
              (if (numberp panelTopY)
                (degk--room-first-loop-shift-y panelTopY loopRecords)
                nil))
      (if (and (numberp dy) (> dy 1e-9))
        (progn
          (setq moveEntities
            (degk--gf-row-entities entities loopRecords floorSpacing))
          (if (degk--move-entities-y moveEntities dy)
            (degk--shift-loop-records-y-data loopRecords dy)
            loopRecords))
        loopRecords))
    loopRecords)
)

(defun degk--stage-square-direct-loop-record
  (rec radius
   / oldEnt rawPts layer color direction squareData newPts newBulges
     beforeEnt makeRes newEnt)
  ;; Multiline olmayan planda eski loopu silmeden filletsiz bir kopya hazirla.
  ;; Tum YAP baglantilari basarili olursa cagiran eski entity'yi siler.
  (setq oldEnt (if (listp rec) (car rec) nil)
        rawPts (if (listp rec) (nth 5 rec) nil)
        layer (if (listp rec) (nth 3 rec) nil)
        color (if (listp rec) (nth 4 rec) nil)
        direction
          (if (and (listp rec) (numberp (nth 6 rec)))
            (nth 6 rec)
            -1.0)
        squareData
          (if rawPts
            (degk--loop-left-square-data rawPts radius direction)
            nil))
  (if (and oldEnt (entget oldEnt) squareData)
    (progn
      (setq newPts (car squareData)
            newBulges (cadr squareData)
            beforeEnt (entlast)
            makeRes
              (degk--entmake-lwpoly-bulges
                newPts newBulges layer color)
            newEnt (entlast))
      (if (and makeRes newEnt (not (eq beforeEnt newEnt)))
        (list
          (list newEnt newPts newBulges layer color rawPts direction)
          oldEnt)
        nil))
    nil)
)

(defun degk--loop-record-top-y (rec / pt topY)
  (foreach pt (if (listp rec) (cadr rec) nil)
    (if (and (listp pt) (numberp (cadr pt))
             (or (null topY) (> (cadr pt) topY)))
      (setq topY (cadr pt))))
  topY
)

(defun degk--direct-route-add-point (pts pt / lastPt)
  (setq lastPt (if pts (last pts) nil))
  (if (and lastPt (degk--pt-eq? lastPt pt 1e-6))
    pts
    (append pts (list pt)))
)

(defun degk--direct-loop-turn-ys
  (firstY lastY previousTopY gap / topTurnY firstTurnY lastTurnY)
  ;; Iki yatay baglanti arasi bir ofsettir. Alt baglanti da altindaki
  ;; loopun ustunden bir ofset yukarida kalir.
  (if (and (numberp firstY) (numberp lastY)
           (numberp previousTopY) (numberp gap) (> gap 1e-9))
    (progn
      (setq topTurnY (+ previousTopY (* 2.0 gap)))
      (if (>= firstY lastY)
        (setq firstTurnY topTurnY
              lastTurnY (- topTurnY gap))
        (setq firstTurnY (- topTurnY gap)
              lastTurnY topTurnY))
      ;; Donus seviyesini mevcut loop agzinin otesine tasima.
      (list (min firstTurnY firstY)
            (min lastTurnY lastY)))
    nil)
)

(defun degk--direct-loop-route-points
  (panelX panelTopY mouthPt turnY / mouthX mouthY z bendY pts)
  ;; YAP'tan loop agzina yalniz dik/yatay parcalarla gider. turnY verilirse
  ;; ust loop once altindaki loopun ustune iner, sonra sola doner.
  (if (and (numberp panelX) (numberp panelTopY)
           (listp mouthPt)
           (numberp (car mouthPt)) (numberp (cadr mouthPt)))
    (progn
      (setq mouthX (car mouthPt)
            mouthY (cadr mouthPt)
            z (if (and (caddr mouthPt) (numberp (caddr mouthPt)))
                (caddr mouthPt)
                0.0)
            bendY
              (if (and (numberp turnY)
                       (>= turnY (- (min panelTopY mouthY) 1e-6))
                       (<= turnY (+ (max panelTopY mouthY) 1e-6)))
                turnY
                (/ (+ panelTopY mouthY) 2.0))
            pts nil)
      (setq pts
        (degk--direct-route-add-point
          pts (list panelX panelTopY z)))
      (setq pts
        (degk--direct-route-add-point
          pts (list panelX bendY z)))
      (setq pts
        (degk--direct-route-add-point
          pts (list mouthX bendY z)))
      (setq pts
        (degk--direct-route-add-point pts mouthPt))
      pts)
    nil)
)

(defun degk--draw-room-panel-direct-loops
  (panelObj loopRecords
   / panelBBoxP panelEnt bb mn mx centerX topY z gap pairPitch records count index
     rec ent pts firstPt lastPt currentCenter targetCenter delta layer color
     panelFirstX panelLastX firstX firstY lastX lastY previousTopY currentTopY
     turnYs firstTurnY lastTurnY firstRoute secondRoute
     stage stagedRecords stagedOldEnts stagedNewEnts beforeEnt firstRes firstEnt
     secondRes secondEnt made ok)
  ;; Kombine multiline yoksa her GF loopunun iki agzini diger looplardan
  ;; bagimsiz olarak YAP'in ust kenarina kadar kendi layer/rengiyle uzat.
  ;; Loop agizlari filletsizdir. Ust looplar once alt loopun ustune iner,
  ;; sonra sola donup YAP'taki kendilerine ait iki noktaya baglanir.
  (setq panelBBoxP
    (and (listp panelObj)
         (eq (car panelObj) 'BOUNDS)
         (listp (cadr panelObj))
         (= (length (cadr panelObj)) 2)))
  (if (and panelObj
           (or (= (type panelObj) 'VLA-OBJECT) panelBBoxP)
           (listp loopRecords))
    (progn
      (if panelBBoxP
        (setq bb (cadr panelObj))
        (progn
          (setq panelEnt
            (vl-catch-all-apply 'vlax-vla-object->ename (list panelObj)))
          (if (vl-catch-all-error-p panelEnt) (setq panelEnt nil))
          (setq bb
            (if panelEnt
              (degk--column-frame-block-visible-bbox panelEnt)
              nil))
          (if (null bb) (setq bb (degk--ent-bbox panelObj)))))
      (foreach rec loopRecords
        (setq ent (if (listp rec) (car rec) nil)
              pts (if (listp rec) (cadr rec) nil))
        (if (and ent (entget ent)
                 (listp pts) (>= (length pts) 2)
                 (= (type (nth 3 rec)) 'STR)
                 (/= (nth 3 rec) ""))
          (setq records (cons rec records))))
      (setq records
        (vl-sort records
          (function
            (lambda (a b)
              (< (degk--loop-record-mouth-y a)
                 (degk--loop-record-mouth-y b))))))
      (if (and bb records)
        (progn
          (setq mn (car bb)
                mx (cadr bb)
                centerX (/ (+ (car mn) (car mx)) 2.0)
                topY (cadr mx)
                z (if (and (caddr mx) (numberp (caddr mx)))
                    (caddr mx)
                    0.0)
                gap (abs (DEG:CFG-DK-NUM-OR 'DK_UNDER_X2 10.0)))
          (if (<= gap 1e-9)
            (setq gap (* 10.0 (DEG:PLAN-UNIT-SCALE))))
          (if (<= gap 1e-9) (setq gap 1.0))
          ;; Ciftin kendi genisligi bir ofset; komsu ciftle boslugu da bir ofset.
          (setq pairPitch (* 2.0 gap)
                count (length records)
                index 0
                made nil
                stagedRecords nil
                stagedOldEnts nil
                stagedNewEnts nil
                ok T)
          ;; Filletli looplari once gecici filletsiz entity'ler olarak kur.
          ;; Eski entity'ler ancak butun YAP baglantilari tamamlaninca silinir.
          (foreach rec records
            (if ok
              (progn
                (setq stage
                  (degk--stage-square-direct-loop-record rec gap))
                (if stage
                  (progn
                    (setq stagedRecords
                            (cons (car stage) stagedRecords)
                          stagedOldEnts
                            (cons (cadr stage) stagedOldEnts)
                          stagedNewEnts
                            (cons (car (car stage)) stagedNewEnts)))
                  (setq ok nil)))))
          (if ok
            (setq records (reverse stagedRecords)))
          (foreach rec records
            (if ok
              (progn
                (setq ent (car rec)
                      pts (cadr rec)
                      firstPt (car pts)
                      lastPt (last pts)
                      layer (nth 3 rec)
                      color (nth 4 rec)
                      currentCenter (/ (+ (car firstPt) (car lastPt)) 2.0)
                      targetCenter
                        ;; Alt loop sagda, ust looplar sirayla solda kalir;
                        ;; YAP cikislarinda yatay kollar dik kollari kesmez.
                        (+ centerX
                           (* (- (/ (- count 1) 2.0)
                                 (* 1.0 index))
                              pairPitch))
                      panelFirstX
                        (+ targetCenter (- (car firstPt) currentCenter))
                      panelLastX
                        (+ targetCenter (- (car lastPt) currentCenter))
                      ;; En alttaki loop YAP ustune kadar stretch edilir.
                      ;; Ust looplar yerinde kalir ve kare guzergahla sola gelir.
                      delta
                        (if (= index 0)
                          (- targetCenter currentCenter)
                          0.0))
                (if (or (<= (abs delta) 1e-9)
                        (degk--shift-lwpoly-x ent delta 'MOUTHS))
                  (progn
                    (setq firstX (+ (car firstPt) delta)
                          firstY (cadr firstPt)
                          lastX (+ (car lastPt) delta)
                          lastY (cadr lastPt)
                          ;; Ilk ciftin yatay rayini esas al; loop govdesindeki
                          ;; cihaz cikintilari baglanti seviyesini yukseltemez.
                          currentTopY
                            (max (cadr (car (nth 5 rec)))
                                 (cadr (last (nth 5 rec))))
                          turnYs
                            (if (and (> index 0) (numberp previousTopY))
                              (degk--direct-loop-turn-ys
                                firstY lastY previousTopY gap)
                              nil)
                          firstTurnY
                            (if turnYs
                              (car turnYs)
                              nil)
                          lastTurnY
                            (if turnYs
                              (cadr turnYs)
                              nil)
                          firstRoute
                            (degk--direct-loop-route-points
                              panelFirstX topY
                              (list firstX firstY z)
                              firstTurnY)
                          secondRoute
                            (degk--direct-loop-route-points
                              panelLastX topY
                              (list lastX lastY z)
                              lastTurnY))
                    (degk--ensure-layer-editable layer)
                    (setq beforeEnt (entlast)
                          firstRes
                            (degk--entmake-lwpoly
                              firstRoute
                              layer color)
                          firstEnt (entlast))
                    (if (and firstRes firstEnt
                             (not (eq beforeEnt firstEnt)))
                      (setq made (cons firstEnt made))
                      (setq ok nil))
                    (if ok
                      (progn
                        (setq beforeEnt (entlast)
                              secondRes
                                (degk--entmake-lwpoly
                                  secondRoute
                                  layer color)
                              secondEnt (entlast))
                        (if (and secondRes secondEnt
                                 (not (eq beforeEnt secondEnt)))
                          (setq made (cons secondEnt made))
                          (setq ok nil)))))
                  (setq ok nil))
                (if (numberp currentTopY)
                  (setq previousTopY
                    (if turnYs
                      (max (car turnYs) (cadr turnYs))
                      currentTopY)))
                (setq index (1+ index)))))
          (if ok
            (progn
              (degk--delete-entity-list stagedOldEnts)
              T)
            (progn
              (degk--delete-entity-list made)
              (degk--delete-entity-list stagedNewEnts)
              nil)))
        nil))
    nil)
)

(defun degk--panel-run-rail-contact (target railY runs / run ed item pt best score bestScore)
  ;; Yatay rayla ayni seviyedeki gercek polyline teget noktasini bul.
  ;; Dikey kolonun X'i, filletin alt seviyesinde temas noktasi degildir.
  (foreach run runs
    (if (equal (car run) (car target) 1e-6)
      (foreach item (entget (cadr run))
        (if (and (= (car item) 10)
                 (setq pt (cdr item))
                 (equal (cadr pt) railY 1e-6))
          (progn
            (setq score (abs (- (car pt) (car target))))
            (if (or (null bestScore) (< score bestScore))
              (setq best pt bestScore score)))))))
  best)

(defun degk--straighten-first-gf-loop
  (records limits runs / rec firstRec y minY raw pts firstTarget lastTarget
   newPts rev before result newEnt)
  ;; Ilk loopun govdesini koru; donusleri kaldirip yatay raylari
  ;; mevcut eslesmelerindeki panel hatlarinin gercek tegetlerinde bitir.
  (foreach rec records
    (setq y (degk--loop-record-mouth-y rec))
    (if (and (numberp y) (or (null minY) (< y minY)))
      (setq minY y firstRec rec)))
  (if (and firstRec (entget (car firstRec))
           (setq raw (nth 5 firstRec))
           (>= (length raw) 4) limits)
    (progn
      (setq pts (cadr firstRec)
            firstTarget (degk--nearest-point-by-x (car pts) limits)
            lastTarget (degk--nearest-point-by-x (last pts) limits))
      (if runs
        (setq firstTarget
                (degk--panel-run-rail-contact firstTarget (cadr (car raw)) runs)
              lastTarget
                (degk--panel-run-rail-contact lastTarget (cadr (last raw)) runs)))
      (if (and firstTarget lastTarget)
        (progn
          (setq newPts
            (cons (cons (car firstTarget) (cdr (car raw))) (cdr raw))
                rev (reverse newPts)
                newPts
            (reverse
              (cons (cons (car lastTarget) (cdr (car rev))) (cdr rev)))
                before (entlast)
                result (degk--entmake-lwpoly
                         newPts (nth 3 firstRec) (nth 4 firstRec))
                newEnt (entlast))
          (if (and result newEnt (not (eq before newEnt)))
            (progn (entdel (car firstRec)) T)
            nil))))
    nil))

(defun degk--extend-second-gf-loop (records targets risers radius
  / rec upperRec y upperY pts raw firstTarget lastTarget before result newEnt
    body newPts bulges i n x1 x2 y1 y2 z1 z2)
  ;; Ust koseler kare; alt koseler panel hattina yatay teget filletlidir.
  (foreach rec records
    (setq y (degk--loop-record-mouth-y rec))
    (if (and (numberp y) (or (null upperY) (> y upperY)))
      (setq upperY y upperRec rec)))
  (if (and (= (length records) 2) upperRec (entget (car upperRec))
           (setq raw (nth 5 upperRec)) (>= (length raw) 4))
    (progn
      (setq pts (cadr upperRec)
            firstTarget (degk--nearest-point-by-x (car pts) targets)
            lastTarget (degk--nearest-point-by-x (last pts) targets))
      (if (and firstTarget lastTarget
               (> (- (cadr (car raw)) (cadr firstTarget)) radius)
               (> (- (cadr (last raw)) (cadr lastTarget)) radius))
        (progn
          (setq x1 (car firstTarget) y1 (cadr firstTarget)
                x2 (car lastTarget) y2 (cadr lastTarget)
                z1 (if (caddr firstTarget) (caddr firstTarget) 0.0)
                z2 (if (caddr lastTarget) (caddr lastTarget) 0.0)
                body (reverse (cdr (reverse (cdr raw))))
                newPts
                  (append
                    (list (list (- x1 radius) y1 z1)
                          (list x1 (+ y1 radius) z1)
                          (list x1 (cadr (car raw)) z1))
                    body
                    (list (list x2 (cadr (last raw)) z2)
                          (list x2 (+ y2 radius) z2)
                          (list (- x2 radius) y2 z2)))
                i 0 n (length newPts) bulges nil)
          (repeat n
            (setq bulges
              (cons (cond ((= i 0) 0.414213562373095)
                          ((= i (- n 2)) -0.414213562373095)
                          (T 0.0)) bulges)
                  i (1+ i)))
          (setq before (entlast)
                result (degk--entmake-lwpoly-bulges
                         newPts (reverse bulges) (nth 3 upperRec) (nth 4 upperRec))
                newEnt (entlast))
          (if (and result newEnt (not (eq before newEnt)))
            (progn
              (entdel (car upperRec))
              (degk--delete-entity-list risers)
              T)
            nil))))))

(defun degk--draw-room-panel-risers
(panelObj layer riserLimits loopRecords riserEntities shaftRiserEntities straightFirstP / panelEnt bb mn mx centerX topY z gap rise x1 x2 upperY lowerY haveTarget oneLoopTargetP twoLoopTargetP singleLoopStretchRes singleLoopEnt singleLoopOriginalData singleLoopShiftedP singleLoopLeftY singleLoopRightY leftBottom rightBottom leftTop rightTop leftX rightX leftMinY leftMaxY rightMinY rightMaxY riserAboveP rebuildRes firstTargetX firstTargetMinY firstTargetMaxY firstTargetJoinY secondTargetX secondTargetMinY secondTargetMaxY secondTargetJoinY shaftInfos shaftTargets shaftRequiredP shaftBranchOne shaftBranchTwo shaftBranchChanges branchChange originalRiser firstEnt secondEnt horizontalOne horizontalTwo extensionOne extensionTwo made ok)
  ;; Yangin panelinden cikan cift hatti saga dondurup GF kombine kolonuna baglar.
  (if (and panelObj (= (type panelObj) 'VLA-OBJECT)
           layer (= (type layer) 'STR) (/= layer ""))
    (progn
      (setq panelEnt
        (vl-catch-all-apply 'vlax-vla-object->ename (list panelObj)))
      (if (vl-catch-all-error-p panelEnt) (setq panelEnt nil))
      (setq bb
        (if panelEnt
          (degk--column-frame-block-visible-bbox panelEnt)
          nil))
      (if (null bb) (setq bb (degk--ent-bbox panelObj)))
      (if bb
        (progn
          (setq mn (car bb)
                mx (cadr bb)
                centerX (/ (+ (car mn) (car mx)) 2.0)
                topY (cadr mx)
                z (if (and (caddr mx) (numberp (caddr mx))) (caddr mx) 0.0)
                gap (* 10.0 (DEG:PLAN-UNIT-SCALE))
                rise (* 200.0 (DEG:PLAN-UNIT-SCALE))
                x1 (- centerX (/ gap 2.0))
                x2 (+ centerX (/ gap 2.0))
                haveTarget
                  (and (listp riserLimits)
                       (>= (length riserLimits) 4)
                       (listp (nth 0 riserLimits))
                       (listp (nth 1 riserLimits))
                       (listp (nth 2 riserLimits))
                       (listp (nth 3 riserLimits)))
                oneLoopTargetP
                  (and haveTarget
                       (listp loopRecords)
                       (= (length loopRecords) 1))
                twoLoopTargetP
                  (and haveTarget
                       (listp loopRecords)
                       (= (length loopRecords) 2))
                shaftInfos (degk--shaft-riser-infos shaftRiserEntities)
                shaftRequiredP (>= (length shaftInfos) 2)
                upperY (+ topY rise)
                ;; Saga donen cift hatta ic kol 100 mm daha kisa biter.
                lowerY (if (or haveTarget shaftRequiredP) (- upperY gap) upperY)
                shaftTargets
                  (if shaftRequiredP
                    (degk--panel-shaft-targets shaftInfos lowerY)
                    shaftInfos)
                made nil
                shaftBranchChanges nil)
          (if haveTarget
            (progn
              (setq riserAboveP
                (degk--riser-limits-above-horizontal-p
                  riserLimits upperY lowerY))
              ;; GF kombinesi yatay baglantidan asagi gidiyorsa tum looplari
              ;; yukari bakan filletlerle yeniden kur. Yeni dik cift tum agizlari
              ;; kapsar; yalniz geometrik en alt loop kare dirsek olarak kalir.
              (if (and (not riserAboveP) loopRecords)
                (progn
                  (setq rebuildRes
                    (vl-catch-all-apply
                      'degk--rebuild-gf-down-riser
                      (list layer riserLimits loopRecords riserEntities)))
                  (cond
                    ((vl-catch-all-error-p rebuildRes)
                      (princ
                        (strcat
                          "\nDK: GF-asagi fillet son islemi atlandi; panel baglantisi mevcut uclara cizilecek: "
                          (vl-catch-all-error-message rebuildRes))))
                    ((and (= (type rebuildRes) 'LIST)
                          (>= (length rebuildRes) 3))
                      (setq riserLimits (car rebuildRes)
                            loopRecords (cadr rebuildRes)
                            riserEntities (caddr rebuildRes))))))
              (setq leftBottom (nth 0 riserLimits)
                    rightBottom (nth 1 riserLimits)
                    leftTop (nth 2 riserLimits)
                    rightTop (nth 3 riserLimits)
                    leftX (car leftBottom)
                    rightX (car rightBottom)
                    leftMinY (min (cadr leftBottom) (cadr leftTop))
                    leftMaxY (max (cadr leftBottom) (cadr leftTop))
                    rightMinY (min (cadr rightBottom) (cadr rightTop))
                    rightMaxY (max (cadr rightBottom) (cadr rightTop)))
              ;; GF dik hatlari yataylarin ustundeyse onceki; altindaysa saga
              ;; donuste paralel sirayi koruyan ters X eslemesini kullan.
              (if riserAboveP
                (setq firstTargetX leftX
                      firstTargetMinY leftMinY
                      firstTargetMaxY leftMaxY
                      secondTargetX rightX
                      secondTargetMinY rightMinY
                      secondTargetMaxY rightMaxY)
                (setq firstTargetX rightX
                      firstTargetMinY rightMinY
                      firstTargetMaxY rightMaxY
                      secondTargetX leftX
                      secondTargetMinY leftMinY
                      secondTargetMaxY leftMaxY))
              (setq firstTargetJoinY
                      (degk--panel-riser-fillet-y
                        upperY firstTargetMinY firstTargetMaxY
                        riserAboveP gap)
                    secondTargetJoinY
                      (degk--panel-riser-fillet-y
                        lowerY secondTargetMinY secondTargetMaxY
                        riserAboveP gap))))
          (if (and straightFirstP twoLoopTargetP)
            (setq firstTargetJoinY upperY
                  secondTargetJoinY lowerY))
          ;; Tek GF loopunda kombine hatti loopa kadar tasima. Loopun yalniz
          ;; iki agiz/fillet bolgesini FAP merkezine stretch et ve magenta
          ;; panel hatlarini bu iki agizda dik olarak bitir.
          (if oneLoopTargetP
            (progn
              (setq singleLoopStretchRes
                (degk--stretch-single-loop-to-panel
                  loopRecords riserLimits centerX))
              (if singleLoopStretchRes
                (setq singleLoopEnt (nth 0 singleLoopStretchRes)
                      singleLoopOriginalData (nth 1 singleLoopStretchRes)
                      singleLoopShiftedP T
                      x1 (nth 3 singleLoopStretchRes)
                      x2 (nth 4 singleLoopStretchRes)
                      singleLoopLeftY (nth 5 singleLoopStretchRes)
                      singleLoopRightY (nth 6 singleLoopStretchRes))
                (setq oneLoopTargetP nil))))
          (degk--ensure-layer-editable layer)
          (setq firstEnt
              (cond
                (oneLoopTargetP
                  (degk--column-frame-polyline
                    (list (list x1 topY z)
                          (list x1 singleLoopLeftY z))
                    layer nil))
                (haveTarget
                  (degk--make-panel-filleted-run
                    x1 topY upperY
                    (if (and straightFirstP twoLoopTargetP) (- firstTargetX gap) firstTargetX)
                    firstTargetJoinY z gap layer
                    (not twoLoopTargetP)))
                (T
                  (degk--column-frame-polyline
                    (list (list x1 topY z)
                          (list x1
                                (if shaftRequiredP (- upperY gap) upperY)
                                z))
                    layer nil)))
                made (if firstEnt (cons firstEnt made) made)
                secondEnt
              (cond
                (oneLoopTargetP
                  (degk--column-frame-polyline
                    (list (list x2 topY z)
                          (list x2 singleLoopRightY z))
                    layer nil))
                (haveTarget
                  (degk--make-panel-filleted-run
                    x2 topY lowerY
                    (if (and straightFirstP twoLoopTargetP) (- secondTargetX gap) secondTargetX)
                    secondTargetJoinY z gap layer
                    (not twoLoopTargetP)))
                (T
                  (degk--column-frame-polyline
                    (list (list x2 topY z)
                          (list x2
                                (if shaftRequiredP (- lowerY gap) lowerY)
                                z))
                    layer nil)))
                made (if secondEnt (cons secondEnt made) made))
          (if haveTarget
            (progn
              ;; GF hedefli iki panel kolu tek parca baglanti olarak kuruldu.
              (setq horizontalOne firstEnt
                    horizontalTwo secondEnt
                    extensionOne T
                    extensionTwo T)))
          (if shaftRequiredP
            (progn
              (setq shaftBranchOne
                      (degk--make-panel-shaft-branch
                        x1 topY upperY (car shaftTargets) z gap layer)
                    made
                      (if shaftBranchOne
                        (append (car shaftBranchOne) made)
                        made)
                    shaftBranchChanges
                      (if shaftBranchOne
                        (cons shaftBranchOne shaftBranchChanges)
                        shaftBranchChanges)
                    shaftBranchTwo
                      (degk--make-panel-shaft-branch
                        x2 topY lowerY (cadr shaftTargets) z gap layer)
                    made
                      (if shaftBranchTwo
                        (append (car shaftBranchTwo) made)
                        made)
                    shaftBranchChanges
                      (if shaftBranchTwo
                        (cons shaftBranchTwo shaftBranchChanges)
                        shaftBranchChanges))))
          (setq ok
            (and firstEnt secondEnt
                 (or (not haveTarget)
                      (and horizontalOne horizontalTwo
                           extensionOne extensionTwo))
                 (or (not shaftRequiredP)
                     (and shaftBranchOne shaftBranchTwo))))
          (if ok
            (progn
              (if (and straightFirstP twoLoopTargetP)
                (degk--extend-second-gf-loop loopRecords
                  (list (list firstTargetX upperY z)
                        (list secondTargetX lowerY z))
                  riserEntities gap))
              (if (and straightFirstP haveTarget (not oneLoopTargetP))
                (degk--straighten-first-gf-loop loopRecords riserLimits
                  (list (list firstTargetX firstEnt)
                        (list secondTargetX secondEnt))))
              T)
            (progn
              (foreach panelEnt made
                (vl-catch-all-apply 'entdel (list panelEnt)))
              ;; Iki baglantidan biri kurulamazsa silinen asil saft dikmelerini
              ;; de geri getir; yarim bir iki-yonlu baglanti birakma.
              (foreach branchChange shaftBranchChanges
                (setq originalRiser (cadr branchChange))
                (if (and originalRiser
                         (caddr branchChange)
                         (null (entget originalRiser)))
                  (vl-catch-all-apply 'entdel (list originalRiser))))
              ;; Tek-loop stretch yapildiysa yarim kalan panel baglantisinda
              ;; loopun ilk geometrisini geri yukle.
              (if (and singleLoopShiftedP singleLoopEnt
                       singleLoopOriginalData (entget singleLoopEnt))
                (if (entmod singleLoopOriginalData)
                  (entupd singleLoopEnt)))
              nil)))
        nil))
    nil)
)

(defun degk--column-centered-text (pt txt layer height rotation / data)
  (if (and pt txt (/= txt "") (numberp height) (> height 0.0))
    (progn
      (setq data
        (list
          '(0 . "TEXT")
          '(100 . "AcDbEntity")
          (cons 8 layer)
          '(100 . "AcDbText")
          (cons 10 pt)
          (cons 40 height)
          (cons 1 txt)
          (cons 50 (if (numberp rotation) rotation 0.0))
          '(41 . 1.0)
          '(7 . "STANDARD")
          '(71 . 0)
          '(72 . 1)
          (cons 11 pt)
          '(100 . "AcDbText")
          '(73 . 2)))
      (entmakex data))
    nil)
)

(defun degk--column-room-text (pt txt layer height)
  ;; Oda basligini verilen noktanin yatay/dikey merkezine yerlestirir.
  (degk--column-centered-text pt txt layer height 0.0)
)

(defun degk--ups-panel-label-text (txt / i key result)
  (setq i 1 result "")
  (while (<= i (strlen txt))
    (setq key (strcase (substr txt i 3)))
    (cond
      ((= key "FAP") (setq result (strcat result "UPS") i (+ i 3)))
      ((= key "YAP") (setq result (strcat result "KGK") i (+ i 3)))
      (T (setq result (strcat result (substr txt i 1)) i (1+ i)))))
  result)

(defun degk--room-device-label (ent text powerP upsLayer labelLayer englishP / bb mn mx x y z center height run tx ed energyY energyText energyRun energyHeight)
  (setq bb (degk--column-frame-block-visible-bbox ent))
  (if (null bb) (setq bb (degk--ent-bbox ent)))
  (if bb
    (progn
      (setq mn (car bb) mx (cadr bb) x (car mn) y (cadr mx)
            z (if (caddr mx) (caddr mx) 0.0)
            center (/ (+ (car mn) (car mx)) 2.0)
            height (* 30.0 (DEG:PLAN-UNIT-SCALE)))
      (if (null upsLayer) (setq upsLayer "E_UPS_LINYE"))
      (if (not (tblsearch "LAYER" upsLayer))
        (entmake (list '(0 . "LAYER") '(100 . "AcDbSymbolTableRecord")
          '(100 . "AcDbLayerTableRecord") (cons 2 upsLayer) '(70 . 0) '(62 . 7) '(6 . "Continuous"))))
      (degk--ensure-layer-editable upsLayer)
      (degk--entmake-lwpoly
        (list (list center (cadr mn) z)
              (list center (- (cadr mn) (* 150.0 (DEG:PLAN-UNIT-SCALE))) z)) upsLayer 256)
      (setq energyY (- (cadr mn) (* 75.0 (DEG:PLAN-UNIT-SCALE)))
            energyHeight (* 25.0 (DEG:PLAN-UNIT-SCALE))
            energyText (if englishP "FOR ENERGY SUPPLY" "GÜÇ BESLEMESÝ")
            energyRun (max (* 200.0 (DEG:PLAN-UNIT-SCALE))
                          (* energyHeight (+ 2.0 (* 0.8 (strlen energyText))))))
      (degk--entmake-lwpoly
        (list (list center energyY z) (list (+ center energyRun) energyY z)) labelLayer 256)
      (degk--add-loop-intersection-mark
        (list center energyY z)
        (DEG:CFG-DK-NUM-OR 'DK_LOOP_MARK_LENGTH 10.0)
        labelLayer)
      (degk--column-centered-text
        (list (+ center (/ energyRun 2.0)) (+ energyY energyHeight) z)
        energyText labelLayer energyHeight 0.0)
      (setq text (if (= (type text) 'STR) text ""))
      (if powerP (setq text (degk--ups-panel-label-text text)))
      (setq run (max (* 200.0 (DEG:PLAN-UNIT-SCALE)) (* height (+ 2.0 (* 0.8 (strlen text))))))
      (degk--entmake-lwpoly (list (list x y z) (list (- x run) y z)) labelLayer 256)
      (if (/= text "")
        (progn
          (setq tx (degk--column-centered-text
            (list (- x (/ run 2.0)) (+ y height) z) text labelLayer height 0.0))
          (if tx
            (progn
              (setq ed (entget tx))
              (setq ed (vl-remove-if '(lambda (p) (member (car p) '(62 420 430))) ed))
              (setq ed (apply 'append (mapcar '(lambda (p)
                (if (= (car p) 8) (list p '(62 . 256)) (list p))) ed)))
              (entmod ed) (entupd tx))))))))

(defun degk--prepare-column-layer (layer / ent ed)
  (degk--ensure-layer-editable layer)
  (if (setq ent (tblobjname "LAYER" layer))
    (progn
      (setq ed (vl-remove-if '(lambda (p) (member (car p) '(420 430))) (entget ent)))
      (setq ed (subst '(62 . 7) (assoc 62 ed) ed))
      (setq ed (if (assoc 370 ed)
                 (subst '(370 . -3) (assoc 370 ed) ed)
                 (append ed '((370 . -3)))))
      (entmod ed)))
  layer)

(defun degk--right-floor-line (pts layer / ent ed)
  (if (not (tblsearch "LTYPE" "HIDDEN"))
    (entmake
      '((0 . "LTYPE") (100 . "AcDbSymbolTableRecord")
        (100 . "AcDbLinetypeTableRecord") (2 . "HIDDEN") (70 . 0)
        (3 . "Hidden __ __ __") (72 . 65) (73 . 2) (40 . 9.525)
        (49 . 6.35) (74 . 0) (49 . -3.175) (74 . 0))))
  (if (setq ent (degk--column-frame-polyline pts layer nil))
    (progn
      (setq ed (entget ent))
      (setq ed (vl-remove-if '(lambda (p) (member (car p) '(6 48 62 420 430))) ed))
      (setq ed (apply 'append
        (mapcar '(lambda (p)
          (if (= (car p) 8)
            (list p '(6 . "HIDDEN") '(62 . 252) (cons 48 (* 10.0 (DEG:PLAN-UNIT-SCALE))))
            (list p))) ed)))
      (entmod ed)
      (entupd ent)))
  ent)

(defun degk--floor-line-outside-shaft (xMin xMax y z layer shaftP / leftX rightX)
  (setq leftX (+ xMin (* 150.0 (DEG:PLAN-UNIT-SCALE)))
        rightX (+ xMin (* 450.0 (DEG:PLAN-UNIT-SCALE))))
  (if (and shaftP (< rightX xMax))
    (progn
      (degk--column-frame-polyline (list (list xMin y z) (list leftX y z)) layer nil)
      (degk--right-floor-line (list (list rightX y z) (list xMax y z)) layer))
    (degk--column-frame-polyline (list (list xMin y z) (list xMax y z)) layer nil)))

(defun degk--panel-loop-label (panelEnt count roomHeight layer / bb mn mx x y z height label run)
  (if (and panelEnt (numberp count) (> count 0))
    (progn
      (setq bb (degk--column-frame-block-visible-bbox panelEnt))
      (if (null bb) (setq bb (degk--ent-bbox panelEnt)))
      (if bb
        (progn
          (setq mn (car bb) mx (cadr bb)
                x (car mx) y (/ (+ (cadr mn) (cadr mx)) 2.0)
                z (if (caddr mx) (caddr mx) 0.0)
                height (/ roomHeight 2.0) label (strcat (itoa count) " LOOP")
                run (max (* 200.0 (DEG:PLAN-UNIT-SCALE)) (* height (+ 2.0 (* 0.8 (strlen label))))))
          (degk--entmake-lwpoly (list (list x y z) (list (+ x run) y z)) layer 256)
          (degk--column-centered-text
            (list (+ x (/ run 2.0)) (+ y height) z) label layer height 0.0))))))

(defun degk--column-floor-label-groups (anchors / groups rec key label y current)
  ;; Ayni kata ait birden fazla loop satirini tek kat etiketi ve ortalama
  ;; yerlesim Y degeri altinda birlestir.
  (foreach rec anchors
    (if (and (listp rec)
             (>= (length rec) 3)
             (numberp (car rec))
             (numberp (nth 2 rec)))
      (progn
        (setq key     (car rec)
              label   (degk--clean-text (if (cadr rec) (cadr rec) ""))
              y       (nth 2 rec)
              current (assoc key groups))
        (if current
          (setq groups
            (subst
              (list key
                    (if (/= (cadr current) "") (cadr current) label)
                    (+ (nth 2 current) y)
                    (1+ (nth 3 current)))
              current
              groups))
          (setq groups (cons (list key label y 1) groups))))))
  (mapcar
    (function
      (lambda (group)
        (list
          (car group)
          (degk--expanded-floor-label
            (if (/= (cadr group) "")
              (cadr group)
              (degk--default-floor-label (car group)))
            (car group))
          (/ (nth 2 group) (nth 3 group)))))
    groups)
)

(defun degk--column-grid-y-values (values / sorted out value)
  (setq sorted
    (vl-sort (vl-remove-if-not 'numberp values)
      (function (lambda (a b) (< a b)))))
  (foreach value sorted
    (if (or (null out)
            (> (abs (- value (last out))) 1e-6))
      (setq out (append out (list value)))))
  out
)

(defun degk--column-grid-cell-at-y (gridYs anchorY / ys lower upper bounds)
  (setq ys (degk--column-grid-y-values gridYs))
  (while (and (cdr ys) (null bounds))
    (setq lower (car ys)
          upper (cadr ys))
    (if (and (>= anchorY (- lower 1e-6))
             (<= anchorY (+ upper 1e-6)))
      (setq bounds (list lower upper)))
    (setq ys (cdr ys)))
  bounds
)

(defun degk--column-floor-groups-english-p (groups / group txt haveLabel turkishP)
  ;; Genisletilmis kat adlarinda Turkce bir kat ifadesi yoksa saft basligini
  ;; kolon semasinin Ingilizce diliyle eslestir.
  (foreach group groups
    (setq txt (strcase (degk--clean-text (if (cadr group) (cadr group) ""))))
    (if (/= txt "") (setq haveLabel T))
    (if (or (wcmatch txt "*ZEMÝN*,*ZEMIN*,*BODRUM*,*ÇATI*,*CATI*")
            (wcmatch txt "* KAT,*KAT"))
      (setq turkishP T)))
  (and haveLabel (not turkishP))
)

(defun degk--draw-column-floor-index
  (xMin xMax yMin yMax gridYs floorAnchors layer z textHeight
   / inset dividerX textX groups group bounds cellKey usedCells ent made
     shaftInset shaftX shaftHeaderDepth shaftHeaderY shaftText)
  ;; Sol cerceve kenarindan 1500 mm iceri kat isimligini, 4500 mm iceri de
  ;; saft kolonunu ciz.
  (setq inset    (* 150.0 (DEG:PLAN-UNIT-SCALE))
        dividerX (+ xMin inset)
        shaftInset (* 450.0 (DEG:PLAN-UNIT-SCALE))
        shaftX (+ xMin shaftInset)
        shaftHeaderDepth (* 100.0 (DEG:PLAN-UNIT-SCALE))
        shaftHeaderY (- yMax shaftHeaderDepth))
  (if (and (> inset 1e-9) (< dividerX xMax))
    (progn
      (setq ent
        (degk--column-frame-polyline
          (list (list dividerX yMin z) (list dividerX yMax z))
          layer nil))
      (if ent (setq made (cons ent made)))
      (setq textX (/ (+ xMin dividerX) 2.0)
            groups (degk--column-floor-label-groups floorAnchors))
      (if (and (> (length groups) 1)
               (> shaftInset inset)
               (< shaftX xMax))
        (progn
          (setq ent
            (degk--column-frame-polyline
              (list (list shaftX yMin z) (list shaftX yMax z))
              layer nil))
          (if ent (setq made (cons ent made)))
          ;; Ust kenardan 1000 mm asagida ayri bir saft baslik bolmesi olustur.
          (if (> shaftHeaderY yMin)
            (progn
              (setq ent
                (degk--column-frame-polyline
                  (list (list dividerX shaftHeaderY z)
                        (list shaftX shaftHeaderY z))
                  layer nil))
              (if ent (setq made (cons ent made)))
              (setq shaftText
                      (if (degk--column-floor-groups-english-p groups)
                        "SHAFT"
                        "ÞAFT")
                    ent
                      (degk--column-centered-text
                        (list (/ (+ dividerX shaftX) 2.0)
                              (/ (+ shaftHeaderY yMax) 2.0)
                              z)
                        shaftText layer textHeight 0.0))
              (if ent (setq made (cons ent made)))))))
      (foreach group groups
        (setq bounds
          (degk--column-grid-cell-at-y gridYs (nth 2 group)))
        (if bounds
          (progn
            (setq cellKey
              (strcat (rtos (car bounds) 2 6) "|" (rtos (cadr bounds) 2 6)))
            (if (not (member cellKey usedCells))
              (progn
                (setq ent
                  (degk--column-centered-text
                    (list textX (/ (+ (car bounds) (cadr bounds)) 2.0) z)
                    (cadr group)
                    layer
                    textHeight
                    (/ pi 2.0)))
                (if ent (setq made (cons ent made)))
                (setq usedCells (cons cellKey usedCells))))))))
  )
  (reverse made)
)

(defun degk--vertical-floor-boundary-steps
  (rowFloors / sorted rec currentFloor previousFloor havePrevious step boundaries)
  ;; Dik moddaki her benzersiz loop satirini gercek katiyla siralar. Yalniz kat
  ;; degisiminden once tamamlanan satir sayilarini cerceve siniri olarak dondurur.
  (setq sorted
    (vl-sort rowFloors
      (function (lambda (a b) (< (car a) (car b)))))
        step 0
        boundaries nil)
  (foreach rec sorted
    (setq currentFloor (cdr rec))
    (if (and havePrevious (not (equal currentFloor previousFloor)))
      (setq boundaries (cons step boundaries)))
    (setq previousFloor currentFloor
          havePrevious T
          step (1+ step)))
  (reverse boundaries)
)

(defun degk--gf-loop-count (records / rec floorNo count haveGf)
  (setq count 0
        haveGf nil)
  (foreach rec records
    (setq floorNo (nth 1 rec))
    (if (and (numberp floorNo) (= floorNo 0))
      (progn
        (setq haveGf T)
        ;; Flasor/ozel looplar dik yerlesimde baglandiklari normal loop
        ;; satirini kullanir; GF yuksekliginde ikinci kez sayilmazlar.
        (if (not (degk--layout-record-flasher-p rec))
          (setq count (1+ count))))))
  (if (and haveGf (= count 0)) 1 count)
)

(defun degk--column-source-inserts (/ ss i ent obj layer out)
  ;; DK:BASE ile ayni kaynak INSERT filtresini olcum oncesinde uygula.
  (setq ss (ssget "_X" '((0 . "INSERT")))
        i 0
        out nil)
  (if ss
    (while (< i (sslength ss))
      (setq ent (ssname ss i)
            obj (if ent
                  (vl-catch-all-apply 'vlax-ename->vla-object (list ent))
                  nil)
            layer
              (if (and obj (not (vl-catch-all-error-p obj)))
                (vl-catch-all-apply 'vla-get-Layer (list obj))
                nil))
      (if (and obj
               (not (vl-catch-all-error-p obj))
               layer
               (not (vl-catch-all-error-p layer))
               (/= (strcase layer) "0")
               (not (DEG:IGNORE-BLOCK-OBJ? obj)))
        (setq out (cons obj out)))
      (setq i (1+ i))))
  out
)

(defun degk--layout-record-ordered-blocks
  (rec blockObjs tol / loopEnts plEnt touched blkObj totalLen useFromStart ordered ins dist key)
  ;; Cizim yapmadan once DK:BASE'in temas ve cihaz siralamasini aynen kur.
  (setq loopEnts (degk--layout-record-members rec)
        plEnt    (nth 4 rec)
        touched nil
        ordered nil)
  (foreach blkObj blockObjs
    (if (degk--block-touches-loop-p loopEnts blkObj tol)
      (setq touched (cons blkObj touched))))
  (if (and touched plEnt (degk--curve-ok? plEnt))
    (progn
      (setq totalLen
              (vlax-curve-getDistAtParam
                plEnt (vlax-curve-getEndParam plEnt))
            useFromStart
              (degk--use-from-lower-sira-side plEnt touched totalLen))
      (foreach blkObj touched
        (setq ins  (deg-get-inspt blkObj)
              dist (degk--dist-along plEnt ins)
              key
                (if (> (length loopEnts) 1)
                  (degk--block-loop-order-key blkObj loopEnts)
                  (if useFromStart dist (- totalLen dist)))
              ordered (cons (cons key blkObj) ordered)))
      (setq ordered
        (vl-sort ordered (function (lambda (a b) (< (car a) (car b))))))))
  ordered
)

(defun degk--layout-record-planned-width
  (rec blockObjs monitorHandles / ordered pair blkObj siraList siraOne dkkP seenTokens seenGroups token groupKey copyP idx positions pos lastPos spacing dx fixedLen maxOffset leftExt handle)
  ;; Loop polyline'inin DK:BASE sonunda olusacak gercek yatay genisligini,
  ;; cihaz kopya yuvalarindan cizim yapmadan hesapla.
  (setq ordered
          (degk--layout-record-ordered-blocks
            rec blockObjs (DEG:CFG-TOL-NUM-OR 'DN_BLOCK_TOL 1.0))
        dkkP (degkk--active-p)
        seenTokens nil
        seenGroups nil
        idx 0
        positions nil)
  (foreach pair ordered
    (setq blkObj   (cdr pair)
          siraList (degk--expand-sira-no (degk--get-att blkObj "SIRA_NO")))
    (if (or (null siraList) (= (length siraList) 0))
      (setq siraList (list (degk--get-att blkObj "SIRA_NO"))))
    (setq siraList (degk--limit-sira-list siraList))
    (foreach siraOne siraList
      (setq siraOne (degk--clean-text siraOne)
            copyP T)
      (if dkkP
        (progn
          (setq token (degkk--normal-token blkObj siraOne)
                groupKey (degkk--normal-group-key blkObj))
          (cond
            ((member token seenTokens)
              (setq copyP nil))
            ((member groupKey seenGroups)
              (setq seenTokens (cons token seenTokens)
                    copyP nil))
            (T
              (setq seenTokens (cons token seenTokens)
                    seenGroups (cons groupKey seenGroups))))))
      (if copyP
        (progn
          (setq positions (append positions (list idx))
                idx (1+ idx)
                handle (strcase (degkk--object-handle blkObj)))
          (if (and (/= handle "") (member handle monitorHandles))
            (setq idx (1+ idx)))))))
  (if positions
    (progn
      (setq spacing  (DEG:CFG-DK-NUM-OR 'DK_COPY_SPACING 100.0)
            dx       (DEG:CFG-DK-NUM-OR 'DK_UNDER_X1 10.0)
            fixedLen (* 90.0 (DEG:PLAN-UNIT-SCALE))
            leftExt  (degk--normal-group-left-extension)
            lastPos  (last positions)
            maxOffset (+ (* lastPos spacing) dx))
      ;; Son blockun sag cikintisi cizilmez; onceki blocklarin p4 noktasi kalir.
      (foreach pos positions
        (if (/= pos lastPos)
          (setq maxOffset
            (max maxOffset (+ (* pos spacing) dx fixedLen)))))
      (+ leftExt maxOffset))
    nil)
)

(defun degk--layout-floor-number (floorNo roofFloor /)
  (if (and roofFloor (degk--roof-floor-p floorNo)) roofFloor floorNo)
)

(defun degk--vertical-pack-floors
  (records blockObjs monitorHandles groupGap roofFloor / rec floorNo width item grouped floorRec widths measurement measurements combined longestOther other eps result)
  ;; Bir katin looplari yan yana geldiginde, baska bir kattaki en uzun tek
  ;; loopu asmiyorsa o kati tek dik-kolon satirinda paketle.
  (setq grouped nil
        measurements nil
        eps 1e-6)
  (foreach rec records
    (if (and (car rec) (not (degk--layout-record-flasher-p rec)))
      (progn
        (setq floorNo
                (degk--layout-floor-number (nth 1 rec) roofFloor)
              width
                (degk--layout-record-planned-width
                  rec blockObjs monitorHandles))
        (if (and (numberp floorNo) (numberp width) (> width eps))
          (progn
            (setq measurements (cons (cons floorNo width) measurements))
            (if (setq floorRec (assoc floorNo grouped))
              (setq grouped
                (subst
                  (cons floorNo (append (cdr floorRec) (list width)))
                  floorRec grouped))
              (setq grouped (cons (list floorNo width) grouped))))))))
  (foreach item grouped
    (setq floorNo (car item)
          widths  (cdr item))
    (if (> (length widths) 1)
      (progn
        (setq combined (* (max 0 (1- (length widths))) groupGap))
        (foreach width widths (setq combined (+ combined width)))
        (setq longestOther nil)
        (foreach measurement measurements
          (if (/= (car measurement) floorNo)
            (setq other (cdr measurement)
                  longestOther
                    (if longestOther (max longestOther other) other))))
        (if (and longestOther (<= combined (+ longestOther eps)))
          (setq result (cons floorNo result))))))
  result
)

(defun degk--vertical-floor-row-count (rowFloors wantedFloor / rec count)
  (setq count 0)
  (foreach rec rowFloors
    (if (equal (cdr rec) wantedFloor)
      (setq count (1+ count))))
  count
)

(defun degk--gf-floor-height-rows (verticalP gfLoopCount)
  (if (and (numberp gfLoopCount) (> gfLoopCount 0))
    (if verticalP
      (+ gfLoopCount 1.0)
      1.5)
    0.0)
)

(defun degk--gf-floor-extra-rows (verticalP gfLoopCount gfLayoutLoopCount)
  ;; Yerlesim kullanilan satirlari zaten sayar. Oda icin yalniz bir ek satir
  ;; birak; ayni satira paketlenen looplar tekrar yukseklik eklemesin.
  (if (and (numberp gfLoopCount) (> gfLoopCount 0))
    (if verticalP
      1.0
      0.5)
    0.0)
)

(defun degk--gf-layout-y
  (baseY floorRow floorNo floorSpacing gfExtraRows / y)
  (setq y (+ baseY (* floorRow floorSpacing)))
  (if (and (numberp floorNo)
           (> floorNo 0)
           (numberp gfExtraRows)
           (> gfExtraRows 1e-9))
    (+ y (* gfExtraRows floorSpacing))
    y)
)

(defun degk--column-frame-gf-grid-y
  (gridY gfAnchorY gfExtraRows floorSpacing)
  (if (and (numberp gridY)
           (numberp gfAnchorY)
           (numberp gfExtraRows)
           (> gfExtraRows 1e-9)
           (numberp floorSpacing)
           (> gridY gfAnchorY))
    (+ gridY (* gfExtraRows floorSpacing))
    gridY)
)

(defun degk--gf-room-dimensions (floorSpacing / referenceHeight)
  (setq referenceHeight (* floorSpacing 1.5))
  (list
    referenceHeight
    (/ referenceHeight 20.0)
    (* referenceHeight (/ 9.0 10.0)))
)

(defun degk--column-frame-room-x-bounds
  (xMin xMax roomAnchor roomWidth margin / roomLeft roomRight)
  (if (and (numberp xMin)
           (numberp xMax)
           (listp roomAnchor)
           (numberp (car roomAnchor))
           (numberp roomWidth)
           (numberp margin))
    (progn
      (setq roomLeft (car roomAnchor)
            roomRight (+ roomLeft roomWidth))
      (list
        (min xMin (- roomLeft margin))
        (max xMax (+ roomRight margin))
        roomLeft
        roomRight))
    (list xMin xMax nil nil))
)

(defun degk--draw-column-frame (entities basePt processResult / roomGfAligned bb mn mx margin upShift floorSpacing layer xMin xMax yMin yMax z y drawY topFloorY verticalRowFloors verticalLayoutP boundarySteps lineStep drawLineP frameGridYs floorLabelAnchors floorLabelGroups mainLoopRecords mainRiserLimits mainRiserEntities shaftCenterX gfRoomAnchorW roomSourceBlocks roomRiserLayer roomGfRiserLimits roomGfLoopRecords roomGfRiserEntities gfFloorExtraRows gfLoopCount gfFloorHeightRows gfRequiredTopY layoutRowYs highestRowY gfAnchorY gfBottomY gfRoomDimensions roomOffset roomWidth roomHeight roomHeader roomTextHeight roomBlockSpacing roomBlockDrop roomXBounds roomLeftX roomRightX roomBottomY roomTopY roomHeaderY roomTextPt roomCenterX roomCenterY powerTargetW panelTargetW powerCopy panelCopy)
  (setq bb (degk--column-frame-bbox entities))
  (if bb
    (progn
      ;; Ayar tabani cm'dir: her kenarda 500 cm = 5000 mm dis pay.
      (setq mn (car bb)
            mx (cadr bb)
            margin (* 500.0 (DEG:PLAN-UNIT-SCALE))
            ;; Cerceve ve kat ayiricilarinin tamami 3000 mm yukariya tasinir.
            upShift (* 300.0 (DEG:PLAN-UNIT-SCALE))
            floorSpacing (DEG:CFG-DK-NUM-OR 'DK_NORMAL_FLOOR_SPACING 700.0)
            verticalRowFloors
              (if (and (= (type processResult) 'LIST)
                       (> (length processResult) 3)
                       (listp (nth 3 processResult)))
                (nth 3 processResult)
                nil)
            verticalLayoutP (if verticalRowFloors T nil)
            boundarySteps
              (if verticalRowFloors
                (degk--vertical-floor-boundary-steps verticalRowFloors)
                nil)
            gfRoomAnchorW
              (if (and (= (type processResult) 'LIST)
                       (> (length processResult) 4)
                       (listp (nth 4 processResult))
                       (numberp (car (nth 4 processResult)))
                       (numberp (cadr (nth 4 processResult))))
                (nth 4 processResult)
                nil)
            roomSourceBlocks
              (if (and (= (type processResult) 'LIST)
                       (> (length processResult) 5)
                       (= (length (nth 5 processResult)) 2))
                (nth 5 processResult)
                nil)
            roomRiserLayer
              (if (and (= (type processResult) 'LIST)
                       (> (length processResult) 6)
                       (= (type (nth 6 processResult)) 'STR)
                       (/= (nth 6 processResult) ""))
                (nth 6 processResult)
                nil)
            roomGfRiserLimits
              (if (and (= (type processResult) 'LIST)
                       (> (length processResult) 7)
                       (listp (nth 7 processResult))
                       (>= (length (nth 7 processResult)) 4))
                (nth 7 processResult)
                nil)
            roomGfLoopRecords
              (if (and (= (type processResult) 'LIST)
                       (> (length processResult) 8)
                       (listp (nth 8 processResult)))
                (nth 8 processResult)
                nil)
            roomGfRiserEntities
              (if (and (= (type processResult) 'LIST)
                       (> (length processResult) 9)
                       (listp (nth 9 processResult)))
                (nth 9 processResult)
                nil)
            gfFloorExtraRows
              (if (and (= (type processResult) 'LIST)
                       (> (length processResult) 10)
                       (numberp (nth 10 processResult)))
                (nth 10 processResult)
                0.0)
            gfLoopCount
              (if (and (= (type processResult) 'LIST)
                       (> (length processResult) 11)
                       (numberp (nth 11 processResult)))
                (nth 11 processResult)
                0)
            layoutRowYs
              (if (and (= (type processResult) 'LIST)
                       (> (length processResult) 12)
                       (listp (nth 12 processResult)))
                (vl-remove-if-not 'numberp (nth 12 processResult))
                nil)
            floorLabelAnchors
              (if (and (= (type processResult) 'LIST)
                       (> (length processResult) 13)
                       (listp (nth 13 processResult)))
                (nth 13 processResult)
                nil)
            mainLoopRecords
              (if (and (= (type processResult) 'LIST)
                       (> (length processResult) 14)
                       (listp (nth 14 processResult)))
                (nth 14 processResult)
                nil)
            mainRiserLimits
              (if (and (= (type processResult) 'LIST)
                       (> (length processResult) 15)
                       (listp (nth 15 processResult))
                       (>= (length (nth 15 processResult)) 2))
                (nth 15 processResult)
                nil)
            mainRiserEntities
              (if (and (= (type processResult) 'LIST)
                       (> (length processResult) 16)
                       (listp (nth 16 processResult)))
                (nth 16 processResult)
                nil)
            highestRowY (if layoutRowYs (apply 'max layoutRowYs) nil)
            gfFloorHeightRows
              (degk--gf-floor-height-rows verticalLayoutP gfLoopCount)
            layer "e_kolon_þemasý"
            xMin (- (car mn) margin)
            xMax (+ (car mx) margin)
            yMin (+ (- (cadr mn) margin) upShift)
            yMax (+ (+ (cadr mx) margin) upShift)
            z (if (caddr mn) (caddr mn) 0.0)
            gfAnchorY (if gfRoomAnchorW (cadr gfRoomAnchorW) nil)
            gfBottomY yMin
            ;; Oda, loop adedinden bagimsiz sabit 1,5 katlik GF referansinin
            ;; eski 1/20 alt pay ve 9/10 yukseklik oranlarini korur.
            gfRoomDimensions (degk--gf-room-dimensions floorSpacing)
            roomOffset (cadr gfRoomDimensions)
            roomWidth (* 1500.0 (DEG:PLAN-UNIT-SCALE))
            roomHeight (nth 2 gfRoomDimensions)
            roomHeader (* 100.0 (DEG:PLAN-UNIT-SCALE))
            roomTextHeight (* 50.0 (DEG:PLAN-UNIT-SCALE))
            roomBlockSpacing (* 600.0 (DEG:PLAN-UNIT-SCALE))
            roomBlockDrop (* 200.0 (DEG:PLAN-UNIT-SCALE)))
      ;; Elektrik odasi cerceveden sonra cizilse de dis cercevenin X sinirlari
      ;; odayi her iki yandan ayni 5000 mm payla kapsar. Bu, secimde kombine
      ;; multiline bulunmadiginda da oda ile kolon semasini tek cercevede tutar.
      (setq roomXBounds
              (degk--column-frame-room-x-bounds
                xMin xMax gfRoomAnchorW roomWidth margin)
            xMin (car roomXBounds)
            xMax (cadr roomXBounds)
            roomLeftX (nth 2 roomXBounds)
            roomRightX (nth 3 roomXBounds))
      ;; 1500-4500 mm arasindaki saft kolonunun orta ekseni 3000 mm'dir.
      ;; Birden fazla katta, ana kombine dik hat ve loop agizlari bu eksene
      ;; stretch edilir; GF'nin elektrik odasina ait ozel kombinesi degismez.
      (setq floorLabelGroups
              (degk--column-floor-label-groups floorLabelAnchors)
            shaftCenterX (+ xMin (* 300.0 (DEG:PLAN-UNIT-SCALE)))
      )
      (if (and (> (length floorLabelGroups) 1)
               mainLoopRecords mainRiserLimits mainRiserEntities)
        (degk--center-main-riser-in-shaft
          mainLoopRecords mainRiserLimits mainRiserEntities shaftCenterX))
      (if (or (null roomRiserLayer)
              (/= (type roomRiserLayer) 'STR)
              (= roomRiserLayer ""))
        (setq roomRiserLayer
          (degk--first-entity-layer roomGfRiserEntities)))
      ;; Yalniz GF secilmis olsa bile sembol bbox'i cerceveyi kisaltamaz.
      ;; GF'nin alt izgara cizgisinden itibaren dikte loop adedi kadar, yatayda
      ;; ise sabit 1,5 katlik yukseklik dis cercevenin asgari ust siniridir.
      (if (and (numberp gfAnchorY)
               (> floorSpacing 1e-9)
               (> gfFloorHeightRows 1e-9))
        (progn
          (setq y (+ yMin floorSpacing))
          (while (<= y gfAnchorY)
            (setq gfBottomY y
                  y (+ y floorSpacing)))
          (setq gfRequiredTopY
            (+ gfBottomY (* gfFloorHeightRows floorSpacing)))
          (if (> gfRequiredTopY yMax)
            (setq yMax gfRequiredTopY))))
      ;; Gercek yerlesim satirlari varsa bbox'taki uzun dik baglantilar ve yazi
      ;; yukseklikleri ust cerceveyi buyutemez. En yuksek loop satirindan sonraki
      ;; ilk kat izgara cizgisi dogrudan cercevenin ust kenari olur.
      (if (> floorSpacing 1e-9)
        (if (numberp highestRowY)
          (progn
            (setq y (+ yMin floorSpacing)
                  drawY
                    (degk--column-frame-gf-grid-y
                      y gfAnchorY gfFloorExtraRows floorSpacing))
            (while (<= drawY highestRowY)
              (setq y (+ y floorSpacing)
                    drawY
                      (degk--column-frame-gf-grid-y
                        y gfAnchorY gfFloorExtraRows floorSpacing)))
            (setq yMax
              (if (and gfRequiredTopY (> gfRequiredTopY drawY))
                gfRequiredTopY
                drawY)))
          ;; Eski/eksik processResult icin bbox tabanli davranisi koru.
          (progn
            (setq y (+ yMin floorSpacing)
                  drawY
                    (degk--column-frame-gf-grid-y
                      y gfAnchorY gfFloorExtraRows floorSpacing)
                  topFloorY nil)
            (while (< drawY yMax)
              (setq topFloorY drawY
                    y (+ y floorSpacing)
                    drawY
                      (degk--column-frame-gf-grid-y
                        y gfAnchorY gfFloorExtraRows floorSpacing)))
            (if topFloorY
              (setq yMax
                (if (and gfRequiredTopY (> gfRequiredTopY topFloorY))
                  gfRequiredTopY
                  topFloorY))))))
      (degk--prepare-column-layer layer)
      (degk--column-frame-polyline
        (list
          (list xMin yMin z)
          (list xMax yMin z)
          (list xMax yMax z)
          (list xMin yMax z))
        layer T)
      ;; Alt kenardan baslayip Kat Mesafesi kadar araliklarla yukari bol.
      (setq frameGridYs (list yMin))
      (if (> floorSpacing 1e-9)
        (progn
          (setq y (+ yMin floorSpacing)
                drawY
                  (degk--column-frame-gf-grid-y
                    y gfAnchorY gfFloorExtraRows floorSpacing)
                lineStep 1)
          (while (< drawY yMax)
            ;; Yatay mod eski davranisini korur. Dik modda ayni kat icindeki
            ;; loop satirlari atlanir; yalniz kat degisim sinirlari cizilir.
            (setq drawLineP
              (or (null verticalRowFloors)
                  (member lineStep boundarySteps)))
            (if drawLineP
              (progn
                (degk--floor-line-outside-shaft
                  xMin xMax drawY z layer (> (length floorLabelGroups) 1))
                (setq frameGridYs (cons drawY frameGridYs))
                ;; GF loop satirinin altinda kalan en yakin gercek kat
                ;; ayiricisini elektrik odasi icin referans al.
                (if (and gfAnchorY
                         (<= drawY gfAnchorY)
                         (> drawY gfBottomY))
                  (setq gfBottomY drawY))))
            (setq y (+ y floorSpacing)
                  drawY
                    (degk--column-frame-gf-grid-y
                    y gfAnchorY gfFloorExtraRows floorSpacing)
                  lineStep (1+ lineStep)))))
      (setq frameGridYs (cons yMax frameGridYs))
      (degk--draw-column-floor-index
        xMin xMax yMin yMax frameGridYs floorLabelAnchors
        layer z roomTextHeight)
      (if gfRoomAnchorW
        (progn
          (setq roomBottomY (+ gfBottomY roomOffset)
                roomTopY (+ roomBottomY roomHeight)
                roomHeaderY (- roomTopY roomHeader)
                roomTextPt
                  (list (/ (+ roomLeftX roomRightX) 2.0)
                        (/ (+ roomTopY roomHeaderY) 2.0)
                        z))
          (degk--column-frame-polyline
            (list
              (list roomLeftX roomBottomY z)
              (list roomRightX roomBottomY z)
              (list roomRightX roomTopY z)
              (list roomLeftX roomTopY z))
            layer T)
          (degk--column-frame-polyline
            (list
              (list roomLeftX roomHeaderY z)
              (list roomRightX roomHeaderY z))
            layer nil)
          (degk--column-room-text
            roomTextPt "ELEKTRÝK ODASI" layer roomTextHeight)
          (if roomSourceBlocks
            (progn
              (setq roomCenterX (/ (+ roomLeftX roomRightX) 2.0)
                    roomCenterY
                      (- (/ (+ roomBottomY roomTopY) 2.0) roomBlockDrop)
                    powerTargetW
                      (list (- roomCenterX (/ roomBlockSpacing 2.0))
                            roomCenterY z)
                    panelTargetW
                      (list (+ roomCenterX (/ roomBlockSpacing 2.0))
                            roomCenterY z)
                    powerCopy
                      (degk--copy-room-block-safe
                        (car roomSourceBlocks) powerTargetW)
                    panelCopy
                      (degk--copy-room-block-safe
                        (cadr roomSourceBlocks) panelTargetW))
              ;; Ikisinden biri kopyalanamazsa odada yarim bir sembol cifti birakma.
              (if (and powerCopy panelCopy)
                (progn
                  (degk--panel-loop-label (vlax-vla-object->ename panelCopy) *degk-panel-loop-count* roomTextHeight layer)
                  (degk--room-device-label (vlax-vla-object->ename panelCopy)
                    *degk-last-panel-name* nil (degk--selected-ups-layer areaSS nil) layer
                    (degk--column-floor-groups-english-p floorLabelGroups))
                  (degk--room-device-label (vlax-vla-object->ename powerCopy)
                    *degk-last-panel-name* T (degk--selected-ups-layer areaSS nil) layer
                    (degk--column-floor-groups-english-p floorLabelGroups))
                (setq *degk-ups-source*
                  (list powerCopy
                        (degk--ups-riser-left-x mainRiserEntities shaftCenterX)
                        (car (degk--pts-x-bounds roomGfRiserLimits))
                        verticalLayoutP))))
              (if (and powerCopy panelCopy)
                (if roomRiserLayer
                  (progn
                    (if (and verticalLayoutP roomGfLoopRecords)
                      (progn
                        (setq roomGfAligned
                          (degk--align-gf-combined-to-panel
                            panelCopy roomGfLoopRecords roomGfRiserLimits
                            roomGfRiserEntities entities floorSpacing mainRiserEntities)
                              roomGfLoopRecords (car roomGfAligned)
                              roomGfRiserLimits (cadr roomGfAligned))))
                    (degk--draw-room-panel-risers
                    panelCopy roomRiserLayer roomGfRiserLimits
                    roomGfLoopRecords roomGfRiserEntities
                    (if (> (length floorLabelGroups) 1)
                      mainRiserEntities
                      nil)
                    verticalLayoutP))
                  ;; Kaynakta kombine multiline yoksa looplari birbirine
                  ;; baglamadan her bir cift ucu ayri ayri YAP'a getir.
                  (if roomGfLoopRecords
                    (progn
                      (setq roomGfLoopRecords
                        (degk--align-gf-loops-to-panel
                          panelCopy roomGfLoopRecords entities floorSpacing))
                      (degk--draw-room-panel-direct-loops
                        panelCopy roomGfLoopRecords))))
                (progn
                  (if powerCopy
                    (vl-catch-all-apply 'vla-Delete (list powerCopy)))
                  (if panelCopy
                    (vl-catch-all-apply 'vla-Delete (list panelCopy)))
                  (princ
                    "\nDK: Elektrik odasi panel/guc kaynagi kopyasi tamamlanamadi.")))))))
      T)
    nil)
)

(defun degk--maybe-draw-column-frame (afterEnt basePt processResult / total entities answer)
  (setq total
    (if (and (= (type processResult) 'LIST)
             (> (length processResult) 1)
             (numberp (cadr processResult)))
      (cadr processResult)
      0))
  (if (> total 0)
    (progn
      (setq entities (degk--column-frame-new-entities afterEnt))
      (initget "Evet Hayir")
      (setq answer
        (getkword
          "\nKolon semasi kat cercevesi cizilsin mi? [Evet/Hayir] <Hayir>: "))
      (if (= answer "Evet")
        (if (degk--perf-call "Cerceve-oda-saft" 'degk--draw-column-frame (list entities basePt processResult))
          (princ "\nDK: Kolon semasi cercevesi ve kat ayiricilari cizildi.")
          (princ "\nDK: Kolon semasi sinirlari hesaplanamadi.")))))
  processResult
)

(defun degk--selected-combined-riser-layer
  (pickset / i ent ed entType layer layers pattern actual selectedLayer)
  ;; Secili alandaki gercek layer adini korur; ayar listesindeki ilk
  ;; eslesen pattern kombine kolon layeri olarak oncelik kazanir.
  (setq i 0
        layers nil)
  (if (and pickset (= (type pickset) 'PICKSET))
    (while (< i (sslength pickset))
      (setq ent     (ssname pickset i)
            ed      (if ent (entget ent) nil)
            entType (if ed (cdr (assoc 0 ed)) nil)
            layer   (if ed (cdr (assoc 8 ed)) nil))
      (if (and layer
               (or (= entType "LWPOLYLINE") (= entType "POLYLINE")))
        (if (not (member (norm-layer layer) (mapcar 'norm-layer layers)))
          (setq layers (append layers (list layer)))))
      (setq i (1+ i))))
  (foreach pattern (DEG:CFG-LIST 'DK_COMBINED_RISER_LAYERS)
    (foreach actual layers
      (if (and (null selectedLayer)
               pattern (/= pattern "")
               (deg-wcmatch actual pattern))
        (setq selectedLayer actual))))
  selectedLayer
)

(defun degk--nearest-mouth-y-pair
  (pointGroups referenceY / group sorted leftPt rightPt meanY score bestScore best)
  ;; X konumu farkli olsa da referans seviyeye en yakin loopun sol/sag agiz
  ;; Y degerlerini verir. Tek bodrum loopunu GF seviyesine uzatmakta kullanilir.
  (foreach group pointGroups
    (if (and (listp group) (>= (length group) 2))
      (progn
        (setq sorted
          (vl-sort group
            (function (lambda (a b) (< (car a) (car b))))))
        (setq leftPt (car sorted)
              rightPt (last sorted))
        (if (and (listp leftPt) (listp rightPt)
                 (numberp (cadr leftPt)) (numberp (cadr rightPt)))
          (progn
            (setq meanY (/ (+ (cadr leftPt) (cadr rightPt)) 2.0)
                  score (abs (- meanY referenceY)))
            (if (or (null bestScore) (< score bestScore))
              (setq bestScore score
                    best (list (cadr leftPt) (cadr rightPt)))))))))
  best
)

(defun degk--draw-combined-riser
  (layer loopPointGroups outerFallbackP / group p allPoints minX z gap leftX rightX
    pointIndex rec leftRecords rightRecords leftRec rightRec score meanY
    candidateIndex candidates candidate pairTolerance usedLeft usedRight
    pairRecords pairIndex pairCount bottomPair topPair singlePair targetPair
    leftMinY leftMaxY rightMinY rightMaxY limitsOnlyP beforeEnt drawEnt beforeSecond secondEnt drawRes secondRes)
  ;; Yalniz aralarindaki Y farki ofset kadar olan sol-sag temaslar gercek
  ;; fillet agzidir. Loopun uzaktaki ust/alt geometrik noktalarini dikkate alma.
  (setq *degk-last-combined-riser-limits* nil
        *degk-last-combined-riser-entities* nil)
  (foreach group loopPointGroups
    (if (listp group)
      (foreach p group
        (if (and (listp p) (numberp (car p)) (numberp (cadr p)))
          (progn
            (setq allPoints (cons p allPoints))
            (if (or (null minX) (< (car p) minX))
              (setq minX (car p)))
            (if (and (null z) (caddr p) (numberp (caddr p)))
              (setq z (caddr p))))))))
  (if (null z) (setq z 0.0))
  (setq gap        (abs (DEG:CFG-DK-NUM-OR 'DK_UNDER_X2 10.0))
        leftX      minX
        rightX     (if minX (+ minX gap) nil)
        pointIndex 0
        leftRecords nil
        rightRecords nil
        candidates nil
        candidateIndex 0
        pairTolerance (max 1e-6 (* gap 0.10))
        usedLeft nil
        usedRight nil
        pairRecords nil
        pairIndex 0)
  (foreach p allPoints
    (setq rec (list (cadr p) pointIndex)
          pointIndex (1+ pointIndex))
    (if (<= (abs (- (car p) leftX)) (abs (- (car p) rightX)))
      (setq leftRecords (cons rec leftRecords))
      (setq rightRecords (cons rec rightRecords))))
  ;; Once tum olasi temaslari puanla. En yakin ofset eslesmelerini global
  ;; sirada tuketmek, uzaktaki bir noktanin gercek fillet ucunu kapmasini onler.
  (foreach leftRec leftRecords
    (foreach rightRec rightRecords
      (setq score (abs (- (abs (- (car leftRec) (car rightRec))) gap)))
      (if (<= score pairTolerance)
        (progn
          (setq meanY (/ (+ (car leftRec) (car rightRec)) 2.0)
                candidates
                  (cons
                    (list score meanY
                          (car leftRec) (car rightRec)
                          (cadr leftRec) (cadr rightRec)
                          candidateIndex)
                    candidates)
                candidateIndex (1+ candidateIndex))))))
  (setq candidates
    (vl-sort candidates
      (function
        (lambda (a b)
          (cond
            ((< (car a) (car b)) T)
            ((> (car a) (car b)) nil)
            ((< (cadr a) (cadr b)) T)
            ((> (cadr a) (cadr b)) nil)
            (T (< (nth 6 a) (nth 6 b))))))))
  (foreach candidate candidates
    (if (and (not (member (nth 4 candidate) usedLeft))
             (not (member (nth 5 candidate) usedRight)))
      (setq usedLeft (cons (nth 4 candidate) usedLeft)
            usedRight (cons (nth 5 candidate) usedRight)
            pairRecords
              (cons
                (list (cadr candidate)
                      (nth 2 candidate)
                      (nth 3 candidate)
                      pairIndex)
                pairRecords)
            pairIndex (1+ pairIndex))))
  ;; Eslesen agizlari alttan uste sirala. Birlesik dik hat ikinci loop
  ;; agzindan sondan bir onceki loop agzina kadar gider.
  (setq pairRecords
    (vl-sort pairRecords
      (function
        (lambda (a b)
          (if (= (car a) (car b))
            (< (nth 3 a) (nth 3 b))
            (< (car a) (car b))))))
        pairCount (length pairRecords))
  (cond
    ;; Yalniz tek bodrum loopu varsa saft dikmelerini GF loop seviyesine kadar
    ;; uzat. X'ler ana loopun agizlarindan, hedef Y'ler GF agizlarindan gelir.
    ((and (= pairCount 1)
          (listp outerFallbackP)
          (eq (car outerFallbackP) 'ONE_SIDE)
          (setq singlePair (car pairRecords))
          (setq targetPair
            (degk--nearest-mouth-y-pair
              (cadr outerFallbackP) (car singlePair))))
      (setq leftMinY  (min (cadr singlePair) (car targetPair))
            leftMaxY  (max (cadr singlePair) (car targetPair))
            rightMinY (min (caddr singlePair) (cadr targetPair))
            rightMaxY (max (caddr singlePair) (cadr targetPair))))
    ;; Tek GF loopunda ayri bir dik multiline gerekmez. Iki panel kolu
    ;; loopun kendi fillet agizlarina dogrudan baglanabilsin diye bu agizlari
    ;; sifir uzunluklu hedef limitleri olarak sakla.
    ((and (eq outerFallbackP 'GF)
          (= pairCount 1)
          (setq singlePair (car pairRecords)))
      (setq leftMinY   (cadr singlePair)
            leftMaxY   (cadr singlePair)
            rightMinY  (caddr singlePair)
            rightMaxY  (caddr singlePair)
            limitsOnlyP T))
    ;; GF'de iki loop varsa her magenta kol panelden gorulen ilk (ust) loopun
    ;; kendi fillet agzinda biter. Diger loop kendi layer rengindeki kare
    ;; uzantiyla bu iki agiz noktasina baglanir.
    ((and (eq outerFallbackP 'GF)
          (= pairCount 2)
          (setq singlePair (last pairRecords)))
      (setq leftMinY   (cadr singlePair)
            leftMaxY   (cadr singlePair)
            rightMinY  (caddr singlePair)
            rightMaxY  (caddr singlePair)
            limitsOnlyP T))
    ;; GF'de uc loop varsa ikinci ve sondan bir onceki ayni orta looptur.
    ;; Iki dik hatti orta loopun iki agiz seviyesi arasinda kisa bir cekirdek
    ;; olarak kur; dis looplar kendi renkleriyle bu cekirdege uzasin.
    ((and (eq outerFallbackP 'GF)
          (= pairCount 3)
          (setq singlePair (nth 1 pairRecords)))
      (setq leftMinY  (min (cadr singlePair) (caddr singlePair))
            leftMaxY  (max (cadr singlePair) (caddr singlePair))
            rightMinY leftMinY
            rightMaxY leftMaxY))
    ;; GF kombinesi panel yatayindan asagi gidiyorsa tum fillet agizlarini
    ;; kapsa; yalniz en alttaki loop daha sonra kare dirsege cevrilir.
    ((and (eq outerFallbackP 'ALL) (>= pairCount 2))
      (setq bottomPair (car pairRecords)
            topPair    (last pairRecords)
            leftMinY  (cadr bottomPair)
            rightMinY (caddr bottomPair)
            leftMaxY  (cadr topPair)
            rightMaxY (caddr topPair)))
    ((>= pairCount 4)
      (setq bottomPair (nth 1 pairRecords)
            topPair    (nth (- pairCount 2) pairRecords)
            leftMinY  (cadr bottomPair)
            rightMinY (caddr bottomPair)
            leftMaxY  (cadr topPair)
            rightMaxY (caddr topPair)))
    ;; GF ayri bir kolon oldugu icin az looplu durumda ilk-son agizlari kullan.
    ((and outerFallbackP (>= pairCount 2))
      (setq bottomPair (car pairRecords)
            topPair    (last pairRecords)
            leftMinY  (cadr bottomPair)
            rightMinY (caddr bottomPair)
            leftMaxY  (cadr topPair)
            rightMaxY (caddr topPair))))
  (if (and layer leftX rightX
           leftMinY leftMaxY rightMinY rightMaxY
           (or limitsOnlyP
               (and (> (- leftMaxY leftMinY) 1e-6)
                    (> (- rightMaxY rightMinY) 1e-6))))
    (progn
      (setq *degk-last-combined-riser-limits*
        (list
          (list leftX leftMinY z)
          (list rightX rightMinY z)
          (list leftX leftMaxY z)
          (list rightX rightMaxY z)))
      (if limitsOnlyP
        T
        (progn
          (degk--ensure-layer-editable layer)
          (setq beforeEnt (entlast)
                drawRes
                  (degk--entmake-lwpoly
                    (list (list leftX leftMaxY z) (list leftX leftMinY z))
                    layer
                    nil)
                drawEnt (entlast)
                beforeSecond drawEnt
                secondRes
                  (if (> gap 1e-9)
                    (degk--entmake-lwpoly
                      (list (list rightX rightMaxY z) (list rightX rightMinY z))
                      layer
                      nil)
                    nil)
                secondEnt (entlast))
          (if (and drawRes secondRes
                   drawEnt secondEnt
                   (not (eq beforeEnt drawEnt))
                   (not (eq beforeSecond secondEnt)))
            (progn
              (setq *degk-last-combined-riser-entities*
                (list drawEnt secondEnt))
              T)
            nil))))
    nil)
)

(defun degk--normal-area-process (dkAreaPickset basePt layoutMode / polylines monitorLinks monitorExtraCount combinedRiserLayer roomSourceBlocks loopLeftPoints gfLoopLeftPoints lastLoopLeftPoints loopDrawRecords gfLoopDrawRecords riserLimits riserEntities gfRiserLimits gfRiserEntities lastLoopDrawRecord groupGap railGap floorSpacing gfShift gfLoopCount gfLayoutLoopCount gfFrameLoopCount gfFloorExtraRows gfRoomAnchorW gfRoomCandidateW layoutRowYs floorLabelAnchors floorLabel floorAnchor haveBelowFloor haveAboveFloor oneSidedRiserP riserFallbackMode baseU targetU targetW groupIndex totalCopies ent memberEnts startPt runRes runSucceededP records rec valid floorNo floorRow floorKey columnNo floorCounts floorRec floorRailSlots railSlotRec railSlotNo floorCountsBefore floorRailSlotsBefore floorRightEdges floorRightRec floorLeftEdges floorLeftRec maxFloor roofFloor roofPresentP fallbackRow verticalP verticalRow verticalCounts verticalCountsBefore verticalRowBefore verticalFloorRows verticalPackFloors verticalPackedFloorRows verticalPackedFloorRowsBefore verticalPackedP verticalPackedRowP packedFloorRowRec sourceInserts flasherSorted specialP terminalSourceObj terminalCopyRec terminalCopyObj terminalBaseW terminalBaseU terminalLayoutRow terminalLayoutFloor terminalUsedCopies terminalUsedCopiesBefore terminalFallback terminalCopyHandle wantedTerminalRow rowRatio edgeKey usedRows *degk-current-layout-row* *degk-current-layout-floor* *degk-dispatch-terminal-source* *degk-dispatch-terminal-copy-rec* *degk-monitor-linked-source-handles* *degk-last-loop-left-points* *degk-last-loop-draw-record* *degk-last-combined-riser-limits* *degk-last-combined-riser-entities*)
  (setq *degk-source-insert-snapshot* (ssget "_X" '((0 . "INSERT"))))
  (setq polylines (degk--normal-area-polylines dkAreaPickset)
        monitorLinks (degk--monitor-link-records dkAreaPickset)
        combinedRiserLayer
          (degk--selected-combined-riser-layer dkAreaPickset)
        roomSourceBlocks (degk--room-source-blocks dkAreaPickset)
        loopLeftPoints nil
        gfLoopLeftPoints nil
        loopDrawRecords nil
        gfLoopDrawRecords nil
        riserLimits nil
        riserEntities nil
        gfRiserEntities nil
        layoutRowYs nil
        floorLabelAnchors nil
        *degk-monitor-linked-source-handles*
          (degk--monitor-linked-source-handles monitorLinks)
        groupGap (abs (DEG:CFG-DK-SIGNED-NUM-OR 'DK_NORMAL_GROUP_SPACING 0.0))
         ;; Yatay paralel raylar DK_UNDER_X2 kadar aralikla dizilir.
         railGap (DEG:CFG-DK-NUM-OR 'DK_UNDER_X2 10.0)
         ;; Kat satirlari arasindaki mesafe DO > DK sayfasindan ayarlanir.
         floorSpacing (DEG:CFG-DK-NUM-OR 'DK_NORMAL_FLOOR_SPACING 700.0)
         ;; GF/ZK/GR loop grubu fiziksel olarak toplam 22000 mm saga kayar.
         gfShift (* 2200.0 (DEG:PLAN-UNIT-SCALE))
         gfRoomAnchorW nil
         baseU (trans basePt 0 1)
        verticalP (eq layoutMode 'DIK)
        verticalRow 0
        verticalCounts nil
        verticalFloorRows nil
        verticalPackedFloorRows nil
        groupIndex 0
        totalCopies 0
        floorCounts nil
        floorRailSlots nil
        floorRightEdges nil
        floorLeftEdges nil
        maxFloor 0
        fallbackRow 0
        terminalUsedCopies nil
        records
          (degk--records-flasher-last
            (degk--perf-call "Kat-loop yerlesim kayitlari" 'degk--normal-area-layout-records (list polylines))))
  (setq gfLoopCount (degk--gf-loop-count records)
        gfFloorExtraRows
          (degk--gf-floor-extra-rows
            verticalP gfLoopCount gfLoopCount))
  (foreach rec records
    (if (car rec)
      (if (degk--roof-floor-p (nth 1 rec))
        (setq roofPresentP T)
        (if (> (nth 1 rec) maxFloor)
          (setq maxFloor (nth 1 rec)))))
  )
  ;; RF/CK sabit ve cok uzak bir kat numarasi kullanmaz. Secimdeki en yuksek
  ;; normal katin tam bir ust satiri olur; gecersiz katlar da catinin ustunden
  ;; devam ederek ayni satira binmez.
  (if roofPresentP
    (setq roofFloor (1+ maxFloor)
          maxFloor roofFloor))
  (setq sourceInserts
          (if verticalP (degk--column-source-inserts) nil)
        verticalPackFloors
          (if verticalP
            (degk--vertical-pack-floors
              records sourceInserts *degk-monitor-linked-source-handles*
              groupGap roofFloor)
            nil)
        gfLayoutLoopCount
          (if (and verticalP
                   (> gfLoopCount 0)
                   (member 0 verticalPackFloors))
            1
            gfLoopCount)
        gfFloorExtraRows
          (degk--gf-floor-extra-rows
            verticalP gfLoopCount gfLayoutLoopCount))
  (setq flasherSorted nil)
  (while records
    ;; Normal looplar tamamlandiginda terminal kopya konumlari artik bellidir.
    ;; Kalan ozel looplari her katta sagdan sola bir kez yeniden sirala.
    (if (and (not flasherSorted)
             (degk--layout-record-flasher-p (car records)))
      (setq records
              (degk--flasher-records-connected-first
                (degk--sort-flasher-records-right-first records))
            flasherSorted T)
    )
    (setq rec     (car records)
          records (cdr records))
    (setq valid   (car rec)
          floorNo (nth 1 rec)
          ent     (nth 4 rec)
          memberEnts (degk--layout-record-members rec)
          specialP (degk--layout-record-flasher-p rec)
          terminalSourceObj (nth 6 rec)
          terminalCopyRec nil
          terminalCopyObj nil
          terminalBaseW nil
          terminalBaseU nil
          terminalLayoutRow nil
          terminalLayoutFloor nil
          railSlotRec nil
          railSlotNo 0
          floorCountsBefore floorCounts
          floorRailSlotsBefore floorRailSlots
          verticalCountsBefore verticalCounts
          verticalRowBefore verticalRow
          verticalPackedFloorRowsBefore verticalPackedFloorRows
          terminalUsedCopiesBefore terminalUsedCopies)
    (if (and valid roofFloor (degk--roof-floor-p floorNo))
      (setq floorNo roofFloor))
    ;; Kaynak planda temas kaydi olsa bile kolon semasinda o kaynagin kopyasi
    ;; yoksa bu gercek bir kolon baglantisi degildir. Kaydi serbest birak ve
    ;; ayni kattaki bos kopya aramasina devam et.
    (if (and specialP terminalSourceObj)
      (progn
        (setq terminalCopyRec
          (degk--area-module-copy-get
            terminalSourceObj
            (if valid floorNo nil)))
        (setq terminalCopyHandle
          (if terminalCopyRec
            (degk--terminal-copy-handle terminalCopyRec)
            ""))
        (if (and (/= terminalCopyHandle "")
                 (member terminalCopyHandle terminalUsedCopies))
          (progn
            ;; Ayni kopyaya ikinci bir loop baglama; bu loop icin baska bos
            ;; terminal ara.
            (setq terminalCopyRec nil
                  terminalSourceObj nil
                  terminalCopyHandle "")))
        (if (null terminalCopyRec)
          (progn
            (princ
              "\nDK: Terminal temasi var fakat kolon kopyasi yok; ayni katta bos modul aranacak.")
            (setq terminalSourceObj nil))
          (setq terminalUsedCopies
            (cons terminalCopyHandle terminalUsedCopies)))))
    ;; Fiziksel baglantisi olmayan flasor loopu icin tahmini kaynak secmek
    ;; yerine, kolon semasinda ayni kat/satirda bos duran gercek kopyayi kullan.
    (if (and specialP (null terminalCopyRec) valid)
      (progn
        (setq wantedTerminalRow (if verticalP nil (- floorNo 1))
              terminalFallback
                (degk--unused-terminal-copy-for-layout
                  rec floorNo wantedTerminalRow terminalUsedCopies))
        (if terminalFallback
          (progn
            (setq terminalSourceObj (car terminalFallback)
                  terminalCopyRec (cadr terminalFallback)
                  terminalCopyHandle (caddr terminalFallback)
                  terminalUsedCopies
                    (cons terminalCopyHandle terminalUsedCopies))
            (princ
              (strcat
                "\nDK: Baglantisiz flasor loop kolon semasindaki bos module baglandi: modul="
                terminalCopyHandle
                " kat=" (itoa floorNo))))
          (princ
            (strcat
              "\nDK: Ayni katta kullanilmamis kolon terminal kopyasi bulunamadi: kat="
              (itoa floorNo))))))
    ;; Bagli loopun kati kolon kopyasinda saklanan gercek kat bilgisinden gelir.
    ;; Yerlesim satiri dik modda kat degildir; yalniz eski yatay kayitlarda
    ;; gercek kat eksikse geriye donuk yedek olarak kullanilir.
    (if (and specialP
             (or terminalCopyRec
                 (and terminalSourceObj
                      (setq terminalCopyRec
                        (degk--area-module-copy-get
                          terminalSourceObj
                          (if valid floorNo nil))))))
      (progn
        (setq terminalLayoutRow   (nth 2 terminalCopyRec)
              terminalLayoutFloor (nth 3 terminalCopyRec))
        (cond
          ((numberp terminalLayoutFloor)
            (setq floorNo terminalLayoutFloor
                  valid T))
          ((and (not verticalP) (numberp terminalLayoutRow))
            (setq floorNo (1+ terminalLayoutRow)
                  valid T)))))
    ;; DKK her polyline'i bagimsiz bir sembol listesi olarak ozetler.
    ;; Ayni sembol baska bir hatta da varsa o hat icin yeniden gosterilir.
    (if (degkk--active-p)
      (setq *DEG_DKK_GROUPS* nil
            *DEG_DKK_SEEN_OCCURRENCES* nil
            *DEG_DK_LAST_COPY_OBJ* nil)
    )
    (if verticalP
      (progn
       (cond
        ((and specialP
              (or terminalCopyRec
                  (and terminalSourceObj
                       (setq terminalCopyRec
                         (degk--area-module-copy-get terminalSourceObj floorNo))))
              (setq terminalCopyObj (car terminalCopyRec))
              (setq terminalBaseW (deg-get-inspt terminalCopyObj)))
          ;; Dik moddaki ozel loop, yeni bir satir acmak yerine baglandigi
          ;; terminal kopyasinin kaydedilmis satirina ve o satirin sonuna gider.
          ;; INSERT noktasindan satir tahmini, blok geometrisine gore bir alt/ust
          ;; satira yuvarlanabildigi icin yalniz eski kayitlarda yedek olarak kalir.
          (setq terminalBaseU (trans terminalBaseW 0 1)
                terminalLayoutRow (nth 2 terminalCopyRec)
                rowRatio
                  (if (> (abs floorSpacing) 1e-9)
                    (/ (- (cadr terminalBaseU) (cadr baseU)) floorSpacing)
                    0.0)
                floorRow
                  (if (numberp terminalLayoutRow)
                    terminalLayoutRow
                    (fix (+ rowRatio (if (>= rowRatio 0.0) 0.5 -0.5))))
                floorRec (assoc floorRow verticalCounts)
                columnNo (if floorRec (cdr floorRec) 0))
          (if floorRec
            (setq verticalCounts
              (subst (cons floorRow (1+ columnNo)) floorRec verticalCounts))
            (setq verticalCounts
              (cons (cons floorRow 1) verticalCounts))))
        ((and specialP valid)
          ;; Terminal/kopya eslesmesi yoksa SIRA_NO'dan bulunan kat satiri
          ;; kullanilir; plandaki gorunmeyen baglanti kati degistirmez.
          (setq packedFloorRowRec
                  (assoc floorNo verticalPackedFloorRows)
                floorRow
                  (if packedFloorRowRec
                    (cdr packedFloorRowRec)
                    (- floorNo 1))
                floorRec (assoc floorRow verticalCounts)
                columnNo (if floorRec (cdr floorRec) 0))
          (if floorRec
            (setq verticalCounts
              (subst (cons floorRow (1+ columnNo)) floorRec verticalCounts))
            (setq verticalCounts
              (cons (cons floorRow 1) verticalCounts)))
          (if (>= floorRow verticalRow)
            (setq verticalRow (1+ floorRow))))
        (T
          ;; Sigan coklu loop kati tek satir kullanir; digerleri ayri satir kalir.
          (setq verticalPackedP
            (and valid (member floorNo verticalPackFloors)))
          (if (and verticalPackedP
                   (setq packedFloorRowRec
                     (assoc floorNo verticalPackedFloorRows)))
            (setq floorRow (cdr packedFloorRowRec))
            (progn
              (setq floorRow verticalRow
                    verticalRow (1+ verticalRow))
              (if verticalPackedP
                (setq verticalPackedFloorRows
                  (cons (cons floorNo floorRow) verticalPackedFloorRows)))))
          (setq
                floorRec (assoc floorRow verticalCounts)
                columnNo (if floorRec (cdr floorRec) 0))
          (if floorRec
            (setq verticalCounts
              (subst (cons floorRow (1+ columnNo)) floorRec verticalCounts))
            (setq verticalCounts
              (cons (cons floorRow 1) verticalCounts)))))
      ;; Paketlenmis dik kat, yatay moddaki iki-ray slotlarini kullanir.
      (setq packedFloorRowRec
              (if valid (assoc floorNo verticalPackedFloorRows) nil)
            verticalPackedRowP
              (and packedFloorRowRec
                   (= floorRow (cdr packedFloorRowRec))))
      (if verticalPackedRowP
        (progn
          (setq railSlotRec (assoc floorRow floorRailSlots)
                railSlotNo (if railSlotRec (cdr railSlotRec) 0))
          (if railSlotRec
            (setq floorRailSlots
              (subst
                (cons floorRow (+ railSlotNo (if specialP 1 2)))
                railSlotRec floorRailSlots))
            (setq floorRailSlots
              (cons (cons floorRow (if specialP 1 2)) floorRailSlots))))))
      (progn
        (if valid
          (setq floorRow (- floorNo 1))
          (progn
            ;; SIRA_NO'suz normal loop yeni bir satir acmaya devam eder. Daha
            ;; sonra bu satirdaki module baglanan ozel loop ayni satir anahtari
            ;; uzerinden mevcut grubun sagina yerlesebilir.
            (setq floorRow (+ maxFloor fallbackRow)
                  fallbackRow (1+ fallbackRow))))
        ;; Yatay duzende sayaclar kat metninden degil gercek satirdan tutulur.
        ;; Boylece SIRA_NO olmasa da ayni satirdaki looplar birbirini gorur.
        (setq floorRec (assoc floorRow floorCounts)
              columnNo (if floorRec (cdr floorRec) 0)
              railSlotRec (assoc floorRow floorRailSlots)
              railSlotNo (if railSlotRec (cdr railSlotRec) 0))
        (if floorRec
          (setq floorCounts
            (subst (cons floorRow (1+ columnNo)) floorRec floorCounts))
          (setq floorCounts (cons (cons floorRow 1) floorCounts)))
        (if railSlotRec
          (setq floorRailSlots
            (subst
              (cons floorRow (+ railSlotNo (if specialP 1 2)))
              railSlotRec
              floorRailSlots))
          (setq floorRailSlots
            (cons (cons floorRow (if specialP 1 2)) floorRailSlots)))
      )
    )
    (setq edgeKey floorRow)
    ;; Elektrik odasi, GF looplari kaydirilmadan onceki baslangic X'ini
    ;; kullanir. Yalniz basariyla cizilen ilk GF loopunda kalici olur.
    (setq gfRoomCandidateW
      (if (and (numberp floorNo) (= floorNo 0))
        (trans
          (list (car baseU)
                (+ (cadr baseU) (* floorRow floorSpacing))
                (if (caddr baseU) (caddr baseU) 0.0))
          1 0)
        nil))
    (setq targetU
           (list (+ (car baseU)
                    (if (and (numberp floorNo) (= floorNo 0))
                      gfShift
                      0.0))
                 (degk--gf-layout-y
                   (cadr baseU) floorRow floorNo
                   floorSpacing gfFloorExtraRows)
                 (if (caddr baseU) (caddr baseU) 0.0))
           targetW (trans targetU 1 0)
           startPt (vl-catch-all-apply 'vlax-curve-getStartPoint (list ent)))
    ;; Ayni kattaki sonraki grup, onceki grubun gercek sag ucundan ayarlanan
    ;; loop araligi kadar sonra baslar. DK alt hatti baslangictan 400 cm sola uzadigi
    ;; icin hedef noktasina bu fiziksel uzanti da eklenir.
    (if (and floorRec
             (setq floorRightRec (assoc edgeKey floorRightEdges)))
      (setq targetW
        (list (+ (cdr floorRightRec)
                 groupGap
                 (degk--normal-group-left-extension))
              (cadr targetW)
              (if (caddr targetW) (caddr targetW) 0.0)))
    )
    (if (vl-catch-all-error-p startPt)
      (setq startPt (cdr (assoc 10 (entget ent))))
    )
     (setq floorLeftRec
       (if (and floorRec (or (not verticalP) verticalPackedRowP))
         (assoc floorRow floorLeftEdges)
         nil))
     (setq *degk-dispatch-sel* (list ent startPt)
           *degk-dispatch-loop-ents* memberEnts
           *degk-dispatch-base* targetW
           *degk-dispatch-loop-drop*
             (if verticalP
               (if verticalPackedRowP
                 ;; Ayni kat satirindaki her normal loop iki ray yeri kaplar.
                 (if specialP
                   (* (max 0 (1- railSlotNo)) railGap)
                   (* railSlotNo railGap))
                 ;; Alt alta kalan dik looplarin mevcut davranisi korunur.
                 (* columnNo railGap))
               (if specialP
                 ;; Ozel loop daha sonra bir ray araligi asagi tasinir; bu nedenle
                 ;; baslangic dusumunu bir slot eksik kur ve gercek rayi siraya oturt.
                 (* (max 0 (1- railSlotNo)) railGap)
                 (* railSlotNo railGap)))
            *degk-dispatch-rail-left-x* (if floorLeftRec (cdr floorLeftRec) nil)
             *degk-current-layout-row* floorRow
             *degk-current-layout-floor* floorNo
             ;; Layout kaydinda belirlenen fiziksel terminali DK:BASE'e aynen
            ;; aktar. DK:BASE ayni hatti tekrar tarayip komsu modulu secmesin.
            *degk-dispatch-terminal-source* terminalSourceObj
            ;; Bos terminal kolon semasindan secildiyse kaynak nesne aramadan
            ;; gercek kopya/anchor kaydini dogrudan DK:BASE'e aktar.
             *degk-dispatch-terminal-copy-rec* terminalCopyRec
             *degk-last-group-min-x* nil
            *degk-last-group-max-x* nil
            *degk-last-loop-left-points* nil
            *degk-last-loop-draw-record* nil
            *degk-last-copy-count* 0)
     (setq runRes (vl-catch-all-apply 'DK:BASE '()))
     (setq *degk-dispatch-sel* nil
           *degk-dispatch-loop-ents* nil
           *degk-dispatch-base* nil
           *degk-dispatch-loop-drop* nil
            *degk-dispatch-rail-left-x* nil
             *degk-current-layout-row* nil
             *degk-current-layout-floor* nil
             *degk-dispatch-terminal-source* nil
            *degk-dispatch-terminal-copy-rec* nil)
    (setq runSucceededP
      (and (not (vl-catch-all-error-p runRes))
           (numberp *degk-last-copy-count*)
           (> *degk-last-copy-count* 0)))
    (if (vl-catch-all-error-p runRes)
      (princ
        (strcat "\nDK: Bir polyline islenemedi, diger hatlara devam ediliyor: "
                (vl-catch-all-error-message runRes)))
    )
     (if runSucceededP
       (progn
         (if (not specialP)
           (setq *degk-panel-loop-count*
             (1+ (if (numberp *degk-panel-loop-count*) *degk-panel-loop-count* 0))))
         (if (and targetW (numberp (cadr targetW)))
            (progn
              (setq layoutRowYs (cons (cadr targetW) layoutRowYs))
              ;; Ozel looplar ayni kat etiketini ikinci kez uretmesin. Gercek
              ;; kat adi normal loopun SIRA_NO bilgisinden ve cizimdeki haliyle gelir.
              (if (and (not specialP) (numberp floorNo))
                (progn
                  (setq floorLabel
                    (degk--floor-label-from-sira (nth 9 rec)))
                  (setq floorLabelAnchors
                    (cons
                      (list floorNo floorLabel (cadr targetW))
                      floorLabelAnchors))))))
         (setq lastLoopLeftPoints *degk-last-loop-left-points*
               lastLoopDrawRecord *degk-last-loop-draw-record*)
         (if lastLoopLeftPoints
           (if (and (numberp floorNo) (= floorNo 0))
             (setq gfLoopLeftPoints
               (cons lastLoopLeftPoints gfLoopLeftPoints))
             (setq loopLeftPoints
               (cons lastLoopLeftPoints loopLeftPoints))))
         (if lastLoopDrawRecord
           (if (and (numberp floorNo) (= floorNo 0))
             (setq gfLoopDrawRecords
               (cons lastLoopDrawRecord gfLoopDrawRecords))
             (setq loopDrawRecords
               (cons lastLoopDrawRecord loopDrawRecords))))
         (if (and (null gfRoomAnchorW) gfRoomCandidateW)
           (setq gfRoomAnchorW gfRoomCandidateW))
         (if (and verticalP (null (assoc floorRow verticalFloorRows)))
           (progn
             (setq floorKey
               (if (and valid (numberp floorNo))
                 floorNo
                 (strcat "ROW_" (itoa floorRow))))
             (setq verticalFloorRows
               (cons (cons floorRow floorKey) verticalFloorRows))))
         (setq totalCopies (+ totalCopies *degk-last-copy-count*)
              groupIndex (1+ groupIndex))
         (if (numberp *degk-last-group-max-x*)
          (if (setq floorRightRec (assoc edgeKey floorRightEdges))
            (setq floorRightEdges
              (subst (cons edgeKey *degk-last-group-max-x*)
                     floorRightRec
                     floorRightEdges))
            (setq floorRightEdges
              (cons (cons edgeKey *degk-last-group-max-x*) floorRightEdges))
          )
        )
         (if (and (or (not verticalP) verticalPackedRowP)
                 (numberp *degk-last-group-min-x*)
                 (null (assoc floorRow floorLeftEdges)))
          (setq floorLeftEdges
            (cons (cons floorRow *degk-last-group-min-x*) floorLeftEdges))
        )
      )
      (progn
        ;; Blok kopyalamayan veya hata veren polyline bir sonraki gorunen loop
        ;; icin bos yatay ray/satir seviyesi ayirmasin.
        (setq floorCounts floorCountsBefore
              floorRailSlots floorRailSlotsBefore
              verticalCounts verticalCountsBefore
              verticalRow verticalRowBefore
              verticalPackedFloorRows verticalPackedFloorRowsBefore
              terminalUsedCopies terminalUsedCopiesBefore)
      )
    )
  )
  (setq *degk-last-combined-riser-limits* nil
        *degk-last-combined-riser-entities* nil)
  (setq haveBelowFloor nil
        haveAboveFloor nil)
  (foreach floorAnchor floorLabelAnchors
    (if (and (listp floorAnchor) (numberp (car floorAnchor)))
      (cond
        ((< (car floorAnchor) 0) (setq haveBelowFloor T))
        ((> (car floorAnchor) 0) (setq haveAboveFloor T)))))
  ;; Yalniz bir yonde kat varsa 2-3 loopta da saft dikmeleri olussun.
  ;; Alt ve ust kat birlikteyse ikinci/sondan-bir-onceki kurali korunur.
  (setq oneSidedRiserP
    (or (and haveBelowFloor (not haveAboveFloor))
        (and haveAboveFloor (not haveBelowFloor))))
  (setq riserFallbackMode
    (cond
      ((and haveBelowFloor
            (not haveAboveFloor)
            (= (length loopLeftPoints) 1)
            gfLoopLeftPoints)
        (list 'ONE_SIDE gfLoopLeftPoints))
      (oneSidedRiserP T)
      (T nil)))
  (if (and combinedRiserLayer loopLeftPoints)
    (if (degk--draw-combined-riser
          combinedRiserLayer loopLeftPoints
          riserFallbackMode)
      (princ
        (strcat
          "\nDK: Kolon semasi sol kombine hatti cizildi: "
          combinedRiserLayer))))
  (if (and combinedRiserLayer
           loopDrawRecords
           *degk-last-combined-riser-limits*)
    (setq loopDrawRecords
      (degk--square-outer-loop-records
        loopDrawRecords
        *degk-last-combined-riser-limits*
        T)))
  (setq riserLimits *degk-last-combined-riser-limits*
        riserEntities *degk-last-combined-riser-entities*)
  (setq *degk-last-combined-riser-limits* nil
        *degk-last-combined-riser-entities* nil)
  (if (and combinedRiserLayer gfLoopLeftPoints)
    (if (degk--draw-combined-riser
          combinedRiserLayer gfLoopLeftPoints 'GF)
      (princ
        (strcat
          "\nDK: GF kolon semasi kombine hatti cizildi: "
          combinedRiserLayer))))
  (setq gfRiserEntities *degk-last-combined-riser-entities*)
  (if (and combinedRiserLayer
           gfLoopDrawRecords
           (> (length gfLoopDrawRecords) 1)
           *degk-last-combined-riser-limits*)
    (setq gfLoopDrawRecords
      (degk--square-outer-loop-records
        gfLoopDrawRecords
        *degk-last-combined-riser-limits*
        (/= (length gfLoopDrawRecords) 2))))
  (setq gfRiserLimits *degk-last-combined-riser-limits*)
  ;; Normal looplar tamamlandiktan sonra monitorun kolon kopyasi bellidir.
  ;; Yardimci hatta temas eden karsi blocku monitorun 1000 mm sagina ekle.
  (setq monitorExtraCount
    (degk--place-monitor-linked-blocks monitorLinks))
  (if (not (numberp monitorExtraCount))
    (setq monitorExtraCount 0))
  (if (> monitorExtraCount 0)
    (progn
      (setq totalCopies (+ totalCopies monitorExtraCount))
      (princ
        (strcat "\nDK: Monitor yardimci hattindan eklenen block: "
                (itoa monitorExtraCount)))))
  (princ
    (strcat "\nDK: Alan islemi tamamlandi. Hat grubu: "
            (itoa groupIndex)
            ", toplam kopya: " (itoa totalCopies)))
  (setq usedRows
    (mapcar 'car (if verticalP verticalCounts floorCounts)))
  (setq usedRows
    (vl-sort usedRows (function (lambda (a b) (< a b)))))
  (setq gfFrameLoopCount
    (if verticalP
      (length
        (vl-remove-if-not
          '(lambda (row) (and (numberp (cdr row)) (= (cdr row) 0)))
          verticalFloorRows))
      (if gfRoomAnchorW 1 0)))
  (list groupIndex totalCopies usedRows
        (if verticalP verticalFloorRows nil)
        gfRoomAnchorW
        roomSourceBlocks
        combinedRiserLayer
        gfRiserLimits
        gfLoopDrawRecords
        gfRiserEntities
        gfFloorExtraRows
        gfFrameLoopCount
        layoutRowYs
        floorLabelAnchors
        loopDrawRecords
        riserLimits
        riserEntities)
)

(defun degk--siren-line-span (pts / pt leftX rightX lowY)
  (foreach pt pts
    (if (and (listp pt) (numberp (car pt)) (numberp (cadr pt)))
      (progn
        (if (or (null leftX) (< (car pt) leftX)) (setq leftX (car pt)))
        (if (or (null rightX) (> (car pt) rightX)) (setq rightX (car pt)))
        (if (or (null lowY) (< (cadr pt) lowY)) (setq lowY (cadr pt))))))
  (if lowY (list leftX rightX lowY) nil))

(defun degk--register-siren-underline (modules terminalRec ent pts layer
  / module anchor terminalEnt floorId)
  (progn
      (setq floorId
        (cond
          ((and (boundp '*degk-current-layout-row*) (numberp *degk-current-layout-row*))
            (list 'ROW *degk-current-layout-row*))
          ((and (boundp '*degk-current-layout-floor*) (numberp *degk-current-layout-floor*))
            (list 'FLOOR *degk-current-layout-floor*))))
      (if (and floorId ent)
        (setq *degk-siren-floor-rails*
          (cons (list floorId ent) *degk-siren-floor-rails*)))
      (if modules
        (progn
          (setq module (car modules) anchor (cdr (assoc 10 (entget module))))
          (if anchor
            (setq *degk-siren-underlines*
              (cons (list modules anchor pts layer floorId
                          (if (boundp '*degk-current-layout-floor*) *degk-current-layout-floor* nil))
                    *degk-siren-underlines*)))))
      (if (and terminalRec (car terminalRec))
        (progn
          (setq terminalEnt (vlax-vla-object->ename (car terminalRec)))
          (setq *degk-siren-branches*
            (cons (list terminalEnt ent pts) *degk-siren-branches*))))))

(defun degk--selected-ups-layer (areaSS combinedP / i name primary secondary)
  (setq i 0)
  (if areaSS
    (repeat (sslength areaSS)
      (setq name (cdr (assoc 8 (entget (ssname areaSS i)))) i (1+ i))
      (cond
        ((and name (= (strcase name) (if combinedP "E_UPS_MULTI_LINE" "E_UPS_LINE"))) (setq primary name))
        ((and name (= (strcase name) (if combinedP "E_UPS_LINYE_KOMBINE" "E_UPS_LINYE"))) (setq secondary name)))))
  (if primary primary secondary))

(defun degk--ups-riser-left-x (entities fallback / ent info leftX)
  (foreach ent entities
    (if (setq info (degk--vertical-riser-entity-info ent))
      (setq leftX (if leftX (min leftX (car info)) (car info)))))
  (if leftX leftX fallback))

(defun degk--extend-ups-target (target newX / ent ed vertices endpoint replacement)
  (setq ent (nth 3 target) ed (if ent (entget ent) nil))
  (if (and ed (= (cdr (assoc 0 ed)) "LWPOLYLINE"))
    (progn
      (setq vertices (vl-remove-if-not '(lambda (item) (= (car item) 10)) ed))
      (cond
        ((equal (cdr (car vertices)) (list (cadr target) (caddr target)) 1e-6)
          (setq endpoint (car vertices)))
        ((equal (cdr (last vertices)) (list (cadr target) (caddr target)) 1e-6)
          (setq endpoint (last vertices))))
      (if endpoint
        (progn
          (setq replacement (cons 10 (list newX (caddr target))))
          (if (entmod (subst replacement endpoint ed))
            (progn (entupd ent) T)))))))

(defun degk--fillet-ups-target (target busX radius direction endY / ent ed pts bulges item index firstP lastP tip tangent newPts newBulges data arc)
  (setq ent (nth 3 target) ed (if ent (entget ent) nil) index -1)
  (if (and ed (= (cdr (assoc 0 ed)) "LWPOLYLINE"))
    (progn
      (foreach item ed
        (cond
          ((= (car item) 10)
            (setq pts (append pts (list (cdr item)))
                  bulges (append bulges (list 0.0)) index (1+ index)))
          ((and (= (car item) 42) (>= index 0))
            (setq bulges (append (reverse (cdr (reverse bulges))) (list (cdr item)))))))
      (setq firstP (equal (car pts) (list (cadr target) (caddr target)) 1e-6)
            lastP (equal (last pts) (list (cadr target) (caddr target)) 1e-6)
            tip (list busX (if (numberp endY) endY (+ (caddr target) (* direction radius))))
            arc (if (> radius 1e-9) (* direction 0.414213562373095) 0.0)
            tangent (list (+ busX radius) (caddr target)))
      (cond
        (firstP
          (setq newPts (append (list tip tangent) (cdr pts))
                newBulges (cons arc bulges)))
        (lastP
          (setq newPts (append (reverse (cdr (reverse pts))) (list tangent tip))
                newBulges (append (reverse (cdr (reverse bulges)))
                  (list (- arc) 0.0)))))
      (if newPts
        (progn
          (if (and endY (listp endY) (= (length endY) 3)
                   (numberp (car endY)) (numberp (cadr endY)) (numberp (caddr endY)))
            (progn
              (setq tip (list busX (car endY)) tangent (list (cadr endY) (caddr endY)))
              (if firstP
                (setq newPts (append (list tangent tip) (cdr newPts))
                      newBulges (cons 0.414213562373095 newBulges))
                (setq newPts (append (reverse (cdr (reverse newPts))) (list tip tangent))
                      newBulges (append (reverse (cdr (reverse newBulges)))
                        (list -0.414213562373095 0.0))))))
          (setq data (vl-remove-if '(lambda (p) (member (car p) '(10 40 41 42 91 -3))) ed)
                data (subst (cons 90 (length newPts)) (assoc 90 data) data)
                index 0)
          (foreach item newPts
            (setq data (append data (list (cons 10 item) (cons 42 (nth index newBulges))))
                  index (1+ index)))
          (setq data (append data (vl-remove-if-not '(lambda (p) (= (car p) -3)) ed)))
          (if (entmod data) (progn (entupd ent) T)))))))

(defun degk--ups-cable-caption (cable count / pos)
  (if (and cable (setq pos (vl-string-search "X" (strcase cable))))
    (strcat (itoa count) "(3" (vl-string-right-trim ". " (substr cable (1+ pos))) ")")
    nil))

(defun degk--add-ups-cable-label (top endY / texts cable layer height run offset margin pt rec module modules)
  (setq texts (mapcar 'cdr *degk-ups-cable-texts*))
  ;; Ayni kolon kopyasi birden fazla kayitta yer alsa da bir kez sayilir.
  (foreach rec *degk-siren-underlines*
    (foreach module (car rec)
      (if (and (entget module) (not (member module modules)))
        (setq modules (cons module modules)))))
  (if (> (abs (- endY (cadr top))) 1e-9)
    (progn
      (setq cable (if (= (length texts) 1)
                    (degk--ups-cable-caption (car texts) (length modules)) nil)
            layer "e_loop_adý"
            height (DEG:CFG-DK-NUM-OR 'DK_LOOP_TEXT_HEIGHT 13.0)
            run (DEG:CFG-DK-NUM-OR 'DK_LOOP_LINE_RUN 300.0)
            offset (DEG:CFG-DK-NUM-OR 'DK_LOOP_TEXT_X_OFFSET 15.0)
            margin (DEG:CFG-DK-NUM-OR 'DK_LOOP_TEXT_Y_MARGIN 5.0)
            pt (list (car top) (/ (+ (cadr top) endY) 2.0) (caddr top)))
      (degk--ensure-loop-layer layer)
      (degk--entmake-lwpoly
        (list pt (list (+ (car pt) run) (cadr pt) (caddr pt))) layer nil)
      (degk--add-loop-intersection-mark
        pt (DEG:CFG-DK-NUM-OR 'DK_LOOP_MARK_LENGTH 10.0) layer)
      (degk--add-loop-text
        (list (+ (car pt) offset) (+ (cadr pt) margin) (caddr pt))
        cable layer height)))
  (cond
    ((> (length texts) 1)
      (princ "\nDK: Power supply etiketi: flasor layerinda birden fazla farkli kablo kesiti var."))
    ((null texts)
      (princ "\nDK: Power supply etiketi: flasor layerinda kablo kesiti yazisi bulunamadi."))))

(defun degk--draw-ups-feeds (top targets shaftX gfFireX layer gap verticalP / x y z turnY gf other target sides side busX minY maxY radius twoWay junctionRadius feedEndX direction branchRadius targetY targetX gfUpP extendedP levels topY previousY trimP targetLayer tails cutY contactY riserMaxY)
  (setq x (car top) y (cadr top) z (caddr top)
        turnY (+ y (* 180.0 (DEG:PLAN-UNIT-SCALE))))
  (foreach target targets
    (if (= (car target) 0)
      (setq gf (cons target gf))
      (setq other (cons target other))))
  (setq twoWay (and gf other))
  ;; Dik GF'nin ilk (en alt) UPS satiri, iki yatay kolun ortak seviyesidir.
  (if (and verticalP gf)
    (setq turnY (apply 'min (mapcar 'caddr gf))))
  (if other (setq sides (cons (list -1.0 (- shaftX gap) other) sides)))
  (if gf
    (setq sides
      (cons (list 1.0
        (if (numberp gfFireX)
          (- gfFireX gap)
          (max (+ x gap) (- (apply 'min (mapcar 'cadr gf)) gap))) gf) sides)))
  (if sides
    (progn
      (degk--ensure-layer-editable layer)
      (setq radius (if twoWay (max 0.0 (min gap (- turnY y)
        (apply 'min (mapcar '(lambda (s) (abs (- (cadr s) x))) sides)))) 0.0))
      (degk--entmake-lwpoly
        (list top (list x (- turnY radius) z)) layer 256)
      (degk--add-ups-cable-label top (- turnY radius))
      (foreach side sides
        (setq busX (cadr side) minY turnY maxY turnY)
        (foreach target (caddr side)
          (setq minY (min minY (caddr target)) maxY (max maxY (caddr target))))
        (setq gfUpP (and verticalP (> (car side) 0.0)
                           (equal minY turnY 1e-9) (> maxY turnY))
              junctionRadius
          (max 0.0 (min gap (if gfUpP gap (- turnY minY)) (- maxY turnY)
            (max 0.0 (- (abs (- busX x)) radius))))
              feedEndX (- busX (* (car side) junctionRadius)))
        (setq levels (vl-sort (mapcar 'caddr (caddr side)) '> )
              topY (car levels) previousY (cadr levels)
              trimP (and previousY (> topY turnY) (>= previousY turnY))
              tails nil cutY nil riserMaxY maxY)
        (foreach target (caddr side)
          (if (equal (caddr target) topY 1e-9)
            (progn
              (setq targetLayer (cdr (assoc 8 (entget (nth 3 target)))))
              (if (or (null targetLayer)
                      (member (strcase targetLayer) '("E_UPS_MULTI_LINE" "E_UPS_LINYE_KOMBINE")))
                (setq trimP nil)))))
        (if (> radius 1e-9)
          (degk--entmake-lwpoly-bulges
            (list (list x (- turnY radius) z)
                  (list (+ x (* (car side) radius)) turnY z)
                  (list feedEndX turnY z))
            (list (* -0.414213562373095 (car side)) 0.0 0.0) layer 256)
          (degk--entmake-lwpoly
            (list (list x turnY z) (list feedEndX turnY z)) layer 256))
        ;; Iki yone devam eden kolonun girisinde ust ve alt yay ayri olusur.
        (if (and (> junctionRadius 1e-9) (not gfUpP))
          (foreach direction (if gfUpP '(1.0) '(-1.0 1.0))
            (degk--entmake-lwpoly-bulges
              (list (list feedEndX turnY z)
                    (list busX (+ turnY (* direction junctionRadius)) z))
              (list (* (car side) direction 0.414213562373095) 0.0) layer 256)))
        (foreach target (caddr side)
          (setq targetX (cadr target) targetY (caddr target)
                direction (if (> targetY turnY) -1.0 1.0)
                branchRadius
                  (if (or (equal targetY minY 1e-9) (equal targetY maxY 1e-9)
                          (equal targetY turnY 1e-9))
                    0.0
                    (max 0.0 (min gap (- targetX busX) (abs (- targetY turnY))))))
          (if (and trimP (equal targetY topY 1e-9))
            (setq tails (cons target tails) extendedP T)
            (progn
          (setq extendedP
            (if (> branchRadius 1e-9)
              (degk--fillet-ups-target target busX branchRadius direction nil)
              (degk--extend-ups-target target
                (if (equal targetY turnY 1e-9) feedEndX busX))))
          (if (and trimP extendedP (equal targetY previousY 1e-9))
            (progn
              (setq contactY (if (equal targetY turnY 1e-9)
                               (+ turnY junctionRadius)
                               (+ targetY (* direction branchRadius))))
              (setq cutY (if cutY (max cutY contactY) contactY))))))
          (if (not extendedP)
            (princ "\nDK: UPS yatay uc birlesimi uygulanamadi.")))
        (if tails
          (progn
            (setq extendedP T)
            (foreach target tails
              (if (not (if (numberp cutY)
                         (degk--fillet-ups-target target busX 0.0 -1.0
                           (if (and gfUpP (> junctionRadius 1e-9)
                                    (equal cutY (+ turnY junctionRadius) 1e-9))
                             (list cutY feedEndX turnY) cutY))
                         (degk--extend-ups-target target busX)))
                (setq extendedP nil)))
            (if (and extendedP (numberp cutY)) (setq riserMaxY cutY))))
        (if (> junctionRadius 1e-9)
          (progn
            (if (> (- turnY junctionRadius minY) 1e-9)
              (degk--entmake-lwpoly
                (list (list busX minY z) (list busX (- turnY junctionRadius) z)) layer 256))
            (if (> (- riserMaxY turnY junctionRadius) 1e-9)
              (if gfUpP
                (degk--entmake-lwpoly-bulges
                  (list (list feedEndX turnY z)
                        (list busX (+ turnY junctionRadius) z) (list busX riserMaxY z))
                  '(0.414213562373095 0.0 0.0) layer 256)
                (degk--entmake-lwpoly
                  (list (list busX (+ turnY junctionRadius) z) (list busX riserMaxY z)) layer 256))))
          (if (> (- riserMaxY minY) 1e-9)
            (degk--entmake-lwpoly
              (list (list busX minY z) (list busX riserMaxY z)) layer 256)))))))

(defun degk--draw-room-ups-feeds (targets layer gap / obj ent bb mn mx)
  (if (and targets layer (boundp '*degk-ups-source*) *degk-ups-source*)
    (progn
      (setq obj (car *degk-ups-source*)
            ent (vlax-vla-object->ename obj)
            bb (degk--column-frame-block-visible-bbox ent))
      (if (null bb) (setq bb (degk--ent-bbox obj)))
      (if bb
        (progn
          (setq mn (car bb) mx (cadr bb))
          (degk--draw-ups-feeds
            (list (/ (+ (car mn) (car mx)) 2.0) (cadr mx) (if (caddr mx) (caddr mx) 0.0))
            targets (cadr *degk-ups-source*) (nth 2 *degk-ups-source*) layer gap
            (nth 3 *degk-ups-source*)))))))

(defun degk--draw-siren-underlines (areaSS / rec modules anchor current dy pts span branch
  branchPts item ed branchSpan xMin xMax lowY gap layer z module base dropX drops lastDrop joinX floorRail floorLevels floorSpan floorId floorLevel dropRadius upsLayer upsCombinedLayer feedTargets feedTarget feedEnt)
  ;; Son GF hizalamalarindan sonra ciz: satirlarin tasinmasi hesaba katilir.
  (setq gap (abs (DEG:CFG-DK-NUM-OR 'DK_UNDER_X2 10.0))
        upsLayer (degk--selected-ups-layer areaSS nil)
        upsCombinedLayer (degk--selected-ups-layer areaSS T))
  (if (<= gap 1e-9) (setq gap (* 10.0 (DEG:PLAN-UNIT-SCALE))))
  ;; Yatayda kat, dikte paketlenmis satir: SM olmayan looplar da hesaba katilir.
  (foreach floorRail *degk-siren-floor-rails*
    (setq pts nil)
    (foreach item (entget (cadr floorRail))
      (if (= (car item) 10) (setq pts (cons (cdr item) pts))))
    (if (setq floorSpan (degk--siren-line-span pts))
      (progn
        (setq floorId (car floorRail) floorLevel (assoc floorId floorLevels))
        (if floorLevel
          (setq floorLevels (subst (cons floorId (min (cdr floorLevel) (caddr floorSpan))) floorLevel floorLevels))
          (setq floorLevels (cons (cons floorId (caddr floorSpan)) floorLevels))))))
  (foreach rec *degk-siren-underlines*
    (setq modules (car rec) anchor (cadr rec)
          current (cdr (assoc 10 (entget (car modules)))))
    (if current
      (progn
        (setq dy (- (cadr current) (cadr anchor))
              pts (degk--shift-point-list-y (nth 2 rec) dy)
              span (degk--siren-line-span pts)
              xMin (car span) xMax (cadr span) lowY (caddr span)
              layer (if upsLayer upsLayer (nth 3 rec)) z (if (caddr current) (caddr current) 0.0))
        (foreach branch *degk-siren-branches*
          (if (member (car branch) modules)
            (progn
              (setq ed (entget (cadr branch)) branchPts nil)
              (if ed
                (foreach item ed
                  (if (= (car item) 10) (setq branchPts (cons (cdr item) branchPts))))
                (setq branchPts (degk--shift-point-list-y (nth 2 branch) dy)))
              (setq branchSpan (degk--siren-line-span branchPts))
              (if branchSpan
                (setq xMin (min xMin (car branchSpan))
                      xMax (max xMax (cadr branchSpan))
                      lowY (min lowY (caddr branchSpan)))))))
        (if (setq floorLevel (assoc (nth 4 rec) floorLevels))
          (setq lowY (cdr floorLevel)))
        (setq drops nil xMax nil)
        (foreach module modules
          (setq base (cdr (assoc 10 (entget module))))
          (if base
            (progn
              (setq dropX (- (car base) gap)
                    xMin (min xMin dropX)
                    xMax (if xMax (max xMax dropX) dropX))
              (if (not (member (list dropX (cadr base)) drops))
                (setq drops (cons (list dropX (cadr base)) drops))))))
        (if (and span xMax (> xMax xMin))
          (progn
            (degk--ensure-layer-editable layer)
            (setq drops (vl-sort drops '(lambda (a b) (> (car a) (car b))))
                  lastDrop (car drops)
                  joinX xMin)
            (if (cdr drops)
              (progn
                (setq base (cadr drops)
                      dropRadius (max 0.0 (min gap (- (cadr base) lowY) (- (car base) xMin)))
                      joinX (- (car base) dropRadius))))
            ;; Son dik ve yatay donusu tek polyline olarak birlestir.
            (degk--entmake-lwpoly
              (list (list (car lastDrop) (cadr lastDrop) z)
                    (list (car lastDrop) lowY z)
                    (list joinX lowY z))
              layer 256)
            (setq feedEnt (entlast))
            (if (> joinX xMin)
              (progn
                (degk--ensure-layer-editable (if upsCombinedLayer upsCombinedLayer layer))
                (degk--entmake-lwpoly
                  (list (list xMin lowY z) (list joinX lowY z))
                  (if upsCombinedLayer upsCombinedLayer layer) 256)
                (setq feedEnt (entlast))))
            (if (numberp (nth 5 rec))
              (setq feedTargets
                (cons (list (nth 5 rec) xMin lowY feedEnt) feedTargets)))
            (foreach base (cdr drops)
              (setq dropRadius
                (max 0.0 (min gap (- (cadr base) lowY) (- (car base) xMin))))
              (if (> dropRadius 1e-9)
                (degk--entmake-lwpoly-bulges
                  (list (list (car base) (cadr base) z)
                        (list (car base) (+ lowY dropRadius) z)
                        (list (- (car base) dropRadius) lowY z))
                  '(0.0 -0.414213562373095 0.0) layer 256)
                (degk--entmake-lwpoly
                  (list (list (car base) (cadr base) z)
                        (list (car base) lowY z))
                  layer 256))))))))
  (degk--draw-room-ups-feeds feedTargets (if upsCombinedLayer upsCombinedLayer upsLayer) gap))

(defun DK:BASE
  (/ tol sel ent plEnt loopEnts plStart plEnd pickPt useFromStart
     ss i e blkObj touched ordered totalLen ins pair dist key
     basePt baseU tmp
     sira siraList idx copyObj fromPt
     curTargetU baseW dY
     siraOne
     plLayer plColor
     allPts thisPts lastPt eps groupBounds loopLeftPoints loopRawPts loopFilletData loopBulges loopEndDirection loopDrawBefore loopDrawEnt loopDrawRes
      txtLayer blkInsBefore dkkState loopText loopDrop railLeftX labelPts
      terminalModule terminalCandidates terminalRec terminalAnchor terminalClearance terminalLinkY moduleRec copyLayoutInfo copyFloor sirenCopies)

  (vl-load-com)
  (setq *degk-last-copy-count* 0
        *degk-last-group-min-x* nil
        *degk-last-group-max-x* nil
        *degk-last-loop-left-points* nil
        *degk-last-loop-draw-record* nil)
   (setq tol (DEG:CFG-TOL-NUM-OR 'DN_BLOCK_TOL 1.0))
   (setq eps 1e-6)
   (setq loopDrop
     (if (and (boundp '*degk-dispatch-loop-drop*)
              (numberp *degk-dispatch-loop-drop*)
              (> *degk-dispatch-loop-drop* 0.0))
       *degk-dispatch-loop-drop*
       0.0))
   (setq railLeftX
     (if (and (boundp '*degk-dispatch-rail-left-x*)
              (numberp *degk-dispatch-rail-left-x*))
       *degk-dispatch-rail-left-x*
       nil))
  (setq txtLayer (DEG:VAL 'O1))
  (degk--ensure-layer-editable txtLayer)
  (degk--ensure-layer-editable (DEG:VAL 'O2))

  (setq *degk-attsync-names* nil)

  (if (and (boundp '*degk-dispatch-sel*) *degk-dispatch-sel*)
    (progn (setq sel *degk-dispatch-sel*) (setq *degk-dispatch-sel* nil))
    (setq sel (entsel "\nDK: Polyline seç: ")))
  (if (null sel)
    (progn (princ "\n\nDEGK iptal.") (princ))
    (progn
      (setq ent (car sel))
      (setq pickPt (cadr sel))
      (setq plEnt ent)
      (setq loopEnts
        (if (and (boundp '*degk-dispatch-loop-ents*)
                 *degk-dispatch-loop-ents*)
          *degk-dispatch-loop-ents*
          (list plEnt)))

      (if (not (degk--curve-ok? plEnt))
        (progn (princ "\n\nSeçilen nesne curve deðil (Polyline/LWPolyline seçmelisin).") (princ))
        (progn
          (setq plLayer (cdr (assoc 8 (entget plEnt))))
          (setq plColor (degk--color-dxfs-from-entity plEnt plLayer))
          (if (and plLayer (/= (strcase plLayer) "0"))
            (degk--ensure-layer-editable plLayer)
          )

          (setq plStart (vlax-curve-getStartPoint plEnt))
          (setq plEnd   (vlax-curve-getEndPoint   plEnt))

          (setq totalLen (vlax-curve-getDistAtParam plEnt (vlax-curve-getEndParam plEnt)))
(if (and (boundp '*degk-dispatch-base*) *degk-dispatch-base*)
  (progn
    (setq basePt *degk-dispatch-base*
          *degk-dispatch-base* nil)
  )
  (progn
    (setq tmp (vl-catch-all-apply 'getpoint
                                  (list "\nDK: Kopyalarin yerlesecegi baslangic noktasini sec: ")))
    (setq basePt (if (vl-catch-all-error-p tmp) nil tmp))
  )
)
(if (null basePt)
            (progn (princ "\n\nDEGK iptal.") (princ))
            (progn
              (setq baseU (trans basePt 0 1))

              (setq ss
                (if (and (boundp '*degk-dispatch-loop-ents*) *degk-dispatch-loop-ents*
                         (boundp '*degk-source-insert-snapshot*) *degk-source-insert-snapshot*)
                  *degk-source-insert-snapshot*
                  (ssget "_X" '((0 . "INSERT")))))
              (setq touched '()
                    terminalCandidates '())
              (if ss
                (progn
                  (setq i 0)
                  (while (< i (sslength ss))
                    (setq e (ssname ss i))
                    (setq blkObj (vlax-ename->vla-object e))
                    (if (degk--source-block-eligible-p blkObj)
                      (progn
                        (if (degk--block-touches-loop-p loopEnts blkObj tol)
                          (progn
                            (setq touched (cons blkObj touched))
                            (degk--attsync-add blkObj)))
                        (if (and (degk--flasher-loop-layer-p plLayer)
                                 (degk--flasher-terminal-module-p blkObj)
                                 (degk--flasher-terminal-touches-loop-p
                                   loopEnts blkObj tol))
                          (setq terminalCandidates
                            (cons blkObj terminalCandidates)))
                      )
                    )
                    (setq i (1+ i))
                  )
                )
              )

              ;; Flasor/strobe hattinin temas ettigi kontrol modulunu, daha once
              ;; ana loopta yapistirilan kopyasiyla eslestir. Eslesme varsa modul
              ;; bu loopta tekrar kopyalanmaz. Loop sagdaki son loop hizasinda
              ;; kalir; modulden loopa ayri bir dik/ortogonal baglanti eklenir.
              (if (degk--flasher-loop-layer-p plLayer)
                (progn
                  (setq terminalModule
                    (cond
                      ((and (boundp '*degk-dispatch-terminal-source*)
                            *degk-dispatch-terminal-source*
                            (= (type *degk-dispatch-terminal-source*) 'VLA-OBJECT))
                        *degk-dispatch-terminal-source*)
                      (terminalCandidates
                        (degk--flasher-terminal-from-touched
                          plEnt terminalCandidates tol))
                      (T nil))
                    terminalRec
                      (cond
                        ((and (boundp '*degk-dispatch-terminal-copy-rec*)
                              *degk-dispatch-terminal-copy-rec*)
                          *degk-dispatch-terminal-copy-rec*)
                        (terminalModule
                          (degk--area-module-copy-get
                            terminalModule
                            (if (and (boundp '*degk-current-layout-floor*)
                                     (numberp *degk-current-layout-floor*))
                              *degk-current-layout-floor*
                              nil)))
                        (T nil))
                    terminalAnchor
                      (if (and terminalRec (cadr terminalRec))
                        (cadr terminalRec)
                        nil))
                  (if terminalModule
                    (if terminalAnchor
                      (princ
                        (strcat
                          "\nDK: Flasor kontrol modulu ve kolon kopyasi eslesti: "
                          (if (degk--blockname terminalModule)
                            (degk--blockname terminalModule)
                            "<MODULE>")))
                      (princ
                        (strcat
                          "\nDK: Flasor kontrol modulu bulundu; kolon kopyasi bulunamadi: "
                          (if (degk--blockname terminalModule)
                            (degk--blockname terminalModule)
                            "<MODULE>"))))
                  )
                  (if terminalAnchor
                    (progn
                      (setq
                        ;; 100 mm = 10 cm. PLAN birimine gore olceklenir.
                        terminalClearance
                          (* 10.0 (DEG:PLAN-UNIT-SCALE))
                        railLeftX nil)
                    )
                  )
                )
              )

              ;; Kontrol modulleri flasor hattinin terminal hedefidir; loop
              ;; cihazlari degildir. Alan temasi veya base temasi nasil
              ;; bulunursa bulunsun hicbiri kopya cihaz listesinde kalmaz.
              (if (degk--flasher-loop-layer-p plLayer)
                (setq touched
                  (vl-remove-if 'degk--flasher-terminal-module-p touched)))

              (if (null touched)
                (progn (princ "\n\nDK: ayarlanan temas toleransi icinde polyline’a degen blok yok.") (princ))
                (progn
      (setq totalLen (vlax-curve-getDistAtParam plEnt (vlax-curve-getEndParam plEnt)))
      (setq useFromStart (degk--use-from-lower-sira-side plEnt touched totalLen))
      (setq ordered '())
      (foreach blkObj touched
        (setq ins  (deg-get-inspt blkObj))
        (setq dist (degk--dist-along plEnt ins))
        (setq key
          (if (> (length loopEnts) 1)
            (degk--block-loop-order-key blkObj loopEnts)
            (if useFromStart dist (- totalLen dist))))
        (setq ordered (cons (cons key blkObj) ordered))
      )
      (setq ordered (vl-sort ordered '(lambda (a b) (< (car a) (car b)))))
      (if (and (degk--flasher-loop-layer-p plLayer)
               (null terminalAnchor))
        (setq ordered (degk--flasher-module-last ordered))
      )

      (setq idx 0)
      (setq allPts '())
      (setq lastPt nil)
      (setq loopText nil)

      (foreach pair ordered
        (setq blkObj (cdr pair))
        (setq sira (degk--get-att blkObj "SIRA_NO"))
        (setq siraList (degk--expand-sira-no sira))
        (if (or (null siraList) (= (length siraList) 0))
          (setq siraList (list sira))
        )
        (setq siraList (degk--limit-sira-list siraList))

        (foreach siraOne siraList
          (setq siraOne (degk--clean-text siraOne))
          (setq copyLayoutInfo (degk--layout-key-from-sira siraOne)
                copyFloor
                  (if copyLayoutInfo
                    (car copyLayoutInfo)
                    (if (and (boundp '*degk-current-layout-floor*)
                             (numberp *degk-current-layout-floor*))
                      *degk-current-layout-floor*
                      nil)))
          (if (and (or (null loopText) (= loopText "")) (/= siraOne ""))
            (setq loopText (degk--loop-name-from-sira siraOne))
          )
          (setq dkkState
            (if (degkk--active-p)
              (degkk--normal-occurrence-state blkObj siraOne)
              'NEW))

          ;; DKK ayni modul sembolunu tek kopyada topladiginda, bu kaynak
          ;; modulun handle'ini da temsilci kopyanin temas noktasina bagla.
          (if (and (eq dkkState 'DUPLICATE)
                   (not (degk--flasher-loop-layer-p plLayer))
                   (degk--column-anchor-module-p blkObj)
                   (setq moduleRec
                     (degk--area-module-symbol-get
                       blkObj
                       (if (and (boundp '*degk-current-layout-floor*)
                                (numberp *degk-current-layout-floor*))
                         *degk-current-layout-floor*
                         copyFloor))))
            (degk--area-module-copy-put
              blkObj
              (car moduleRec)
              (cadr moduleRec)
              (nth 2 moduleRec)
              (nth 3 moduleRec))
          )

          (if (and (eq dkkState 'NEW)
                   (not (DEG:IGNORE-BLOCK-OBJ? blkObj)))
            (progn
              (setq curTargetU (list (+ (car baseU) (* idx (DEG:CFG-DK-NUM-OR 'DK_COPY_SPACING 100.0))) (cadr baseU) 0.0))
              (setq baseW (trans curTargetU 1 0))
              (if (degk--copy-dk-block-safe blkObj baseW siraOne)
                (progn
                  (if (and (not (degk--flasher-loop-layer-p plLayer))
                           (or (degk--flasher-terminal-module-p blkObj)
                               (degk--flasher-terminal-module-p *DEG_DK_LAST_COPY_OBJ*)))
                    (setq sirenCopies
                      (cons (vlax-vla-object->ename *DEG_DK_LAST_COPY_OBJ*) sirenCopies)))
                  (if (degkk--active-p)
                    (degkk--register-normal-copy blkObj *DEG_DK_LAST_COPY_OBJ*)
                  )
                  (if (and
                        (not (degk--flasher-loop-layer-p plLayer))
                        ;; Dinamik/anonim kaynak adi bazi cizimlerde terminal
                        ;; filtresinden kacabiliyor. Kopyanin gercek adi terminal
                        ;; ise yine kolon terminal haritasina mutlaka kaydet.
                        (or (degk--column-anchor-module-p blkObj)
                            (and *DEG_DK_LAST_COPY_OBJ*
                                 (= (type *DEG_DK_LAST_COPY_OBJ*) 'VLA-OBJECT)
                                 (degk--column-anchor-module-p
                                   *DEG_DK_LAST_COPY_OBJ*))))
                    (degk--area-module-copy-put
                      blkObj
                      *DEG_DK_LAST_COPY_OBJ*
                      (degk--under-top-pt baseW)
                      (if (and (boundp '*degk-current-layout-row*)
                               (numberp *degk-current-layout-row*))
                        *degk-current-layout-row*
                        nil)
                      ;; Modulun kolon semasindaki gercek kati, kendi eksik
                      ;; veya hatali SIRA_NO'su degil islenen normal loopun katidir.
                      (if (and (boundp '*degk-current-layout-floor*)
                               (numberp *degk-current-layout-floor*))
                        *degk-current-layout-floor*
                        copyFloor))
                  )
                  (setq thisPts
                    (degk--drop-under-rail-pts
                      (degk--under-pts
                        baseW
                        (DEG:CFG-DK-NUM-OR 'DK_UNDER_X1 10.0)
                        (DEG:CFG-DK-NUM-OR 'DK_UNDER_X2 10.0)
                        (DEG:CFG-DK-NUM-OR 'DK_UNDER_W 70.0)
                        (DEG:CFG-DK-NUM-OR 'DK_UNDER_H 60.0))
                      loopDrop))

                  (if (null allPts)
                    (setq allPts thisPts)
                    (progn
                      (if (degk--pt-eq? lastPt (car thisPts) eps)
                        (setq allPts (append allPts (cdr thisPts)))
                        (setq allPts (append allPts thisPts))
                      )
                    )
                  )
                  (setq lastPt (car (last thisPts)))
                  (setq idx (1+ idx))
                  ;; Bu monitorun sagina yardimci hattan bulunan ek cihaz
                  ;; sonradan yerlestirilecek. Sonraki normal blocku bir yuva
                  ;; daha saga al: monitor -> ek cihaz 1000 mm, monitor ->
                  ;; sonraki normal block 2000 mm; devam edenler yine 1000 mm.
                  (if (and
                        (boundp '*degk-monitor-linked-source-handles*)
                        *degk-monitor-linked-source-handles*
                        (degk--monitor-module-p blkObj)
                        (member
                          (strcase (degkk--object-handle blkObj))
                          *degk-monitor-linked-source-handles*))
                    (setq idx (1+ idx)))
                )
              )
            )
          )
        )
      )

      (setq loopText (or (degk--source-loop-title loopEnts) loopText))
      (if (and allPts (> (length allPts) 1) (deg-layerE-str-p plLayer) (/= (strcase plLayer) "0"))
        (progn
          (if (degk--flasher-loop-layer-p plLayer)
            (progn
              ;; Baslik eski kapali geometrinin baslangicinda kalir; cizilecek
              ;; ozel loop ise son blok temasinda acik olarak biter.
              (setq labelPts
                (degk--close-under-pts
                  allPts
                  (DEG:CFG-DK-NUM-OR 'DK_UNDER_X2 10.0)))
              (degk--add-loop-label labelPts loopText T (degk--source-cable-text loopEnts loopText))
              (setq allPts (degk--trim-at-last-block-contact allPts))
            )
            (progn
              (setq allPts
                (degk--close-under-pts
                  allPts
                  (DEG:CFG-DK-NUM-OR 'DK_UNDER_X2 10.0)))
              ;; Etiket kendi loopunun mevcut baslangicinda kalir.
              (degk--add-loop-label allPts loopText nil (degk--source-cable-text loopEnts loopText))
              (if railLeftX
                (setq allPts (degk--extend-under-rails-left allPts railLeftX))
              )
            )
          )
          (if terminalAnchor
            (progn
              (setq terminalLinkY (degk--pts-min-y allPts))
              (if (numberp terminalLinkY)
                (progn
                  (setq terminalLinkY (- terminalLinkY terminalClearance)
                        allPts
                          (degk--move-lowest-rail-to-y
                            allPts
                            terminalLinkY)
                        allPts
                          (degk--prepend-flasher-module-link
                            allPts
                            terminalAnchor
                            terminalLinkY))
                )
              )
            )
          )
          ;; GF altindaki bodrum katlarinda fillet uclari yukari; GF ve
          ;; ustundeki katlarda asagi bakar. Yay yaricapi Sag Ofset degeridir.
          (setq loopRawPts allPts
                loopEndDirection
            (if (and (boundp '*degk-current-layout-floor*)
                     (numberp *degk-current-layout-floor*)
                     (< *degk-current-layout-floor* 0.0))
              1.0
              -1.0)
            loopFilletData
              (degk--loop-left-fillet-data
                allPts
                (DEG:CFG-DK-NUM-OR 'DK_UNDER_X2 10.0)
                loopEndDirection))
          (if loopFilletData
            (setq allPts     (car loopFilletData)
                  loopBulges (cadr loopFilletData)))
          (setq groupBounds (degk--pts-x-bounds allPts))
          (if groupBounds
            (setq *degk-last-group-min-x*
                    (if (and loopFilletData
                             (numberp (nth 3 loopFilletData)))
                      (nth 3 loopFilletData)
                      (car groupBounds))
                  *degk-last-group-max-x* (cadr groupBounds)
                  loopLeftPoints
                    (if (and loopFilletData (nth 2 loopFilletData))
                      (nth 2 loopFilletData)
                      (degk--pts-at-x allPts (car groupBounds) 1e-6))
                  *degk-last-loop-left-points* loopLeftPoints)
          )
          (setq loopDrawBefore (entlast)
                loopDrawRes
                  (if loopBulges
                    (degk--entmake-lwpoly-bulges allPts loopBulges plLayer plColor)
                    (degk--entmake-lwpoly allPts plLayer plColor))
                loopDrawEnt (entlast))
          (if (and loopDrawRes loopDrawEnt (not (eq loopDrawBefore loopDrawEnt)))
            (degk--register-siren-underline
              sirenCopies terminalRec loopDrawEnt loopRawPts plLayer))
          (if (and loopFilletData
                   loopDrawRes
                   loopDrawEnt
                   (not (eq loopDrawBefore loopDrawEnt)))
            (setq *degk-last-loop-draw-record*
              (list loopDrawEnt allPts loopBulges plLayer plColor
                    loopRawPts loopEndDirection)))
        )
      )

      (degk--attsync-run)
      (setq *degk-last-copy-count* idx)
      (princ (strcat "\nDK: Yerleþtirilen toplam kopya: " (itoa idx)))
    )
  )
  (princ)
)



)
)
)
)
)
)
(defun degk--area-select-with-layout (/ layoutMode input areaSS)
  ;; Yon secimi alan seciminden ayridir ve zorunludur. Secilen yonden sonra
  ;; her iki mod da standart AutoCAD secim kumesini kullanir.
  (initget 1 "Dik Yatay")
  (setq input (getkword "\nDK: Kolon semasi yonunu sec [Dik/Yatay]: "))
  (if input
    (progn
      (setq layoutMode (if (= input "Dik") 'DIK 'YATAY))
      (princ "\nDK: Alani normal secimle secin; Space/Enter ile bitirin:")
      (setq areaSS (ssget '((0 . "LWPOLYLINE,POLYLINE,INSERT"))))))
  (if areaSS (list areaSS layoutMode) nil)
)

(defun DK_ORIG (/ *degk-source-cache-active* *degk-terminal-type-cache* *degk-source-eligible-cache* *degk-number-mode* *degk-title-index* *degk-title-index-ready* *degk-title-cache* *degk-loop-bounds-cache* *degk-number-warning* *degk-cable-index* *degk-panel-loop-count* *degk-siren-underlines* *degk-siren-branches* *degk-siren-floor-rails* *degk-ups-source* sel ent pickPt plObj layU ucsTmp res msg oldTS areaSS normalPolys basePt selectionRes layoutMode frameStart processResult *DS-LAYER-STATES* *degk-last-panel-name* *degk-area-module-copy-map* *degk-area-module-symbol-map* *degk-column-terminal-copies* *degk-flasher-contact-bbox-cache* *degk-dispatch-terminal-copy-rec*)
  (setq *degk-source-cache-active* T)
  (vl-load-com)

  (setq *degk-perf-active* T *degk-perf-data* nil *degk-perf-stack* nil
        *degk-perf-selected* 0 *degk-perf-texts* 0 *degk-perf-leaders* 0 *degk-perf-touches* 0)
  ;; DK, kopyalama sirasinda kaynak/nested obje layerlarini gecici olarak
  ;; acip thaw/unlock eder. Komut nasil biterse bitsin mevcut layer durumlari korunur.
  (setq *DS-LAYER-STATES* nil)
  (DS--snapshot-all-layer-states)

  ;; DK yazýlarý için TEXTSTYLE -> STANDARD
  (setq oldTS (getvar "TEXTSTYLE"))
  (degk--ensure-textstyle "STANDARD" "arial.ttf")
  (setvar "TEXTSTYLE" "STANDARD")


  ;; DK en baþýnda UCS -> World (WCS), iþlem bitince eski UCS'ye don.
  (setq ucsTmp "DEG_DK_UCS_TMP")
  (vl-catch-all-apply 'vl-cmdf (list "_.UCS" "_D" ucsTmp))
  (vl-cmdf "_.UCS" "_S" ucsTmp)
  (vl-cmdf "_.UCS" "_W")

  (setq res
    (vl-catch-all-apply
      (function
        (lambda ()
          (deg-reset-session)
          (deg-clear-deg-done-xdata)
          (setq *degk-last-panel-name* (degk--select-last-panel-name)
                selectionRes (degk--area-select-with-layout)
                areaSS      (if selectionRes (car selectionRes) nil)
                layoutMode  (if selectionRes (cadr selectionRes) 'YATAY))
          (if (not areaSS)
            (progn (princ "\n\nDEGK iptal.") nil)
            (progn
              (setq *degk-perf-selected* (sslength areaSS))
              (setq *degk-number-mode*
                (degk--perf-call "Alan numara modu" 'degk--area-number-mode (list areaSS)))
              (setq normalPolys (degk--perf-call "Secili normal hat taramasi" 'degk--normal-area-polylines (list areaSS))
                    *degk-cable-index* (degk--cable-source-index areaSS))
              (if (and (= (sslength areaSS) 1)
                       (= (sslength normalPolys) 0)
                       (member (cdr (assoc 0 (entget (ssname areaSS 0))))
                               '("LWPOLYLINE" "POLYLINE")))
                (progn
                  (setq ent (degk--as-ename (ssname areaSS 0)))
                  (if ent
                    (progn
                      (setq pickPt (vl-catch-all-apply 'vlax-curve-getStartPoint (list ent)))
                      (if (vl-catch-all-error-p pickPt)
                        (setq pickPt (cdr (assoc 10 (entget ent)))))
                      (setq plObj (vlax-ename->vla-object ent)
                            layU (strcase (vla-get-Layer plObj))
                            *degk-dispatch-sel* (list ent pickPt))
                      (cond
                        ((DEGK--data-layer-name-p layU) (DEGV:RUN))
                        ((DEGQ:_cctv-layer-name-p layU) (DEGQ:RUN))
                        (T
                          (setq *degk-dispatch-sel* nil)
                          (princ
                            (strcat "\nDK: Secilen polyline normal alan layer listesinde degil: "
                                    (vla-get-Layer plObj))))
                      )
                    )
                  )
                )
                (progn
                  (if (= (sslength normalPolys) 0)
                    (princ "\nDK: Alanda ayar listesindeki normal hat polylinesi bulunamadi.")
                    (progn
                      (setq basePt (getpoint "\nDK: Ilk hat grubunun yapistirma noktasini sec: "))
                      (if basePt
                        (progn
                          (setq frameStart (entlast)
                                processResult
                                  (degk--perf-call "Ana loop cizimi (yerlesim ve kablo dahil)" 'degk--normal-area-process
                                    (list areaSS basePt layoutMode)))
                          (degk--maybe-draw-column-frame
                            frameStart basePt processResult)
                          (degk--perf-call "Siren-UPS cizimi" 'degk--draw-siren-underlines (list areaSS)))
                        (princ "\nDEGK iptal."))
                    )
                  )
                )
              )
            )
          )
          nil
        )
      )
      '()
    )
  )

  (setq *degk-dispatch-sel* nil
        *degk-dispatch-base* nil)

  ;; UCS restore (iptal dahil)
  (vl-catch-all-apply 'vl-cmdf (list "_.UCS" "_R" ucsTmp))
  (vl-catch-all-apply 'vl-cmdf (list "_.UCS" "_D" ucsTmp))


  ;; TEXTSTYLE restore (iptal dahil)
  (if oldTS (setvar "TEXTSTYLE" oldTS))
  (DS--restore-layer-states)
  (degk--perf-report)
  (if (vl-catch-all-error-p res)
    (progn
      (setq msg (vl-catch-all-error-message res))
      (if (and msg (/= msg "Function cancelled"))
        (princ (strcat "\n; error: " msg))
      )
    )
  )
  (princ)
)


;; ============================================================
;; KC cihaz kodu lisansi
;; - Ilk kullanimda rastgele bir cihaz kodu uretilir ve Windows DPAPI ile bu PC'ye baglanir.
;; - GitHub'da yalnizca bu cihaza ait kc/izinler/<KOD>.lic dosyasi sorgulanir.
;; - Tam izin listesi, bypass sifresi veya bypass dogrulayicisi diske indirilmez.
;; - Basarili cihaz izni 24 saatlik DPAPI sifreli yerel grant olarak saklanir.
;; - Basarili bypass izni yalnizca mevcut Windows acilisi boyunca gecerlidir.
;; ============================================================

(setq *KC_LICENSE_MARKER_BASE_URL* "https://raw.githubusercontent.com/cakirkaancc-ship-it/kc-allowlist/refs/heads/main/kc/izinler")
(setq *KC_BYPASS_VERIFIER_URL* "https://raw.githubusercontent.com/cakirkaancc-ship-it/kc-allowlist/refs/heads/main/kc/BYPASS%20S%C4%B0FRES%C4%B0")
(setq *KC_ALLOW_CACHE_DAYS* 1.0)
(setq *KC_UPDATE_COMMIT_API_URL* "https://api.github.com/repos/cakirkaancc-ship-it/kc-allowlist/commits?path=kc/guncelleme&sha=main&per_page=1")
(setq *KC_UPDATE_CONTENTS_API_URL* "https://api.github.com/repos/cakirkaancc-ship-it/kc-allowlist/contents/kc/guncelleme")
(setq *KC_UPDATE_RAW_BASE_URL* "https://raw.githubusercontent.com/cakirkaancc-ship-it/kc-allowlist/refs/heads/main/kc/guncelleme")

(defun KC:Trim (s) (if s (vl-string-trim " \t\r\n" s) ""))

(defun KC:ProgramDataDir (/ pd)
  (setq pd (getenv "ProgramData"))
  (if (or (null pd) (= (KC:Trim pd) "")) (setq pd "C:\\ProgramData"))
  pd
)

(defun KC:EnsureDir (dir)
  (if (and dir (not (vl-file-directory-p dir))) (vl-mkdir dir))
  dir
)

(defun KC:BaseDir ()
  (KC:EnsureDir (strcat (KC:ProgramDataDir) "\\KC"))
)

(defun KC:DeviceCodeFile () (strcat (KC:BaseDir) "\\device.id"))
(defun KC:LicenseGrantFile () (strcat (KC:BaseDir) "\\license.grant"))
(defun KC:SessionOverrideFile () (strcat (KC:BaseDir) "\\session_override.key"))

(defun KC:FileExists (p) (and p (findfile p) T))

(defun KC:WriteTextFile (path text / f)
  (setq f (open path "w"))
  (if f (progn (write-line text f) (close f) T) nil)
)

(defun KC:ReadFirstLine (path / f line)
  (setq line "")
  (if (KC:FileExists path)
    (progn
      (setq f (open path "r"))
      (if f (progn (setq line (read-line f)) (close f)))
    )
  )
  (KC:Trim line)
)

(defun KC:NormalizeDeviceCode (s / u raw i ch ok)
  (setq u (strcase (KC:Trim s)))
  (if (and (>= (strlen u) 5) (= (substr u 1 5) "KCPC-"))
    (progn
      (setq raw ""
            i   6)
      (while (<= i (strlen u))
        (setq ch (substr u i 1))
        (if (/= ch "-") (setq raw (strcat raw ch)))
        (setq i (1+ i)))
      (setq ok (= (strlen raw) 32)
            i  1)
      (while (and ok (<= i 32))
        (if (null (vl-string-search (substr raw i 1) "0123456789ABCDEF"))
          (setq ok nil))
        (setq i (1+ i)))
      (if ok
        (strcat
          "KCPC-"
          (substr raw 1 8) "-" (substr raw 9 8) "-"
          (substr raw 17 8) "-" (substr raw 25 8))))
  )
)

(defun KC:ValidDeviceCodeP (s)
  (if (KC:NormalizeDeviceCode s) T nil)
)

(defun KC:SleepMS (ms / t0)
  (setq t0 (getvar "MILLISECS"))
  (while (< (- (getvar "MILLISECS") t0) ms) (princ))
  T
)
(defun KC:RunHidden (cmd wait / sh r)
  ;; Komut satýrý penceresi göstermeden (gizli) sistem komutu alistirir.
  ;; wait=T ise komut bitene kadar bekler.
  (vl-load-com)
  (setq sh (vlax-create-object "WScript.Shell"))
  (setq r (vlax-invoke-method sh 'Run cmd 0 (if wait :vlax-true :vlax-false)))
  (vlax-release-object sh)
  r
)

(defun KC:ProcessToken (/ pid hwnd)
  (setq pid (vl-catch-all-apply 'getvar (list "PROCESSID")))
  (cond
    ((and (not (vl-catch-all-error-p pid)) (= (type pid) 'INT) (> pid 0))
      (itoa pid)
    )
    ((and (not (vl-catch-all-error-p pid)) (= (type pid) 'REAL) (> pid 0.0))
      (rtos pid 2 0)
    )
    (T
      (setq hwnd (vl-catch-all-apply 'getvar (list "HWND")))
      (if (and (not (vl-catch-all-error-p hwnd))
               (member (type hwnd) '(INT REAL))
               (> hwnd 0))
        (if (= (type hwnd) 'INT) (itoa hwnd) (rtos hwnd 2 0))
        (strcat
          (itoa (getvar "MILLISECS"))
          "_"
          (vl-string-translate ".-" "__" (rtos (getvar "DATE") 2 12))
        )
      )
    )
  )
)

(defun KC:GetDeviceCode (/ script state resultPath logPath cmd runResult result code file)
  (setq script (DEGDO--win-script-path)
        state
          (DEG:RUNTIME-FILE
            (strcat "kc_device_" (KC:ProcessToken) ".txt"))
        resultPath (strcat state ".result")
        logPath    (strcat state ".log"))
  (foreach file (list state resultPath logPath)
    (if (KC:FileExists file) (vl-file-delete file)))
  (if script
    (progn
      (setq cmd
        (strcat
          "powershell.exe -NoProfile -ExecutionPolicy Bypass -WindowStyle Hidden -File \""
          script
          "\" -Mode DeviceCode -StatePath \""
          state
          "\" -DeviceCodePath \""
          (KC:DeviceCodeFile)
          "\""))
      (setq runResult (vl-catch-all-apply 'KC:RunHidden (list cmd T)))
      (if (and (not (vl-catch-all-error-p runResult))
               (KC:FileExists resultPath))
        (setq result (KC:Trim (KC:ReadFirstLine resultPath))))
      (if (and result (= (substr result 1 (min 3 (strlen result))) "OK|"))
        (setq code (KC:NormalizeDeviceCode (substr result 4))))
      (foreach file (list state resultPath)
        (if (KC:FileExists file) (vl-file-delete file)))
      (if (and code (KC:FileExists logPath)) (vl-file-delete logPath))))
  code
)

(defun KC:DeleteLegacyLicenseCache (/ path)
  ;; Eski sistemin tum izin listesini iceren duz metin cache'lerini kaldir.
  (foreach path
    (list
      (strcat (KC:BaseDir) "\\allowlist.cache")
      (strcat (KC:BaseDir) "\\allowlist.time"))
    (if (KC:FileExists path) (vl-file-delete path)))
  T
)

(defun KC:CheckDeviceLicense (code / script state resultPath logPath cmd runResult result file)
  (setq script (DEGDO--win-script-path)
        state
          (DEG:RUNTIME-FILE
            (strcat "kc_license_check_" (KC:ProcessToken) ".txt"))
        resultPath (strcat state ".result")
        logPath    (strcat state ".log"))
  (foreach file (list state resultPath logPath)
    (if (KC:FileExists file) (vl-file-delete file)))
  (if (and script code)
    (progn
      (setq cmd
        (strcat
          "powershell.exe -NoProfile -ExecutionPolicy Bypass -WindowStyle Hidden -File \""
          script
          "\" -Mode LicenseCheck -StatePath \""
          state
          "\" -DeviceCode \""
          code
          "\" -LicenseMarkerBaseUrl \""
          *KC_LICENSE_MARKER_BASE_URL*
          "\" -LicenseGrantPath \""
          (KC:LicenseGrantFile)
          "\" -LicenseOverridePath \""
          (KC:SessionOverrideFile)
          "\" -LicenseGrantHours 24"))
      (setq runResult (vl-catch-all-apply 'KC:RunHidden (list cmd T)))
      (if (and (not (vl-catch-all-error-p runResult))
               (KC:FileExists resultPath))
        (setq result (KC:Trim (KC:ReadFirstLine resultPath)))
        (setq result
          (if (vl-catch-all-error-p runResult)
            "FAILED|POWERSHELL_START"
            "FAILED|RESULT_MISSING")))
      (foreach file (list state resultPath)
        (if (KC:FileExists file) (vl-file-delete file)))
      (if (and (KC:FileExists logPath)
               result
               (wcmatch (strcase result) "OK|*"))
        (vl-file-delete logPath))
      result)
    "FAILED|UI_SCRIPT_NOT_FOUND")
)

(defun KC:Blocked ()
  (princ "\n[KC] Yetkisiz.\n")
  (princ)
)

(defun DKK_ORIG
  (/ *DEG_DKK_MODE* *DEG_DKK_GROUPS* *DEG_DKK_SEEN_OCCURRENCES*
     *DEG_DKK_LIST_COUNTS* *DEG_DKK_LIST_GROUPS* *DEG_DK_LAST_COPY_OBJ*)
  (setq *DEG_DKK_MODE* T
        *DEG_DKK_GROUPS* nil
        *DEG_DKK_SEEN_OCCURRENCES* nil
        *DEG_DKK_LIST_COUNTS* nil
        *DEG_DKK_LIST_GROUPS* nil
        *DEG_DK_LAST_COPY_OBJ* nil)
  (princ "\nDKK: Ayni semboller tek gosterilecek, ADET toplami yazilacak.")
  (DK_ORIG)
)

;; Basarili lisans sonucu AutoCAD oturumu boyunca tum dokumanlarla paylasilir.
(setq *KC_LICENSE_SESSION_VERSION* "KC_SESSION_V5_DEVICE_MARKER_PBKDF2")
(setq *KC_LICENSE_OK* nil
      *KC_LICENSE_CHECKED* nil
      *KC_LICENSE_LAST_CHECK* nil)

(defun KC:ShowDeviceCodeDialog (code / script path resultPath logPath file pid cmd runResult result item)
  (setq script (DEGDO--win-script-path)
        path
          (DEG:RUNTIME-FILE
            (strcat
              "kc_license_"
              (KC:ProcessToken)
              "_"
              (itoa (getvar "MILLISECS"))
              ".txt"))
        resultPath (strcat path ".result")
        logPath    (strcat path ".log"))
  (foreach item (list path resultPath logPath)
    (if (KC:FileExists item) (vl-file-delete item)))
  (if (and script (setq file (open path "w")))
    (progn
      (write-line "DEG" file)
      (write-line (if code code "<KOD_OLUSTURULAMADI>") file)
      (close file)
      (setq pid (vl-catch-all-apply 'getvar (list "PROCESSID")))
      (if (or (vl-catch-all-error-p pid) (not (numberp pid)))
        (setq pid 0)
        (setq pid (fix pid)))
      (setq cmd
        (strcat
          "powershell.exe -NoProfile -ExecutionPolicy Bypass -STA -WindowStyle Hidden -File \""
          script
          "\" -Mode License -StatePath \""
          path
          "\" -DeviceCode \""
          (if code code "")
          "\" -PasswordUrl \""
          *KC_BYPASS_VERIFIER_URL*
          "\" -LicenseOverridePath \""
          (KC:SessionOverrideFile)
          "\" -HostPid " (itoa pid)
          " -HostHwnd 0"))
      (setq runResult (vl-catch-all-apply 'KC:RunHidden (list cmd T)))
      (if (and (not (vl-catch-all-error-p runResult))
               (KC:FileExists resultPath))
        (setq result (strcase (KC:Trim (KC:ReadFirstLine resultPath)))))
      (foreach item (list path resultPath)
        (if (KC:FileExists item) (vl-file-delete item)))
      (if (and (not (vl-catch-all-error-p runResult))
               (= runResult 0)
               (member result '("OK" "CLOSED"))
               (KC:FileExists logPath))
        (vl-file-delete logPath))
      (= result "OK"))
    nil)
)

(defun KC:UpdateStateFile ()
  (strcat (KC:BaseDir) "\\update.commit")
)

(defun KC:UpdateDirValidP (dir)
  (and dir
       (KC:FileExists (strcat dir "\\DG_DO_R05.vlx"))
       (KC:FileExists (strcat dir "\\DG_WINDOWS_UI.ps1"))
       (KC:FileExists (strcat dir "\\DG_DT_TAVA_PALET.ps1")))
)

(defun KC:UpdateTargetDir (/ self dir base ext script)
  (setq self (DEG:SELF-FILE))
  (if self
    (setq dir  (vl-filename-directory self)
          base (strcase (vl-filename-base self))
          ext  (strcase (if (vl-filename-extension self) (vl-filename-extension self) ""))))
  (if (not (and dir
                (= base "DG_DO_R05")
                (= ext ".VLX")
                (KC:UpdateDirValidP dir)))
    (progn
      (setq script (DEGDO--win-script-path)
            dir    (if script (vl-filename-directory script) nil))))
  (if (KC:UpdateDirValidP dir) dir nil)
)

(defun KC:CheckForUpdates (showProgress / script target state resultPath logPath cmd runResult result file pid)
  (setq script (DEGDO--win-script-path)
        target (KC:UpdateTargetDir))
  (if (and script target)
    (progn
      (setq state
        (DEG:RUNTIME-FILE
          (strcat "kc_update_" (KC:ProcessToken) ".txt"))
        resultPath (strcat state ".result")
        logPath    (strcat state ".log"))
      (foreach file (list state resultPath logPath)
        (if (KC:FileExists file) (vl-file-delete file)))
      (setq pid (vl-catch-all-apply 'getvar (list "PROCESSID")))
      (if (or (vl-catch-all-error-p pid) (not (numberp pid)))
        (setq pid 0)
        (setq pid (fix pid)))
      (setq cmd
        (strcat
          "powershell.exe -NoProfile -ExecutionPolicy Bypass -WindowStyle Hidden -File \""
          script
          "\" -Mode Update -StatePath \""
          state
          "\" -UpdateApiUrl \""
          *KC_UPDATE_COMMIT_API_URL*
          "\" -UpdateContentsApiUrl \""
          *KC_UPDATE_CONTENTS_API_URL*
          "\" -UpdateRawBaseUrl \""
          *KC_UPDATE_RAW_BASE_URL*
          "\" -TargetDirectory \""
          target
          "\" -UpdateStatePath \""
          (KC:UpdateStateFile)
          "\" -HostPid "
          (itoa pid)
          (if showProgress " -ShowProgress" "")))
      (setq runResult (vl-catch-all-apply 'KC:RunHidden (list cmd T)))
      (if (and (not (vl-catch-all-error-p runResult))
               (KC:FileExists resultPath))
        (setq result (KC:Trim (KC:ReadFirstLine resultPath)))
        (setq result
          (if (vl-catch-all-error-p runResult)
            "FAILED|POWERSHELL_START"
            "FAILED|RESULT_MISSING")))
      (foreach file (list state resultPath)
        (if (KC:FileExists file) (vl-file-delete file)))
      (if (and (KC:FileExists logPath)
               (not (wcmatch (strcase result) "FAILED|*")))
        (vl-file-delete logPath))
      (if (and result (wcmatch (strcase result) "UPDATED|*"))
        (princ "\n[KC] Yeni DEG surumu kuruldu. CAD programini yeniden baslatin.\n"))
      result)
    (if script
      "FAILED|TARGET_NOT_FOUND"
      "FAILED|UI_SCRIPT_NOT_FOUND"))
)

(defun KC:SessionLicenseRead (/ data)
  (setq data
    (vl-catch-all-apply
      'vl-bb-ref
      (list 'KC_LICENSE_SESSION_DATA)
    )
  )
  (if (or (vl-catch-all-error-p data)
          (/= (type data) 'LIST)
          (< (length data) 4)
          (/= (car data) *KC_LICENSE_SESSION_VERSION*)
          (not (nth 1 data))
          (not (numberp (nth 3 data)))
          (> (- (getvar "DATE") (nth 3 data)) *KC_ALLOW_CACHE_DAYS*))
    nil
    data
  )
)

(defun KC:SessionLicenseWrite (ok code / result)
  (setq result
    (vl-catch-all-apply
      'vl-bb-set
      (list
        'KC_LICENSE_SESSION_DATA
        (list
          *KC_LICENSE_SESSION_VERSION*
          (if ok T nil)
          code
          (getvar "DATE")
        )
      )
    )
  )
  (not (vl-catch-all-error-p result))
)

(defun KC:LicenseCheckFreshP ()
  (and *KC_LICENSE_CHECKED*
       *KC_LICENSE_OK*
       (numberp *KC_LICENSE_LAST_CHECK*)
       (<= (- (getvar "DATE") *KC_LICENSE_LAST_CHECK*) *KC_ALLOW_CACHE_DAYS*))
)

(defun KC:InitLicense (/ session code result ok)
  (if (not (KC:LicenseCheckFreshP))
    (progn
      (setq *KC_LICENSE_OK* nil
            *KC_LICENSE_CHECKED* nil
            *KC_LICENSE_LAST_CHECK* nil)
      (setq session (KC:SessionLicenseRead))
      (if session
        (progn
          (setq *KC_LICENSE_OK* T
                *KC_LICENSE_CHECKED* T
                *KC_LICENSE_LAST_CHECK* (nth 3 session)))
        (progn
          (KC:DeleteLegacyLicenseCache)
          (setq code   (KC:GetDeviceCode)
                result (if code (KC:CheckDeviceLicense code) nil)
                ok     (and result (wcmatch (strcase result) "OK|*")))

          ;; PowerShell once Windows-acilisina bagli bypass kaydini, sonra 24
          ;; saatlik DPAPI grant'i denetler; gerekirse yalniz bu cihazin .lic
          ;; dosyasini GitHub'dan sorgular.
          (if ok
            (progn
              (setq *KC_LICENSE_OK* T
                    *KC_LICENSE_CHECKED* T
                    *KC_LICENSE_LAST_CHECK* (getvar "DATE"))
              (KC:SessionLicenseWrite T code))
            (progn
              (setq *KC_LICENSE_OK* nil
                    *KC_LICENSE_CHECKED* nil
                    *KC_LICENSE_LAST_CHECK* nil)
              (if (KC:ShowDeviceCodeDialog code)
                (progn
                  (setq *KC_LICENSE_OK* T
                        *KC_LICENSE_CHECKED* T
                        *KC_LICENSE_LAST_CHECK* (getvar "DATE"))
                  (KC:SessionLicenseWrite T code))))))
      )
    )
  )
  *KC_LICENSE_OK*
)



(defun deg--to-ename (x)
  (cond
    ((= (type x) 'ENAME) x)
    ((= (type x) 'VLA-OBJECT) (vlax-vla-object->ename x))
    (T nil)
  )
)

(defun deg--set-color-aci (x aci / e o)
  (setq e (deg--to-ename x))
  (if e
    (progn
      (setq o (vlax-ename->vla-object e))
      (if o
        (vl-catch-all-apply
          '(lambda ()
             (if (vlax-property-available-p o 'Color)
               (progn (DEG-DGT--mark-color e) (vla-put-Color o aci))
             )
           )
          nil
        )
      )
    )
  )
)

(defun deg--colorize-ents (lst aci / it)
  (foreach it lst
    (deg--set-color-aci it aci)
  )
)

(defun deg-paint-ref-chain (lst aci)
  (deg--colorize-ents lst aci)
)


(defun deg-color-ref-chain-white ( / ch)
  (vl-load-com)
  (if (and (boundp '*degRefChainEnts*) (setq ch *degRefChainEnts*))
    (deg--colorize-ents ch (DEG:CFG-ACI-OR 'DGT_REF_COLOR 7))
  )
)

(defun DGT_ORIG
  ( / blkEnt continue tmp s txtObj pageName sortedList
     scopeSel scopePolySS scopeBlkSS res )

  (deg-reset-session)
  (deg-clear-deg-done-xdata)
  (vl-load-com)
  (setq continue T)

  (while continue
    (setq *degDGScopePolySS* nil)
    (setq *degDGScopeBlkSS*  nil)

    (setq blkEnt (entsel "\nReferans polyline'ý seçin (ESC = bitir): "))
    (if (not blkEnt)
      (setq continue nil)
      (progn
        (setq tmp (car blkEnt))
        (setq s   (cadr blkEnt))
        (if (not (and tmp
                      (wcmatch (cdr (assoc 0 (entget tmp))) "LWPOLYLINE,POLYLINE")))
          (progn
            (setq continue nil)
            (princ "\n\nLütfen geçerli bir polyline seçin.")
          )
          (progn
            (princ "\nSonra alan seçin (polyline ve blocklar): ")
            (setq scopeSel (ssget '((0 . "LWPOLYLINE,POLYLINE,INSERT"))))

            (if (not scopeSel)
              (progn
                (setq continue nil)
                (princ "\n\nDGT bitti (alan seçilmedi).")
              )
              (progn
                (setq scopePolySS (DEG:SS-FILTER-BY-TYPE scopeSel "LWPOLYLINE,POLYLINE"))
                (setq scopeBlkSS  (DEG:SS-FILTER-BY-TYPE scopeSel "INSERT"))
                (setq scopeBlkSS  (DEG:SS-REMOVE-IGNORED-BLOCKS scopeBlkSS))

                (if (<= (DEG:SS-LEN scopePolySS) 0) (setq scopePolySS nil))
                (if (<= (DEG:SS-LEN scopeBlkSS) 0)  (setq scopeBlkSS  nil))

                (if (not scopePolySS) (setq scopePolySS (ssadd)))
                (if (and tmp (not (DEG:SS-CONTAINS-ENAME? scopePolySS tmp)))
                  (ssadd tmp scopePolySS)
                )

                (setq *degDGScopePolySS* scopePolySS)
                (setq *degDGScopeBlkSS*  scopeBlkSS)

                (setq txtObj   (vlax-ename->vla-object tmp))
                (setq pageName (deg-pt3 (deg-nearest-vertex txtObj s)))
                (if (not pageName) (setq pageName (deg-pt3 s)))
                (if (not pageName) (setq pageName (deg-pt3 (vlax-curve-getStartPoint txtObj))))
                (setq *degForceRefObj* txtObj)
                (setq *degForceRefPt*  pageName)

                ;; Sadece test/renk/tol çemberleri: popup/CSV/yol sorusu yok
                (setq res (vl-catch-all-apply 'deg-build-data (list T pageName)))

                (setq *degForceRefObj* nil)
                (setq *degForceRefPt*  nil)

                (if (vl-catch-all-error-p res)
                  (princ "\n\nDGT hata verdi; geçersiz nokta/içerik atlanarak iþlem durduruldu.")
                  (progn
                    (setq sortedList res)
                    (deg-color-ref-chain-white)
                  )
                )
              )
            )
          )
        )
      )
    )
  )

  (setq *degDGScopePolySS* nil)
  (setq *degDGScopeBlkSS*  nil)
  (princ)
)



(defun DEGDO--trim (s)
  (if s (vl-string-trim " \t\r\n" s) "")
)

(defun DEGDO--join-layers (lst / out)
  (foreach x lst
    (setq x (DEGDO--trim x))
    (if (and (/= x "") (not (member (norm-layer x) (mapcar 'norm-layer out))))
      (setq out (append out (list x)))
    )
  )
  (if out
    (apply 'strcat
      (cons (car out)
        (mapcar '(lambda (a) (strcat "," a)) (cdr out))
      )
    )
    ""
  )
)

(defun DEGDO--codes-merged (codes / out)
  (foreach c codes
    (setq out (append out (DEG:VAL-LIST c)))
  )
  (DEGDO--join-layers out)
)


(defun DEGDO--plan-e-line-layer-list (/ ss i ent ed lay ctab laytab out)
  ;; GstarCAD uyumu: DO acilirken ActiveX ile model taramasi yapma.
  (setq ctab (strcase (getvar "CTAB"))
        out  nil)
  (setq ss (ssget "_X" '((0 . "LINE,LWPOLYLINE,POLYLINE"))))
  (if ss
    (progn
      (setq i 0)
      (while (< i (sslength ss))
        (setq ent (ssname ss i)
              ed  (entget ent)
              lay (cdr (assoc 8 ed))
              laytab (cdr (assoc 410 ed)))
        (if (and lay
                 (or (null laytab) (= (strcase laytab) ctab))
                 (wcmatch (strcase lay) "E_*")
                 (not (member (norm-layer lay) (mapcar 'norm-layer out))))
          (setq out (cons lay out))
        )
        (setq i (1+ i))
      )
    )
  )
  (if out
    (vl-sort out '(lambda (a b) (< (strcase a) (strcase b))))
    nil
  )
)
(defun DEGDO--plan-e-line-layers ()
  (DEGDO--join-layers (DEGDO--plan-e-line-layer-list))
)
(setq *DEGDO_DP_E_LAYERS* nil)
(setq *DEGDO_DP_E_BLOCKS* nil)

(defun DEGDO--dcl-safe (s)
  (if s (vl-string-translate (chr 34) "'" s) "")
)

(defun DEGDO--split-delim (s delim / txt pos part out dlen)
  (setq txt  (if s s "")
        dlen (strlen delim)
        out  nil)
  (while (/= txt "")
    (setq pos (vl-string-search delim txt))
    (if pos
      (progn
        (setq part (substr txt 1 pos))
        (setq txt (substr txt (+ pos dlen 1)))
      )
      (progn
        (setq part txt)
        (setq txt "")
      )
    )
    (setq out (append out (list part)))
  )
  out
)

(defun DEGDO--dp-e-values-alist (/ part pos layer val out)
  (foreach part (DEGDO--split-delim (DEG:CFG-GET 'DP_E_LINE_VALUES) "|")
    (setq pos (vl-string-search "=" part))
    (if pos
      (progn
        (setq layer (norm-layer (substr part 1 pos)))
        (setq val   (DEGDO--trim (substr part (+ pos 2))))
        (if (and (/= layer "") (/= val ""))
          (setq out (cons (cons layer val) out))
        )
      )
    )
  )
  (reverse out)
)

(defun DEGDO--dp-e-value-get (al layer / a)
  (if (setq a (assoc (norm-layer layer) al))
    (cdr a)
    ""
  )
)

(defun DEGDO--dp-e-values-pack (al / out p)
  (foreach p al
    (if (and (car p) (cdr p) (/= (DEGDO--trim (cdr p)) ""))
      (setq out (append out (list (strcat (norm-layer (car p)) "=" (DEGDO--trim (cdr p))))))
    )
  )
  (if out
    (apply 'strcat (cons (car out) (mapcar '(lambda (a) (strcat "|" a)) (cdr out))))
    ""
  )
)

(defun DEGP--layer-list-add-unique (layers lay / u)
  (setq u (norm-layer lay))
  (if (and (/= u "") (not (member u layers)))
    (setq layers (append layers (list u)))
  )
  layers
)

(defun DEGP--merge-layer-lists (a b / out lay)
  (setq out nil)
  (foreach lay (append a b)
    (setq out (DEGP--layer-list-add-unique out lay))
  )
  out
)

(defun DEGP--data-comb-like-layer-p (lay / u)
  (setq u (norm-layer lay))
  (wcmatch u "*KOMBINE*,*COMBINE*,*MULTI*")
)

(defun DEGP--dp-data-line-layers (/ out selected)
  (setq out
    (DEGP--merge-layer-lists
      (DEG:VALS '(C1 C2))
      (DEG:CFG-LIST 'DP_DATA_LINE_LAYERS)))
  (setq selected
    (if (and (boundp '*DEGP_DP_DATA_SELECTED_LAYER*)
             *DEGP_DP_DATA_SELECTED_LAYER*)
      *DEGP_DP_DATA_SELECTED_LAYER*
      ""))
  (if (and (/= selected "")
           (not (DEGP--data-comb-like-layer-p selected)))
    (setq out (DEGP--layer-list-add-unique out selected))
  )
  out
)

(defun DEGP--dp-data-comb-layers (/ out selected)
  (setq out
    (DEGP--merge-layer-lists
      (DEG:VALS '(C3 C4))
      (DEG:CFG-LIST 'DP_DATA_COMB_LAYERS)))
  (setq selected
    (if (and (boundp '*DEGP_DP_DATA_SELECTED_LAYER*)
             *DEGP_DP_DATA_SELECTED_LAYER*)
      *DEGP_DP_DATA_SELECTED_LAYER*
      ""))
  (if (and (/= selected "")
           (DEGP--data-comb-like-layer-p selected))
    (setq out (DEGP--layer-list-add-unique out selected))
  )
  out
)

(defun DEGP--data-line-layers ()
  (DEGP--dp-data-line-layers)
)

(defun DEGP--data-comb-layers ()
  (DEGP--dp-data-comb-layers)
)

(defun DEGP--data-ref-layers ()
  (DEGP--data-comb-layers)
)

(defun DEGP--data-dal-layers ()
  (DEGP--data-line-layers)
)

(defun DEGP--dp-data-mode-p ()
  (and (boundp '*DEGP_DP_DATA_MODE*) *DEGP_DP_DATA_MODE*)
)

(defun DEGP--data-code-snapshot ()
  (list
    (assoc 'C1 *DEG_CODE_OVERRIDES*)
    (assoc 'C2 *DEG_CODE_OVERRIDES*)
    (assoc 'C3 *DEG_CODE_OVERRIDES*)
    (assoc 'C4 *DEG_CODE_OVERRIDES*)
  )
)

(defun DEGP--apply-data-code-overrides (/ lineLayers combLayers)
  (setq lineLayers (DEGDO--join-layers (DEGP--data-line-layers)))
  (setq combLayers (DEGDO--join-layers (DEGP--data-comb-layers)))
  (setq *DEG_CODE_OVERRIDES* (DEG:ALIST-PUT *DEG_CODE_OVERRIDES* 'C1 lineLayers))
  (setq *DEG_CODE_OVERRIDES* (DEG:ALIST-PUT *DEG_CODE_OVERRIDES* 'C2 lineLayers))
  (setq *DEG_CODE_OVERRIDES* (DEG:ALIST-PUT *DEG_CODE_OVERRIDES* 'C3 combLayers))
  (setq *DEG_CODE_OVERRIDES* (DEG:ALIST-PUT *DEG_CODE_OVERRIDES* 'C4 combLayers))
  (princ)
)

(defun DEGP--restore-data-code-snapshot (snap / item key)
  (foreach key '(C1 C2 C3 C4)
    (setq *DEG_CODE_OVERRIDES* (DEG:ALIST-DEL *DEG_CODE_OVERRIDES* key))
  )
  (foreach item snap
    (if item
      (setq *DEG_CODE_OVERRIDES*
        (DEG:ALIST-PUT *DEG_CODE_OVERRIDES* (car item) (cdr item))
      )
    )
  )
  (princ)
)
(defun DEGDO--dp-allow-e-block-p (bname / u)
  (setq u (strcase (if bname bname "")))
  (and (/= u "")
       (wcmatch u "E_*")
       (not (or (vl-string-search "E_OK" u)
                (vl-string-search "PANEL" u)
                (vl-string-search "RACK" u)
                (vl-string-search "DOSEME" u))))
)

(defun DEGDO--plan-e-block-list (/ ss i ent ed bname ctab laytab out)
  ;; GstarCAD uyumu: EffectiveName icin ActiveX cagirmadan INSERT adlarini oku.
  (setq ctab (strcase (getvar "CTAB"))
        out  nil)
  (setq ss (ssget "_X" '((0 . "INSERT"))))
  (if ss
    (progn
      (setq i 0)
      (while (< i (sslength ss))
        (setq ent (ssname ss i)
              ed  (entget ent)
              bname (cdr (assoc 2 ed))
              laytab (cdr (assoc 410 ed)))
        (if (and bname
                 (or (null laytab) (= (strcase laytab) ctab))
                 (DEGDO--dp-allow-e-block-p bname)
                 (not (member (strcase bname) (mapcar 'strcase out))))
          (setq out (cons bname out))
        )
        (setq i (1+ i))
      )
    )
  )
  (if out
    (vl-sort out '(lambda (a b) (< (strcase a) (strcase b))))
    nil
  )
)
(defun DEGDO--dp-e-block-values-alist (/ part pos blk rest vals data tel tv out)
  (foreach part (DEGDO--split-delim (DEG:CFG-GET 'DP_E_BLOCK_VALUES) "|")
    (setq pos (vl-string-search "=" part))
    (if pos
      (progn
        (setq blk  (strcase (DEGDO--trim (substr part 1 pos)))
              rest (substr part (+ pos 2))
              vals (DEGDO--split-delim rest "^")
              data (DEGDO--trim (car vals))
              tel  (DEGDO--trim (cadr vals))
              tv   (DEGDO--trim (caddr vals)))
        (if (/= blk "")
          (setq out (cons (list blk data tel tv) out))
        )
      )
    )
  )
  (reverse out)
)

(defun DEGDO--dp-e-block-row-get (al blk / row hit)
  (setq blk (strcase blk))
  (foreach row al
    (if (= (car row) blk)
      (setq hit row)
    )
  )
  hit
)

(defun DEGDO--dp-e-block-value-get (al blk idx / row)
  (setq row (DEGDO--dp-e-block-row-get al blk))
  (if row
    (nth (+ idx 1) row)
    ""
  )
)

(defun DEGDO--dp-e-block-values-pack (al / out row blk data tel tv)
  (foreach row al
    (setq blk  (if (car row) (strcase (car row)) "")
          data (DEGDO--trim (nth 1 row))
          tel  (DEGDO--trim (nth 2 row))
          tv   (DEGDO--trim (nth 3 row)))
    (if (and (/= blk "")
             (or (/= data "") (/= tel "") (/= tv "")))
      (setq out (append out (list (strcat blk "=" data "^" tel "^" tv))))
    )
  )
  (if out
    (apply 'strcat (cons (car out) (mapcar '(lambda (a) (strcat "|" a)) (cdr out))))
    ""
  )
)

(defun DEGDO--split-columns (lst cols / total per idx chunk out)
  (if (< cols 1) (setq cols 1))
  (setq total (length lst))
  (if (= total 0)
    nil
    (progn
      (setq per (fix (/ (+ total cols -1) cols)))
      (if (< per 1) (setq per 1))
      (setq idx 0
            out nil)
      (while (< idx total)
        (setq chunk nil)
        (repeat per
          (if (< idx total)
            (progn
              (setq chunk (append chunk (list (nth idx lst))))
              (setq idx (1+ idx))
            )
          )
        )
        (setq out (append out (list chunk)))
      )
      out
    )
  )
)

(defun DEGDO--dp-dcl-lines (/ layers layerCols layerChunks out idx lay chunk)
  (setq layers (DEGDO--plan-e-line-layer-list))
  (setq *DEGDO_DP_E_LAYERS* layers)
  (setq out
    '(
      "do_dp : dialog {"
      "  label = \"DO - DP\";"
      "  : column {"
      "    : boxed_column {"
      "      label = \"Menuler\";"
      "      : row { spacer; : button { key = \"tab_dd\"; label = \"DD\"; width = 9; fixed_width = true; } : button { key = \"tab_df\"; label = \"DF\"; width = 9; fixed_width = true; } : button { key = \"tab_dg\"; label = \"DG\"; width = 9; fixed_width = true; } : button { key = \"tab_dgt\"; label = \"DGT\"; width = 9; fixed_width = true; } : button { key = \"tab_dn\"; label = \"DN\"; width = 9; fixed_width = true; } : button { key = \"tab_dk\"; label = \"DK\"; width = 9; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
      "      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DP Plan e_ Layerlari\";"
    )
  )
  (if layers
    (progn
      (setq layerCols   (if (> (length layers) 14) 2 1)
            layerChunks (DEGDO--split-columns layers layerCols)
            idx         1)
      (if (> layerCols 1)
        (setq out (append out '("        : row {")))
      )
      (foreach chunk layerChunks
        (if (> layerCols 1)
          (setq out (append out '("          : column {")))
        )
        (setq out (append out (list "            : row { : text { label = \"Layer\"; width = 26; } : text { label = \"Sayi\"; width = 8; } }")))
        (foreach lay chunk
          (setq out
            (append out
              (list
                (strcat
                  "            : row { : text { label = \"" (DEGDO--dcl-safe lay) "\"; width = 26; }"
                  " : edit_box { key = \"dp_e_qty_" (itoa idx) "\"; edit_width = 8; } }"
                )
              )
            )
          )
          (setq idx (1+ idx))
        )
        (if (> layerCols 1)
          (setq out (append out '("          }")))
        )
      )
      (if (> layerCols 1)
        (setq out (append out '("        }")))
      )
    )
    (setq out (append out '("        : text { label = \"Planda e_ ile baslayan LINE/POLYLINE layer bulunamadi.\"; }")))
  )
  (append out
    '(
      "    }"
      "    : boxed_column {"
      "      label = \"DP AYDINLATMA Layerlari\";"
      "      : edit_box { key = \"dp_light_line\"; label = \"Aydinlatma Hatlari (,)\"; edit_width = 38; }"
      "      : edit_box { key = \"dp_light_comb\"; label = \"Aydinlatma Kombine (,)\"; edit_width = 38; }"
      "    }"
      "    : boxed_column {"
      "      label = \"DP DATA Layerlari\";"
      "      : edit_box { key = \"dp_data_line\"; label = \"Data Hatlari (,)\"; edit_width = 38; }"
      "      : edit_box { key = \"dp_data_comb\"; label = \"Data Kombine (,)\"; edit_width = 38; }"
      "    }"
      "    : boxed_column {"
      "      label = \"DP KOMBINE Layerlari\";"
      "      : edit_box { key = \"dp_kombine_line\"; label = \"Hat Layerlari (,)\"; edit_width = 38; }"
      "      : edit_box { key = \"dp_kombine_comb\"; label = \"Kombine Layerlari (,)\"; edit_width = 38; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
    )
  )
)

(defun DEGDO--blocklar-dcl-lines (/ blocks blockCols blockChunks out idx blk chunk)
  (setq blocks (DEGDO--plan-e-block-list))
  (setq *DEGDO_DP_E_BLOCKS* blocks)
  (setq out
    '(
      "do_blocklar : dialog {"
      "  label = \"DO - BLOCKLAR\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
      "      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DP Plan e_ Blocklari\";"
    )
  )
  (if blocks
    (progn
      (setq blockCols
        (cond
          ((> (length blocks) 24) 3)
          ((> (length blocks) 10) 2)
          (T 1)
        )
      )
      (setq blockChunks (DEGDO--split-columns blocks blockCols)
            idx         1)
      (if (> blockCols 1)
        (setq out (append out '("        : row {")))
      )
      (foreach chunk blockChunks
        (if (> blockCols 1)
          (setq out (append out '("          : column {")))
        )
        (setq out (append out (list "            : row { : text { label = \"Block\"; width = 24; } : text { label = \"Data\"; width = 6; } : text { label = \"Tel\"; width = 6; } : text { label = \"TV\"; width = 6; } }")))
        (foreach blk chunk
          (setq out
            (append out
              (list
                (strcat
                  "            : row { : text { label = \"" (DEGDO--dcl-safe blk) "\"; width = 24; }"
                  " : edit_box { key = \"dp_e_blk_data_" (itoa idx) "\"; edit_width = 6; }"
                  " : edit_box { key = \"dp_e_blk_tel_" (itoa idx) "\"; edit_width = 6; }"
                  " : edit_box { key = \"dp_e_blk_tv_" (itoa idx) "\"; edit_width = 6; } }"
                )
              )
            )
          )
          (setq idx (1+ idx))
        )
        (if (> blockCols 1)
          (setq out (append out '("          }")))
        )
      )
      (if (> blockCols 1)
        (setq out (append out '("        }")))
      )
    )
    (setq out (append out '("        : text { label = \"Planda e_ ile baslayan BLOCK bulunamadi.\"; }")))
  )
  (append out
    '(
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
    )
  )
)
(defun DEGDO--write-dcl (/ fn f lines)
  (setq fn (strcat (getenv "TEMP") "\\deg_do.dcl"))
  (setq lines
    (append
      '(
      "do_dg : dialog {"
      "  label = \"DO - DG\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DG Layer Ayarlari\";"
      "      : row {"
      "        : boxed_column {"
      "          label = \"Aydinlatma / Priz\";"
      "          : edit_box { key = \"light_line\"; label = \"Aydinlatma Hatlari (,)\"; edit_width = 38; }"
      "          : edit_box { key = \"light_comb\"; label = \"Aydinlatma Kombine (,)\"; edit_width = 38; }"
      "          : edit_box { key = \"priz_line\"; label = \"Priz Hatlari (,)\"; edit_width = 38; }"
      "          : edit_box { key = \"priz_comb\"; label = \"Priz Kombine (,)\"; edit_width = 38; }"
      "        }"
      "        : boxed_column {"
      "          label = \"KNX / Buton / Anahtar / Kit\";"
      "          : edit_box { key = \"knx_layers\"; label = \"KNX Layerlari (,)\"; edit_width = 38; }"
      "          : edit_box { key = \"buton_layers\"; label = \"Buton Hatlari (,)\"; edit_width = 38; }"
      "          : edit_box { key = \"anahtar_layers\"; label = \"Anahtar Hatlari (,)\"; edit_width = 38; }"
      "          : edit_box { key = \"kit_layers\"; label = \"Kit Sinyal Hatlari (,)\"; edit_width = 38; }"
      "          : edit_box { key = \"dg_extra\"; label = \"Ek Layerlar (,)\"; edit_width = 38; }"
      "        }"
      "      }"
      "      : row {"
      "        : boxed_column {"
      "          label = \"Data / Fiber\";"
      "          : edit_box { key = \"data_line\"; label = \"Data Hatlari (,)\"; edit_width = 38; }"
      "          : edit_box { key = \"data_comb\"; label = \"Data Kombine (,)\"; edit_width = 38; }"
      "          : edit_box { key = \"fiber_line\"; label = \"Fiber Hatlari (,)\"; edit_width = 38; }"
      "          : edit_box { key = \"fiber_comb\"; label = \"Fiber Kombine (,)\"; edit_width = 38; }"
      "        }"
      "        : boxed_column {"
      "          label = \"Telefon / TV\";"
      "          : edit_box { key = \"tel_line\"; label = \"Telefon Hatlari (,)\"; edit_width = 38; }"
      "          : edit_box { key = \"tel_comb\"; label = \"Telefon Kombine (,)\"; edit_width = 38; }"
      "          : edit_box { key = \"tv_line\"; label = \"TV Hatlari (,)\"; edit_width = 38; }"
      "          : edit_box { key = \"tv_comb\"; label = \"TV Kombine (,)\"; edit_width = 38; }"
      "        }"
      "      }"
      "      : row {"
      "        : boxed_column {"
      "          label = \"UPS\";"
      "          : edit_box { key = \"ups_line\"; label = \"UPS Hatlari (,)\"; edit_width = 38; }"
      "          : edit_box { key = \"ups_comb\"; label = \"UPS Kombine (,)\"; edit_width = 38; }"
      "        }"
      "        : boxed_column {"
      "          label = \"Kartli Gecis\";"
      "          : edit_box { key = \"kartli_line\"; label = \"Kartli Hatlari (,)\"; edit_width = 38; }"
      "          : edit_box { key = \"kartli_comb\"; label = \"Kartli Kombine (,)\"; edit_width = 38; }"
      "        }"
      "      }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dd : dialog {"
      "  label = \"DO - DD\";"
      "  : column {"
      "    : boxed_column {"
      "      label = \"Menuler\";"
      "      : row { spacer; : button { key = \"tab_dd\"; label = \"DD\"; width = 9; fixed_width = true; } : button { key = \"tab_df\"; label = \"DF\"; width = 9; fixed_width = true; } : button { key = \"tab_dg\"; label = \"DG\"; width = 9; fixed_width = true; } : button { key = \"tab_dgt\"; label = \"DGT\"; width = 9; fixed_width = true; } : button { key = \"tab_dn\"; label = \"DN\"; width = 9; fixed_width = true; } : button { key = \"tab_dk\"; label = \"DK\"; width = 9; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DD Ayarlari\";"
      "      : edit_box { key = \"dd_offset\"; label = \"Ofset\"; edit_width = 18; }"
      "      : edit_box { key = \"dd_agiz_arama\"; label = \"Ana Hat Agiz Arama Mesafesi\"; edit_width = 18; }"
      "      : edit_box { key = \"dd_blok_yakinlik\"; label = \"Blok Yakinlik Mesafesi\"; edit_width = 18; }"
      "      : edit_box { key = \"dd_dirsek_dist\"; label = \"Dirsek Baslama Mesafesi\"; edit_width = 18; }"
      "      : edit_box { key = \"dd_dirsek_kacis\"; label = \"Dirsek Kacis Mesafesi\"; edit_width = 18; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_df : dialog {"
      "  label = \"DO - DF\";"
      "  : column {"
      "    : boxed_column {"
      "      label = \"Menuler\";"
      "      : row { spacer; : button { key = \"tab_dd\"; label = \"DD\"; width = 9; fixed_width = true; } : button { key = \"tab_df\"; label = \"DF\"; width = 9; fixed_width = true; } : button { key = \"tab_dg\"; label = \"DG\"; width = 9; fixed_width = true; } : button { key = \"tab_dgt\"; label = \"DGT\"; width = 9; fixed_width = true; } : button { key = \"tab_dn\"; label = \"DN\"; width = 9; fixed_width = true; } : button { key = \"tab_dk\"; label = \"DK\"; width = 9; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
      "      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DF Ayarlari\";"
      "      : edit_box { key = \"df_offset\"; label = \"Ofset\"; edit_width = 18; }"
      "      : edit_box { key = \"df_agiz_arama\"; label = \"Ana Hat Agiz Arama Mesafesi\"; edit_width = 18; }"
      "      : edit_box { key = \"df_blok_yakinlik\"; label = \"Blok Yakinlik Mesafesi\"; edit_width = 18; }"
      "      : edit_box { key = \"df_dirsek_dist\"; label = \"Dirsek Baslama Mesafesi\"; edit_width = 18; }"
      "      : edit_box { key = \"df_dirsek_kacis\"; label = \"Dirsek Kacis Mesafesi\"; edit_width = 18; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dgt : dialog {"
      "  label = \"DO - DGT\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DGT Renkleri\";"
      "      : popup_list { key = \"dgt_chain_color\"; label = \"Zincir polyline\"; edit_width = 22; }"
      "      : popup_list { key = \"dgt_tol_small_color\"; label = \"Tol <= 7 cember\"; edit_width = 22; }"
      "      : popup_list { key = \"dgt_tol_big_color\"; label = \"Tol > 7 cember\"; edit_width = 22; }"
      "      : popup_list { key = \"dgt_sorti_color\"; label = \"R2 test cemberi\"; edit_width = 22; }"
      "      : popup_list { key = \"dgt_ref_color\"; label = \"Referans zinciri\"; edit_width = 22; }"
      "    }"
      "    : row { : button { key = \"defaults\"; label = \"Varsayilan\"; width = 12; fixed_width = true; } : button { key = \"dgt_reset\"; label = \"DGT Reset\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dtt : dialog {"
      "  label = \"DO - DTT\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
      "      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DTT Tava Etiket Ayarlari\";"
      "      : edit_box { key = \"dtt_outside_gap\"; label = \"Cizgi Dis Uzunlugu\"; edit_width = 14; }"
      "      : edit_box { key = \"dtt_rect_width\"; label = \"Dikdortgen Boyu\"; edit_width = 14; }"
      "      : edit_box { key = \"dtt_rect_height\"; label = \"Dikdortgen Eni\"; edit_width = 14; }"
      "      : edit_box { key = \"dtt_att_text_height\"; label = \"Attribute Text Height\"; edit_width = 14; }"
      "      : popup_list { key = \"dtt_att_text_style\"; label = \"Attribute Text Style\"; edit_width = 22; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dt : dialog {"
      "  label = \"DO - DT\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
      "      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DT Tava Turleri\";"
      "      : row { : text { label = \"Kisa Ad\"; width = 8; } : text { label = \"Layer Adi\"; width = 24; } : text { label = \"Cizgi Rengi\"; width = 11; } : text { label = \"Hatch Style\"; width = 12; } : text { label = \"Layer Rengi\"; width = 11; } : text { label = \"Hatch Scale\"; width = 11; } }"
      "      : row { : edit_box { key = \"dt_type1_code\"; edit_width = 6; } : edit_box { key = \"dt_type1_layer\"; edit_width = 22; } : popup_list { key = \"dt_type1_color\"; edit_width = 9; } : popup_list { key = \"dt_type1_hatch_pattern\"; edit_width = 10; } : popup_list { key = \"dt_type1_hatch_color\"; edit_width = 9; } : edit_box { key = \"dt_type1_hatch_scale\"; edit_width = 9; } }"
      "      : row { : edit_box { key = \"dt_type2_code\"; edit_width = 6; } : edit_box { key = \"dt_type2_layer\"; edit_width = 22; } : popup_list { key = \"dt_type2_color\"; edit_width = 9; } : popup_list { key = \"dt_type2_hatch_pattern\"; edit_width = 10; } : popup_list { key = \"dt_type2_hatch_color\"; edit_width = 9; } : edit_box { key = \"dt_type2_hatch_scale\"; edit_width = 9; } }"
      "      : row { : edit_box { key = \"dt_type3_code\"; edit_width = 6; } : edit_box { key = \"dt_type3_layer\"; edit_width = 22; } : popup_list { key = \"dt_type3_color\"; edit_width = 9; } : popup_list { key = \"dt_type3_hatch_pattern\"; edit_width = 10; } : popup_list { key = \"dt_type3_hatch_color\"; edit_width = 9; } : edit_box { key = \"dt_type3_hatch_scale\"; edit_width = 9; } }"
      "      : row { : edit_box { key = \"dt_type4_code\"; edit_width = 6; } : edit_box { key = \"dt_type4_layer\"; edit_width = 22; } : popup_list { key = \"dt_type4_color\"; edit_width = 9; } : popup_list { key = \"dt_type4_hatch_pattern\"; edit_width = 10; } : popup_list { key = \"dt_type4_hatch_color\"; edit_width = 9; } : edit_box { key = \"dt_type4_hatch_scale\"; edit_width = 9; } }"
      "      : row { : edit_box { key = \"dt_type5_code\"; edit_width = 6; } : edit_box { key = \"dt_type5_layer\"; edit_width = 22; } : popup_list { key = \"dt_type5_color\"; edit_width = 9; } : popup_list { key = \"dt_type5_hatch_pattern\"; edit_width = 10; } : popup_list { key = \"dt_type5_hatch_color\"; edit_width = 9; } : edit_box { key = \"dt_type5_hatch_scale\"; edit_width = 9; } }"
      "      : row { : edit_box { key = \"dt_type6_code\"; edit_width = 6; } : edit_box { key = \"dt_type6_layer\"; edit_width = 22; } : popup_list { key = \"dt_type6_color\"; edit_width = 9; } : popup_list { key = \"dt_type6_hatch_pattern\"; edit_width = 10; } : popup_list { key = \"dt_type6_hatch_color\"; edit_width = 9; } : edit_box { key = \"dt_type6_hatch_scale\"; edit_width = 9; } }"
      "      : row { : edit_box { key = \"dt_type7_code\"; edit_width = 6; } : edit_box { key = \"dt_type7_layer\"; edit_width = 22; } : popup_list { key = \"dt_type7_color\"; edit_width = 9; } : popup_list { key = \"dt_type7_hatch_pattern\"; edit_width = 10; } : popup_list { key = \"dt_type7_hatch_color\"; edit_width = 9; } : edit_box { key = \"dt_type7_hatch_scale\"; edit_width = 9; } }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dn : dialog {"
      "  label = \"DO - DN\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      : button { key = \"dn_clear_sira\"; label = \"Plandaki Tum SIRA_NO Degerlerini Temizle\"; }"
      "      label = \"DN Layer / Block Ayarlari\";"
      "      : row {"
      "        : boxed_column {"
      "          label = \"DN Hat Patternleri\";"
      "          : edit_box { key = \"dn_data_pattern\"; label = \"Data Layer Pattern (,)\"; edit_width = 38; }"
      "          : edit_box { key = \"dn_tel_pattern\"; label = \"Telefon Layer Pattern (,)\"; edit_width = 38; }"
      "          : edit_box { key = \"dn_tv_pattern\"; label = \"TV Layer Pattern (,)\"; edit_width = 38; }"
      "          : edit_box { key = \"dn_kartli_pattern\"; label = \"Kartli Layer Pattern (,)\"; edit_width = 38; }"
      "        }"
      "        : boxed_column {"
      "          label = \"DN CCTV\";"
      "          : edit_box { key = \"dn_cctv_layers\"; label = \"CCTV Layerlari (,)\"; edit_width = 60; edit_limit = 2048; }"
      "          : edit_box { key = \"dn_cctv_pattern\"; label = \"CCTV Pattern (,)\"; edit_width = 38; }"
      "          : edit_box { key = \"dn_cctv_keyword\"; label = \"CCTV Keyword\"; edit_width = 38; }"
      "        }"
      "      }"
      "      : row {"
      "        : boxed_column {"
      "          label = \"Dosemeye Inis / Not\";"
      "          : edit_box { key = \"dn_doseme_block\"; label = \"Dosemeye Inis Block\"; edit_width = 38; }"
      "          : edit_box { key = \"dn_doseme_patterns\"; label = \"Dosemeye Inis Pattern (,)\"; edit_width = 38; }"
      "          : edit_box { key = \"dn_not_block\"; label = \"Ilgili Not Block\"; edit_width = 38; }"
      "          : edit_box { key = \"dn_ignore_pattern\"; label = \"Yok Say Pattern (,)\"; edit_width = 38; }"
      "        }"
      "        : boxed_column {"
      "          label = \"Kolon / Yardimci\";"
      "          : edit_box { key = \"dn_kolon_no_layer\"; label = \"Kolon No Layer\"; edit_width = 38; }"
      "          : edit_box { key = \"dn_kolon_sembol_layer\"; label = \"Kolon Sembol Layer\"; edit_width = 38; }"
      "          : edit_box { key = \"dn_linye_block\"; label = \"Linye Block\"; edit_width = 38; }"
      "          : edit_box { key = \"dn_mahal_block\"; label = \"Mahal Block\"; edit_width = 38; }"
      "        }"
      "      }"
      "      : row {"
      "        : boxed_column {"
      "          label = \"Buat / Pano\";"
      "          : edit_box { key = \"dn_buat_blocks\"; label = \"Buat Blocklari (,)\"; edit_width = 38; }"
      "          : edit_box { key = \"dn_buat_patterns\"; label = \"Buat Pattern (,)\"; edit_width = 38; }"
      "          : edit_box { key = \"dn_pano_blocks\"; label = \"Pano Blocklari (,)\"; edit_width = 38; }"
      "          : edit_box { key = \"dn_pano_pattern\"; label = \"Pano Pattern (,)\"; edit_width = 38; }"
      "        }"
      "        : boxed_column {"
      "          label = \"Yangin / Terminal\";"
      "          : edit_box { key = \"dn_flasor_layer\"; label = \"Flasor Layer\"; edit_width = 38; }"
      "          : edit_box { key = \"dn_yangin_blocks\"; label = \"Yangin Blocklari (,)\"; edit_width = 38; }"
      "          : edit_box { key = \"dn_yangin_patterns\"; label = \"Yangin Pattern (,)\"; edit_width = 38; }"
      "          : edit_box { key = \"dn_flasor_keywords\"; label = \"Flasor Keyword (,)\"; edit_width = 38; }"
      "          : edit_box { key = \"dn_terminal_keywords\"; label = \"Terminal Keyword (,)\"; edit_width = 38; }"
      "        }"
      "      }"
      "      : row {"
      "        : boxed_column {"
      "          label = \"DN skipThis\";"
      "          : edit_box { key = \"dn_skip_blocks\"; label = \"Direkt Skip Block (,)\"; edit_width = 38; edit_limit = 2048; }"
      "          : edit_box { key = \"dn_skip_layer_patterns\"; label = \"Layer Skip Pattern (,)\"; edit_width = 38; edit_limit = 2048; }"
      "          : edit_box { key = \"dn_skip_layer_blocks\"; label = \"Layer Skip Block (,)\"; edit_width = 38; edit_limit = 2048; }"
      "        }"
      "        : boxed_column {"
      "          label = \"DN Fire/Flasher Filter\";"
      "          : edit_box { key = \"dn_filter_ignore_blocks\"; label = \"Ignore Block/Pattern (,)\"; edit_width = 38; edit_limit = 2048; }"
      "          : edit_box { key = \"dn_filter_co_layers\"; label = \"CO Layer Pattern (,)\"; edit_width = 38; edit_limit = 2048; }"
      "          : edit_box { key = \"dn_filter_co_blocks\"; label = \"CO Block (,)\"; edit_width = 38; edit_limit = 2048; }"
      "          : edit_box { key = \"dn_filter_flasor_layers\"; label = \"Flasor Layer (,)\"; edit_width = 38; edit_limit = 2048; }"
      "          : edit_box { key = \"dn_filter_flasor_blocks\"; label = \"Flasor Block Pattern (,)\"; edit_width = 38; edit_limit = 2048; }"
      "          : edit_box { key = \"dn_filter_sound_layers\"; label = \"Sounder Layer Pattern (,)\"; edit_width = 38; edit_limit = 2048; }"
      "          : edit_box { key = \"dn_filter_sound_blocks\"; label = \"Sounder Block Pattern (,)\"; edit_width = 38; edit_limit = 2048; }"
      "          : edit_box { key = \"dn_filter_fire_layers\"; label = \"Fire Layer Pattern (,)\"; edit_width = 38; edit_limit = 2048; }"
      "          : edit_box { key = \"dn_filter_fire_exclude_blocks\"; label = \"Fire Exclude Block Name (,)\"; edit_width = 38; edit_limit = 2048; }"
      "        }"
      "      }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dk : dialog {"
      "  label = \"DO - DK\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : row {"
      "      : boxed_column {"
      "        label = \"DK Normal\";"
      "        : edit_box { key = \"dk_copy_spacing\"; label = \"Kopya Araligi\"; edit_width = 12; }"
      "        : edit_box { key = \"dk_text_height\"; label = \"Yazi Yukseklik\"; edit_width = 12; }"
      "        : edit_box { key = \"dk_text_offset_y\"; label = \"Yazi Y Ofset\"; edit_width = 12; }"
      "      }"
      "      : boxed_column {"
      "        label = \"DK Normal Alt Cizgi\";"
      "        : edit_box { key = \"dk_under_x1\"; label = \"Sol Ofset\"; edit_width = 12; }"
      "        : edit_box { key = \"dk_under_x2\"; label = \"Sag Ofset\"; edit_width = 12; }"
      "        : edit_box { key = \"dk_under_w\"; label = \"Genislik\"; edit_width = 12; }"
      "        : edit_box { key = \"dk_under_h\"; label = \"Yukseklik\"; edit_width = 12; }"
      "        : edit_box { key = \"dk_under_y_offset\"; label = \"Cizgi Y Kaydirma\"; edit_width = 12; }"
      "      }"
      "    }"
      "    : row {"
      "      : boxed_column {"
      "        label = \"DK Normal Loop Layerlari\";"
      "        : edit_box { key = \"dk_normal_area_layers\"; label = \"Normal Loop Polyline Layerlari (,)\"; edit_width = 42; edit_limit = 2048; }"
      "      }"
      "      : boxed_column {"
      "        label = \"DK Kombine Layerlari\";"
      "        : edit_box { key = \"dk_combined_riser_layers\"; label = \"Kombine Polyline Layerlari (,)\"; edit_width = 42; edit_limit = 2048; }"
      "      }"
      "    }"
      "    : row {"
      "      : boxed_column {"
      "        label = \"DK Loop Ayarlari\";"
      "        : edit_box { key = \"dk_normal_group_spacing\"; label = \"Ayni Kat Loop Araligi\"; edit_width = 12; }"
      "        : edit_box { key = \"dk_normal_floor_spacing\"; label = \"Katlar Arasi Mesafe\"; edit_width = 12; }"
      "        : edit_box { key = \"dk_loop_text_height\"; label = \"Text Height\"; edit_width = 12; }"
      "        : edit_box { key = \"dk_loop_text_x_offset\"; label = \"Text X Ofset\"; edit_width = 12; }"
      "        : edit_box { key = \"dk_loop_text_y_margin\"; label = \"Text Y Bosluk\"; edit_width = 12; }"
      "      }"
      "      : boxed_column {"
      "        label = \"DK Loop Baslik Cizgisi\";"
      "        : edit_box { key = \"dk_loop_line_shift_x\"; label = \"X Kaydirma\"; edit_width = 12; }"
      "        : edit_box { key = \"dk_loop_line_rise\"; label = \"Dikey Uzunluk\"; edit_width = 12; }"
      "        : edit_box { key = \"dk_loop_line_run\"; label = \"Yatay Uzunluk\"; edit_width = 12; }"
      "      }"
      "      : boxed_column {"
      "        label = \"DK Loop Isaret\";"
      "        : edit_box { key = \"dk_loop_mark_length\"; label = \"45 Derece Boy\"; edit_width = 12; }"
      "      }"
      "    }"
      "    : row {"
      "      : boxed_column {"
      "        label = \"DK DATA / CCTV Genel\";"
      "        : edit_box { key = \"dkx_copy_spacing\"; label = \"Kopya Araligi\"; edit_width = 12; }"
      "        : edit_box { key = \"dkx_firststart_x\"; label = \"Ilk Baslangic X\"; edit_width = 12; }"
      "        : edit_box { key = \"dkx_firststart_y\"; label = \"Ilk Baslangic Y\"; edit_width = 12; }"
      "        : edit_box { key = \"dkx_lastbottom_x\"; label = \"Ana Hat X\"; edit_width = 12; }"
      "        : edit_box { key = \"dkx_lastbottom_y\"; label = \"Ana Hat Y\"; edit_width = 12; }"
      "        : edit_box { key = \"dkx_text_offset_y\"; label = \"Yazi Y Ofset\"; edit_width = 12; }"
      "        : edit_box { key = \"dkx_text_height\"; label = \"Yazi Yukseklik\"; edit_width = 12; }"
      "      }"
      "      : boxed_column {"
      "        label = \"DK DATA / CCTV Cizgi\";"
      "        : edit_box { key = \"dkx_multi_dx\"; label = \"Coklu X Kaydirma\"; edit_width = 12; }"
      "        : edit_box { key = \"dkx_multi_drop_y\"; label = \"Coklu Y Dusum\"; edit_width = 12; }"
      "        : edit_box { key = \"dkx_vlen_main\"; label = \"Dikey Ana\"; edit_width = 12; }"
      "        : edit_box { key = \"dkx_vlen_secondary\"; label = \"Dikey Ikincil\"; edit_width = 12; }"
      "        : edit_box { key = \"dkx_hlen_default\"; label = \"Yatay Standart\"; edit_width = 12; }"
      "        : edit_box { key = \"dkx_hlen_last2\"; label = \"Son 2li\"; edit_width = 12; }"
      "        : edit_box { key = \"dkx_hlen_last3_left\"; label = \"Son 3lu Sol\"; edit_width = 12; }"
      "        : edit_box { key = \"dkx_hlen_last3_right\"; label = \"Son 3lu Sag\"; edit_width = 12; }"
      "      }"
      "    }"
      "    : row {"
      "      : boxed_column {"
      "        label = \"DK DATA Layerlari\";"
      "        : edit_box { key = \"dk_data_layers\"; label = \"Data Layerlari (,)\"; edit_width = 42; edit_limit = 2048; }"
      "        : edit_box { key = \"dk_data_pattern\"; label = \"Data Pattern (,)\"; edit_width = 42; edit_limit = 2048; }"
      "        : edit_box { key = \"dk_data_keyword\"; label = \"Data Keyword\"; edit_width = 42; edit_limit = 256; }"
      "        : edit_box { key = \"dkx_data_shift_y\"; label = \"Block Y Yukari Kaydirma\"; edit_width = 16; }"
      "        : edit_box { key = \"dkx_data_shift_blocks\"; label = \"Yukari Kayacak Blocklar (,)\"; edit_width = 42; edit_limit = 2048; }"
      "      }"
      "      : boxed_column {"
      "        label = \"DK CCTV Layerlari\";"
      "        : edit_box { key = \"dk_cctv_layers\"; label = \"CCTV Layerlari (,)\"; edit_width = 42; edit_limit = 2048; }"
      "        : edit_box { key = \"dk_cctv_pattern\"; label = \"CCTV Pattern (,)\"; edit_width = 42; edit_limit = 2048; }"
      "        : edit_box { key = \"dk_cctv_keyword\"; label = \"CCTV Keyword\"; edit_width = 42; edit_limit = 256; }"
      "      }"
      "    }"
      "    : row {"
      "      : boxed_column {"
      "        label = \"DK Cikti Layerlari\";"
      "        : edit_box { key = \"dk_kolon_no_layer\"; label = \"Kolon No Layer\"; edit_width = 42; edit_limit = 512; }"
      "        : edit_box { key = \"dk_kolon_sembol_layer\"; label = \"Kolon Sembol Layer\"; edit_width = 42; edit_limit = 512; }"
      "      }"
      "      : boxed_column {"
      "        label = \"DK Yardimci\";"
      "        : edit_box { key = \"dk_doseme_block\"; label = \"Dosemeye Inis Block\"; edit_width = 42; edit_limit = 512; }"
      "        : edit_box { key = \"dk_doseme_patterns\"; label = \"Dosemeye Inis Pattern (,)\"; edit_width = 42; edit_limit = 1024; }"
      "        : edit_box { key = \"dk_ignore_pattern\"; label = \"Yok Say Pattern (,)\"; edit_width = 42; edit_limit = 1024; }"
      "        : edit_box { key = \"dk_terminal_keywords\"; label = \"Terminal Keyword (,)\"; edit_width = 42; edit_limit = 1024; }"
      "      }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      )
      (DEGDO--dp-dcl-lines)
      (DEGDO--blocklar-dcl-lines)
      '(
      "do_dz : dialog {"
      "  label = \"DO - DZ\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DZ Ayarlari\";"
      "      : edit_box { key = \"dz_offset\"; label = \"Ofset\"; edit_width = 18; }"
      "      : edit_box { key = \"dz_agiz_arama\"; label = \"Ana Hat Agiz Arama Mesafesi\"; edit_width = 18; }"
      "      : edit_box { key = \"dz_blok_yakinlik\"; label = \"Blok Yakinlik Mesafesi\"; edit_width = 18; }"
      "      : edit_box { key = \"dz_dirsek_dist\"; label = \"Dirsek Baslama Mesafesi\"; edit_width = 18; }"
      "      : edit_box { key = \"dz_dirsek_kacis\"; label = \"Dirsek Kacis Mesafesi\"; edit_width = 18; }"
      "      : edit_box { key = \"dz_cocuk_hat_mesafe\"; label = \"Cocuk Hat Baglanti Mesafesi\"; edit_width = 18; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dc : dialog {"
      "  label = \"DO - DC\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DC Ayarlari\";"
      "      : edit_box { key = \"dc_down_len\"; label = \"Asagi Mesafe\"; edit_width = 18; }"
      "      : edit_box { key = \"dc_fillet_r\"; label = \"Fillet\"; edit_width = 18; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dr : dialog {"
      "  label = \"DO - DR\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column { label = \"DR\"; : text { label = \"Bu komut icin ayar sayfasi hazir.\"; } : text { label = \"Duzenlenebilir alan sonraki revizyonda eklenecek.\"; } }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dw : dialog {"
      "  label = \"DO - DW\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column { label = \"DW\"; : text { label = \"Bu komut icin ayar sayfasi hazir.\"; } : text { label = \"Duzenlenebilir alan sonraki revizyonda eklenecek.\"; } }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_dm : dialog {"
      "  label = \"DO - DM\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column { label = \"DM\"; : text { label = \"Bu komut icin ayar sayfasi hazir.\"; } : text { label = \"Duzenlenebilir alan sonraki revizyonda eklenecek.\"; } }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_ds : dialog {"
      "  label = \"DO - DS\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
      "      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"DS Mesafe Ayarlari\";"
      "      : edit_box { key = \"ds_row_spacing\"; label = \"Satir Araligi\"; edit_width = 14; }"
      "      : edit_box { key = \"ds_symbol_dx\"; label = \"Sembol Yazi X\"; edit_width = 14; }"
      "      : edit_box { key = \"ds_count_dx\"; label = \"Adet Yazi Ek X\"; edit_width = 14; }"
      "      : edit_box { key = \"ds_text_height\"; label = \"Yazi Height\"; edit_width = 14; }"
      "    }"
      "    : boxed_column {"
      "      label = \"DS Liste Bolum Araliklari\";"
      "      : edit_box { key = \"ds_table_block_w\"; label = \"Block Bolumu\"; edit_width = 14; }"
      "      : edit_box { key = \"ds_table_symbol_w\"; label = \"Sembol Bolumu\"; edit_width = 14; }"
      "      : edit_box { key = \"ds_table_count_w\"; label = \"Adet Bolumu\"; edit_width = 14; }"
      "    }"
      "    : boxed_column {"
      "      label = \"Dahil Edilmeyen Blocklar\";"
      "      : edit_box { key = \"ds_exclude_blocks\"; label = \"Block Kelimeleri (,)\"; edit_width = 58; edit_limit = 2048; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_tol : dialog {"
      "  label = \"DO - TOL\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : row {"
      "      : boxed_column {"
      "        label = \"DG / DGT / DATA Tol\";"
      "        : edit_box { key = \"dg_knx_start_tol\"; label = \"KNX Baslangic\"; edit_width = 12; }"
      "        : edit_box { key = \"dg_knx_block_tol\"; label = \"KNX Block\"; edit_width = 12; }"
      "        : edit_box { key = \"dg_knx_end_tol\"; label = \"KNX Uc-Uc\"; edit_width = 12; }"
      "        : edit_box { key = \"dg_ref_tol\"; label = \"Referans\"; edit_width = 12; }"
      "        : edit_box { key = \"dg_chain_tol\"; label = \"Zincir\"; edit_width = 12; }"
      "        : edit_box { key = \"dg_report_tol\"; label = \"BLOCK ALGILAMA !!!\"; edit_width = 12; }"
      "        : edit_box { key = \"dg_ref_dal_tol\"; label = \"Dal Referans\"; edit_width = 12; }"
      "        : edit_box { key = \"dg_dal_single_tol\"; label = \"Tek Dal\"; edit_width = 12; }"
      "        : edit_box { key = \"dg_p1_tol\"; label = \"P1 Ozel\"; edit_width = 12; }"
      "      }"
      "      : boxed_column {"
      "        label = \"DN / Kolon Þemasý Tol\";"
      "        : edit_box { key = \"dn_chain_tol\"; label = \"DN Zincir\"; edit_width = 12; }"
      "        : edit_box { key = \"dn_block_tol\"; label = \"DN Block\"; edit_width = 12; }"
      "        : edit_box { key = \"dn_doseme_tol\"; label = \"DN Döþeme\"; edit_width = 12; }"
      "        : edit_box { key = \"dn_modl_tol\"; label = \"DN MODL\"; edit_width = 12; }"
      "      }"
      "      : boxed_column {"
      "        label = \"DW / DR Tol\";"
      "        : edit_box { key = \"dw_touch_tol\"; label = \"DW Temas\"; edit_width = 14; }"
      "        : edit_box { key = \"dr_tree_tol\"; label = \"DR Agac\"; edit_width = 14; }"
      "      }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_cmds : dialog {"
      "  label = \"DO - KOMUTLAR\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : row {"
      "      : boxed_column {"
      "        label = \"Komut Adlari 1\";"
      "        : edit_box { key = \"cmd_dg\";  label = \"DG\";  edit_width = 12; }"
      "        : text { label = \"Aydinlatma priz data panel ve kesif\"; }"
      "        : edit_box { key = \"cmd_dgt\"; label = \"DGT\"; edit_width = 12; }"
      "        : text { label = \"DG icin cizim testi\"; }"
      "        : edit_box { key = \"cmd_dn\";  label = \"DN\";  edit_width = 12; }"
      "        : text { label = \"Zayif akim numaralandirma\"; }"
      "        : edit_box { key = \"cmd_dk\";  label = \"DK\";  edit_width = 12; }"
      "        : text { label = \"Kolon semasi cizimi\"; }"
      "        : edit_box { key = \"cmd_dkk\"; label = \"DKK\"; edit_width = 12; }"
      "        : text { label = \"Kolon semasi sembol adet ozeti\"; }"
      "        : edit_box { key = \"cmd_dp\";  label = \"DP\";  edit_width = 12; }"
      "        : text { label = \"Hat uzunlugu ve KOMBINE ozel mod\"; }"
      "        : edit_box { key = \"cmd_dd\";  label = \"DD\";  edit_width = 12; }"
      "        : text { label = \"Loop basit cizim\"; }"
      "        : edit_box { key = \"cmd_df\";  label = \"DF\";  edit_width = 12; }"
      "        : text { label = \"Tiklanan polyline segmentinden loop cizimi\"; }"
      "      }"
      "      : boxed_column {"
      "        label = \"Komut Adlari 2\";"
      "        : edit_box { key = \"cmd_dz\";  label = \"DZ\";  edit_width = 12; }"
      "        : text { label = \"Loop cizimi\"; }"
      "        : edit_box { key = \"cmd_dw\";  label = \"DW\";  edit_width = 12; }"
      "        : text { label = \"Adet kesif\"; }"
      "        : edit_box { key = \"cmd_dm\";  label = \"DM\";  edit_width = 12; }"
      "        : text { label = \"Mahal mahal adet kesif\"; }"
      "        : edit_box { key = \"cmd_ds\";  label = \"DS\";  edit_width = 12; }"
      "        : text { label = \"E_ block sembol ve adet listesi\"; }"
      "        : edit_box { key = \"cmd_dt\";  label = \"DT\";  edit_width = 12; }"
      "        : text { label = \"10 birim kablo tavasi cizimi\"; }"
      "        : edit_box { key = \"cmd_dtm\"; label = \"DTM\"; edit_width = 12; }"
      "        : text { label = \"Tava metraji ve donus elemani adedi\"; }"
      "        : edit_box { key = \"cmd_dtt\"; label = \"DTT\"; edit_width = 12; }"
      "        : text { label = \"Tavalara dikdortgen ve baglanti cizgisi\"; }"
      "        : edit_box { key = \"cmd_do\";  label = \"DO\";  edit_width = 12; }"
      "        : text { label = \"Ayar ekranlari\"; }"
      "        : edit_box { key = \"cmd_ucs\"; label = \"UCS\"; edit_width = 12; }"
      "        : text { label = \"AutoCAD UCS komutu\"; }"
      "      }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_plan : dialog {"
      "  label = \"DO - PLAN\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"PLAN Ayarlari\";"
      "      : popup_list { key = \"plan_unit\"; label = \"Olcu Birimi\"; edit_width = 18; }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      "do_kayit : dialog {"
      "  label = \"DO - KAYIT\";"
      "  : column {"
      "    : boxed_column {"
      "      label = \"Menuler\";"
      "      : row { spacer; : button { key = \"tab_dd\"; label = \"DD\"; width = 10; fixed_width = true; } : button { key = \"tab_dg\"; label = \"DG\"; width = 10; fixed_width = true; } : button { key = \"tab_dgt\"; label = \"DGT\"; width = 10; fixed_width = true; } : button { key = \"tab_dn\"; label = \"DN\"; width = 10; fixed_width = true; } : button { key = \"tab_dk\"; label = \"DK\"; width = 10; fixed_width = true; } spacer; }"
      "      : row { spacer; : button { key = \"tab_dp\"; label = \"DP\"; width = 9; fixed_width = true; } : button { key = \"tab_dz\"; label = \"DZ\"; width = 9; fixed_width = true; } : button { key = \"tab_dc\"; label = \"DC\"; width = 9; fixed_width = true; } : button { key = \"tab_dw\"; label = \"DW\"; width = 9; fixed_width = true; } : button { key = \"tab_dm\"; label = \"DM\"; width = 9; fixed_width = true; } : button { key = \"tab_ds\"; label = \"DS\"; width = 9; fixed_width = true; } spacer; }"
"      : row { spacer; : button { key = \"tab_dt\"; label = \"DT\"; width = 8; fixed_width = true; } : button { key = \"tab_dtt\"; label = \"DTT\"; width = 8; fixed_width = true; } : button { key = \"tab_plan\"; label = \"PLAN\"; width = 9; fixed_width = true; } : button { key = \"tab_tol\"; label = \"TOL\"; width = 8; fixed_width = true; } : button { key = \"tab_blocklar\"; label = \"BLOCKLAR\"; width = 11; fixed_width = true; } : button { key = \"tab_cmds\"; label = \"KOMUTLAR\"; width = 11; fixed_width = true; } : button { key = \"tab_kayit\"; label = \"KAYIT\"; width = 9; fixed_width = true; } spacer; }"
      "    }"
      "    : boxed_column {"
      "      label = \"Kayit Ayarlari\";"
      "      : row {"
      "        : edit_box { key = \"kayit_path\"; label = \"Dosya Lokasyonu\"; edit_width = 44; }"
      "        : button { key = \"kayit_browse\"; label = \"Browse\"; width = 12; fixed_width = true; }"
      "      }"
      "    }"
      "    : row { : button { key = \"defaults\"; label = \"Varsayilan\"; width = 12; fixed_width = true; } spacer; : button { key = \"accept\"; label = \"Kaydet\"; is_default = true; width = 12; fixed_width = true; } : button { key = \"cancel\"; label = \"Kapat\"; is_cancel = true; width = 12; fixed_width = true; } }"
      "  }"
      "}"
      )
    )
  )
  (if (setq f (open fn "w"))
    (progn
      (foreach ln lines (write-line ln f))
      (close f)
      fn
    )
    nil
  )
)

(defun DEGDO--bind-tabs (page / saveCmd)
  (setq saveCmd
    (cond
      ((= page "do_dd") "(DEGDO--save-dd) ")
      ((= page "do_df") "(DEGDO--save-df) ")
      ((= page "do_dg") "(DEGDO--save-dg) ")
      ((= page "do_dgt") "(DEGDO--save-dgt) ")
      ((= page "do_dt") "(DEGDO--save-dt) ")
      ((= page "do_dtt") "(DEGDO--save-dtt) ")
      ((= page "do_dn") "(DEGDO--save-dn) ")
      ((= page "do_dp") "(DEGDO--save-dp) ")
      ((= page "do_blocklar") "(DEGDO--save-blocklar) ")
      ((= page "do_dz") "(DEGDO--save-dz) ")
      ((= page "do_dc") "(DEGDO--save-dc) ")
      ((= page "do_ds") "(DEGDO--save-ds) ")
      ((= page "do_plan") "(DEGDO--save-plan) ")
      ((= page "do_kayit") "(DEGDO--save-kayit) ")
      ((= page "do_tol") "(DEGDO--save-tol) ")
      (T "")
    )
  )
  (action_tile "tab_dd"  (strcat saveCmd "(setq *DEGDO_NEXT* \"do_dd\") (done_dialog 2)"))
  (action_tile "tab_df"  (strcat saveCmd "(setq *DEGDO_NEXT* \"do_df\") (done_dialog 2)"))
  (action_tile "tab_dg"  (strcat saveCmd "(setq *DEGDO_NEXT* \"do_dg\") (done_dialog 2)"))
  (action_tile "tab_dgt" (strcat saveCmd "(setq *DEGDO_NEXT* \"do_dgt\") (done_dialog 2)"))
  (action_tile "tab_dt"  (strcat saveCmd "(setq *DEGDO_NEXT* \"do_dt\") (done_dialog 2)"))
  (action_tile "tab_dtt" (strcat saveCmd "(setq *DEGDO_NEXT* \"do_dtt\") (done_dialog 2)"))
  (action_tile "tab_dn"  (strcat saveCmd "(setq *DEGDO_NEXT* \"do_dn\") (done_dialog 2)"))
  (action_tile "tab_dk"  (strcat saveCmd "(setq *DEGDO_NEXT* \"do_dk\") (done_dialog 2)"))
  (action_tile "tab_dp"  (strcat saveCmd "(setq *DEGDO_NEXT* \"do_dp\") (done_dialog 2)"))
  (action_tile "tab_blocklar" (strcat saveCmd "(setq *DEGDO_NEXT* \"do_blocklar\") (done_dialog 2)"))
  (action_tile "tab_dz"  (strcat saveCmd "(setq *DEGDO_NEXT* \"do_dz\") (done_dialog 2)"))
  (action_tile "tab_dc"  (strcat saveCmd "(setq *DEGDO_NEXT* \"do_dc\") (done_dialog 2)"))
  (action_tile "tab_dr"  (strcat saveCmd "(setq *DEGDO_NEXT* \"do_dr\") (done_dialog 2)"))
  (action_tile "tab_dw"  (strcat saveCmd "(setq *DEGDO_NEXT* \"do_dw\") (done_dialog 2)"))
  (action_tile "tab_dm"  (strcat saveCmd "(setq *DEGDO_NEXT* \"do_dm\") (done_dialog 2)"))
  (action_tile "tab_ds"  (strcat saveCmd "(setq *DEGDO_NEXT* \"do_ds\") (done_dialog 2)"))
  (action_tile "tab_plan" (strcat saveCmd "(setq *DEGDO_NEXT* \"do_plan\") (done_dialog 2)"))
  (action_tile "tab_tol" (strcat saveCmd "(setq *DEGDO_NEXT* \"do_tol\") (done_dialog 2)"))
  (action_tile "tab_cmds" (strcat saveCmd "(setq *DEGDO_NEXT* \"do_cmds\") (done_dialog 2)"))
  (action_tile "tab_kayit" (strcat saveCmd "(setq *DEGDO_NEXT* \"do_kayit\") (done_dialog 2)"))
)

(defun DEGDO--fill-dd ()
  (set_tile "dd_offset" (DEGDO--dddz-display 'DD_OFFSET))
  (set_tile "dd_agiz_arama" (DEGDO--dddz-display-or 'DD_AGIZ_ARAMA 20.0))
  (set_tile "dd_blok_yakinlik" (DEGDO--dddz-display-or 'DD_BLOK_YAKINLIK 100.0))
  (set_tile "dd_dirsek_dist" (DEGDO--dddz-display-or 'DD_DIRSEK_DIST 200.0))
  (set_tile "dd_dirsek_kacis" (DEGDO--dddz-display-or 'DD_DIRSEK_KACIS 50.0))
)

(defun DEGDO--save-dd ()
  (DEG:CFG-SET 'DD_OFFSET (DEGDO--dddz-store "dd_offset"))
  (DEG:CFG-SET 'DD_AGIZ_ARAMA (DEGDO--dddz-store "dd_agiz_arama"))
  (DEG:CFG-SET 'DD_BLOK_YAKINLIK (DEGDO--dddz-store "dd_blok_yakinlik"))
  (DEG:CFG-SET 'DD_DIRSEK_DIST (DEGDO--dddz-store "dd_dirsek_dist"))
  (DEG:CFG-SET 'DD_DIRSEK_KACIS (DEGDO--dddz-store "dd_dirsek_kacis"))
  (DEG:CFG-SET 'DD_DZ_ORTHO "0")
  (DEG:SAVE-SETTINGS)
)

(defun DEGDO--reset-dd ()
  (DEG:CFG-SET 'DD_OFFSET "")
  (DEG:CFG-SET 'DD_AGIZ_ARAMA "")
  (DEG:CFG-SET 'DD_BLOK_YAKINLIK "")
  (DEG:CFG-SET 'DD_DIRSEK_DIST "")
  (DEG:CFG-SET 'DD_DIRSEK_KACIS "")
  (DEG:CFG-SET 'DD_DZ_ORTHO "0")
  (DEGDO--fill-dd)
)

(defun DEGDO--fill-df ()
  (set_tile "df_offset" (DEGDO--dddz-display 'DF_OFFSET))
  (set_tile "df_agiz_arama" (DEGDO--dddz-display-or 'DF_AGIZ_ARAMA 20.0))
  (set_tile "df_blok_yakinlik" (DEGDO--dddz-display-or 'DF_BLOK_YAKINLIK 100.0))
  (set_tile "df_dirsek_dist" (DEGDO--dddz-display-or 'DF_DIRSEK_DIST 200.0))
  (set_tile "df_dirsek_kacis" (DEGDO--dddz-display-or 'DF_DIRSEK_KACIS 50.0))
)

(defun DEGDO--save-df ()
  (DEG:CFG-SET 'DF_OFFSET (DEGDO--dddz-store "df_offset"))
  (DEG:CFG-SET 'DF_AGIZ_ARAMA (DEGDO--dddz-store "df_agiz_arama"))
  (DEG:CFG-SET 'DF_BLOK_YAKINLIK (DEGDO--dddz-store "df_blok_yakinlik"))
  (DEG:CFG-SET 'DF_DIRSEK_DIST (DEGDO--dddz-store "df_dirsek_dist"))
  (DEG:CFG-SET 'DF_DIRSEK_KACIS (DEGDO--dddz-store "df_dirsek_kacis"))
  (DEG:CFG-SET 'DD_DZ_ORTHO "0")
  (DEG:SAVE-SETTINGS)
)

(defun DEGDO--reset-df ()
  (DEG:CFG-SET 'DF_OFFSET "")
  (DEG:CFG-SET 'DF_AGIZ_ARAMA "")
  (DEG:CFG-SET 'DF_BLOK_YAKINLIK "")
  (DEG:CFG-SET 'DF_DIRSEK_DIST "")
  (DEG:CFG-SET 'DF_DIRSEK_KACIS "")
  (DEG:CFG-SET 'DD_DZ_ORTHO "0")
  (DEGDO--fill-df)
)

(defun DEGDO--fill-dz ()
  (set_tile "dz_offset" (DEGDO--dddz-display 'DZ_OFFSET))
  (set_tile "dz_agiz_arama" (DEGDO--dddz-display-or 'DZ_AGIZ_ARAMA 20.0))
  (set_tile "dz_blok_yakinlik" (DEGDO--dddz-display-or 'DZ_BLOK_YAKINLIK 100.0))
  (set_tile "dz_dirsek_dist" (DEGDO--dddz-display-or 'DZ_DIRSEK_DIST 200.0))
  (set_tile "dz_dirsek_kacis" (DEGDO--dddz-display-or 'DZ_DIRSEK_KACIS 50.0))
  (set_tile "dz_cocuk_hat_mesafe" (DEGDO--dddz-display-or 'DZ_COCUK_HAT_MESAFE 750.0))
)

(defun DEGDO--save-dz ()
  (DEG:CFG-SET 'DZ_OFFSET (DEGDO--dddz-store "dz_offset"))
  (DEG:CFG-SET 'DZ_AGIZ_ARAMA (DEGDO--dddz-store "dz_agiz_arama"))
  (DEG:CFG-SET 'DZ_BLOK_YAKINLIK (DEGDO--dddz-store "dz_blok_yakinlik"))
  (DEG:CFG-SET 'DZ_DIRSEK_DIST (DEGDO--dddz-store "dz_dirsek_dist"))
  (DEG:CFG-SET 'DZ_DIRSEK_KACIS (DEGDO--dddz-store "dz_dirsek_kacis"))
  (DEG:CFG-SET 'DZ_COCUK_HAT_MESAFE (DEGDO--dddz-store "dz_cocuk_hat_mesafe"))
  (DEG:CFG-SET 'DD_DZ_ORTHO "0")
  (DEG:SAVE-SETTINGS)
)

(defun DEGDO--reset-dz ()
  (DEG:CFG-SET 'DZ_OFFSET "")
  (DEG:CFG-SET 'DZ_AGIZ_ARAMA "")
  (DEG:CFG-SET 'DZ_BLOK_YAKINLIK "")
  (DEG:CFG-SET 'DZ_DIRSEK_DIST "")
  (DEG:CFG-SET 'DZ_DIRSEK_KACIS "")
  (DEG:CFG-SET 'DZ_COCUK_HAT_MESAFE "")
  (DEG:CFG-SET 'DD_DZ_ORTHO "0")
  (DEGDO--fill-dz)
)

(defun DEGDO--fill-dc ()
  (set_tile "dc_down_len" (DEG:CFG-GET 'DC_DOWN_LEN))
  (set_tile "dc_fillet_r" (DEG:CFG-GET 'DC_FILLET_R))
)

(defun DEGDO--save-dc ()
  (DEG:CFG-SET 'DC_DOWN_LEN (DEGDO--trim (get_tile "dc_down_len")))
  (DEG:CFG-SET 'DC_FILLET_R (DEGDO--trim (get_tile "dc_fillet_r")))
  (DEG:SAVE-SETTINGS)
)

(defun DEGDO--reset-dc ()
  (DEG:CFG-SET 'DC_DOWN_LEN "")
  (DEG:CFG-SET 'DC_FILLET_R "")
  (DEGDO--fill-dc)
)

(defun DEGDO--fill-plan (/ v idx)
  (start_list "plan_unit")
  (add_list "mm")
  (add_list "cm")
  (add_list "metre")
  (end_list)
  (setq v (strcase (DEGDO--trim (DEG:CFG-GET 'PLAN_UNIT))))
  (setq idx
    (cond
      ((= v "CM") 1)
      ((or (= v "METRE") (= v "M")) 2)
      (T 0)
    )
  )
  (set_tile "plan_unit" (itoa idx))
)

(defun DEGDO--save-plan (/ idx)
  (setq idx (atoi (get_tile "plan_unit")))
  (DEG:CFG-SET 'PLAN_UNIT
    (cond
      ((= idx 1) "cm")
      ((= idx 2) "metre")
      (T "mm")
    )
  )
  (DEG:SAVE-SETTINGS)
  (DEG:TOL-REFRESH-DN-GLOBALS)
)

(defun DEGDO--reset-plan ()
  (DEG:CFG-SET 'PLAN_UNIT "")
  (DEG:TOL-REFRESH-DN-GLOBALS)
  (DEGDO--fill-plan)
)

(defun DEGDO--fill-kayit ()
  (set_tile "kayit_path" (DEG:CFG-GET 'DO_KAYIT_PATH))
)

(defun DEGDO--save-kayit ()
  (DEG:CFG-SET 'DO_KAYIT_PATH (DEGDO--trim (get_tile "kayit_path")))
  (DEG:SAVE-SETTINGS)
)

(defun DEGDO--reset-kayit ()
  (DEG:CFG-SET 'DO_KAYIT_PATH "")
  (DEGDO--fill-kayit)
)

(defun DEGDO--browse-kayit (/ cur base pick)
  (setq cur (DEGDO--trim (get_tile "kayit_path")))
  (if (= cur "")
    (progn
      (setq base (getvar "DWGPREFIX"))
      (setq cur (if (and base (/= base "")) (strcat base "kayit.txt") "kayit.txt"))
    )
  )
  (setq pick (getfiled "Kayit dosya konumu sec" cur "" 1))
  (if pick
    (set_tile "kayit_path" pick)
  )
  (princ)
)

(defun DEGDO--csv-folder-from-path (raw / p ext dir)
  (setq p (DEGDO--trim raw))
  (cond
    ((= p "") nil)
    ((vl-file-directory-p p) p)
    ((setq ext (vl-filename-extension p))
      (setq dir (vl-filename-directory p))
      (if (and dir (/= dir "")) dir p)
    )
    (T p)
  )
)

(defun DEGDO--csv-folder (currentFolder pageName prompt / cfg)
  (setq cfg (DEGDO--csv-folder-from-path (DEG:CFG-GET 'DO_KAYIT_PATH)))
  (cond
    ((and cfg (/= cfg "")) cfg)
    (T nil)
  )
)

(defun DEGDO--csv-filepath (folder pageName)
  (if (or (null folder) (= folder ""))
    (strcat pageName ".csv")
    (strcat
      folder
      (if (or (= (substr folder (strlen folder) 1) "\\")
              (= (substr folder (strlen folder) 1) "/"))
        ""
        "\\")
      pageName
      ".csv")
  )
)

(defun DEGDO--dgt-color-acis ()
  '(1 2 3 4 5 6 7 8 9)
)

(defun DEGDO--dgt-color-labels ()
  '("1 - Kirmizi" "2 - Sari" "3 - Yesil" "4 - Cyan" "5 - Mavi" "6 - Magenta" "7 - Beyaz" "8 - Gri" "9 - Acik Gri")
)

(defun DEGDO--dgt-color-index (aci / lst idx n a)
  (setq lst (DEGDO--dgt-color-acis)
        idx 0
        n   0)
  (foreach a lst
    (if (= a aci) (setq idx n))
    (setq n (1+ n))
  )
  idx
)

(defun DEGDO--fill-dgt-color (tile key def / label)
  (start_list tile)
  (foreach label (DEGDO--dgt-color-labels)
    (add_list label)
  )
  (end_list)
  (set_tile tile (itoa (DEGDO--dgt-color-index (DEG:CFG-ACI-OR key def))))
)

(defun DEGDO--dgt-color-value (tile def / idx acis val)
  (setq idx  (atoi (get_tile tile))
        acis (DEGDO--dgt-color-acis)
        val  (nth idx acis))
  (if val (itoa val) (itoa def))
)

(defun DEGDO--fill-dgt ()
  (DEGDO--fill-dgt-color "dgt_chain_color"     'DGT_CHAIN_COLOR 1)
  (DEGDO--fill-dgt-color "dgt_tol_small_color" 'DGT_TOL_SMALL_COLOR 2)
  (DEGDO--fill-dgt-color "dgt_tol_big_color"   'DGT_TOL_BIG_COLOR 3)
  (DEGDO--fill-dgt-color "dgt_sorti_color"     'DGT_SORTI_COLOR 4)
  (DEGDO--fill-dgt-color "dgt_ref_color"       'DGT_REF_COLOR 7)
)

(defun DEGDO--save-dgt ()
  (DEG:CFG-SET 'DGT_CHAIN_COLOR     (DEGDO--dgt-color-value "dgt_chain_color" 1))
  (DEG:CFG-SET 'DGT_TOL_SMALL_COLOR (DEGDO--dgt-color-value "dgt_tol_small_color" 2))
  (DEG:CFG-SET 'DGT_TOL_BIG_COLOR   (DEGDO--dgt-color-value "dgt_tol_big_color" 3))
  (DEG:CFG-SET 'DGT_SORTI_COLOR     (DEGDO--dgt-color-value "dgt_sorti_color" 4))
  (DEG:CFG-SET 'DGT_REF_COLOR       (DEGDO--dgt-color-value "dgt_ref_color" 7))
  (DEG:SAVE-SETTINGS)
)

(defun DEGDO--reset-dgt ()
  (foreach k '(DGT_CHAIN_COLOR DGT_TOL_SMALL_COLOR DGT_TOL_BIG_COLOR DGT_SORTI_COLOR DGT_REF_COLOR)
    (DEG:CFG-SET k "")
  )
  (DEGDO--fill-dgt)
)

(defun DEGDO--apply-dt-layer-colors (/ rec)
  (foreach rec (DT--type-configs)
    (DT--ensure-layer (cadr rec) (nth 5 rec) nil)
    (DT--ensure-layer (DT--line-layer-name (cadr rec)) (nth 2 rec) nil)
  )
  (DT--repair-existing-model-hatch-colors)
  (DT--repair-existing-fitting-line-layers)
)

(defun DEGDO--fill-dt-color (tile idx / label)
  (start_list tile)
  (foreach label (DEGDO--dgt-color-labels)
    (add_list label)
  )
  (end_list)
  (set_tile tile (itoa (DEGDO--dgt-color-index (DT--type-color idx))))
)

(defun DEGDO--fill-dt-hatch-color (tile idx / label)
  (start_list tile)
  (foreach label (DEGDO--dgt-color-labels)
    (add_list label)
  )
  (end_list)
  (set_tile tile (itoa (DEGDO--dgt-color-index (DT--type-hatch-color idx))))
)

(defun DEGDO--text-style-names (/ rec name out)
  (setq rec (tblnext "STYLE" T)
        out nil)
  (while rec
    (setq name (cdr (assoc 2 rec)))
    (if (and name (/= (vl-string-trim " \t\r\n" name) ""))
      (setq out (cons name out))
    )
    (setq rec (tblnext "STYLE"))
  )
  (if (not (vl-some '(lambda (x) (= (strcase x) "STANDARD")) out))
    (setq out (cons "Standard" out))
  )
  (acad_strlsort out)
)

(defun DEGDO--string-index-ci (value items / target i found)
  (setq target (strcase (if value value ""))
        i 0)
  (while (and items (null found))
    (if (= target (strcase (car items)))
      (setq found i)
      (setq i (1+ i)
            items (cdr items))
    )
  )
  found
)

(defun DEGDO--dt-hatch-patterns ()
  '("SOLID" "HEX")
)

(defun DEGDO--fill-dt-hatch-pattern (tile idx / patterns wanted selected pattern)
  (setq patterns (DEGDO--dt-hatch-patterns)
        wanted   (DT--type-hatch-pattern idx)
        selected (DEGDO--string-index-ci wanted patterns))
  (start_list tile)
  (foreach pattern patterns (add_list pattern))
  (end_list)
  (set_tile tile (itoa (if selected selected 0)))
)

(defun DEGDO--dt-hatch-pattern-value (tile / patterns value)
  (setq patterns (DEGDO--dt-hatch-patterns)
        value    (nth (atoi (get_tile tile)) patterns))
  (if value value "SOLID")
)

(defun DEGDO--fill-dtt (/ wanted idx style)
  (set_tile "dtt_outside_gap" (DEGDO--dtt-display 'DTT_OUTSIDE_GAP))
  (set_tile "dtt_rect_width" (DEGDO--dtt-display 'DTT_RECT_WIDTH))
  (set_tile "dtt_rect_height" (DEGDO--dtt-display 'DTT_RECT_HEIGHT))
  (set_tile "dtt_att_text_height" (DEGDO--dtt-display 'DTT_ATT_TEXT_HEIGHT))
  (setq *DEGDO_DTT_TEXT_STYLES* (DEGDO--text-style-names))
  (start_list "dtt_att_text_style")
  (foreach style *DEGDO_DTT_TEXT_STYLES* (add_list style))
  (end_list)
  (setq wanted (DEG:CFG-GET 'DTT_ATT_TEXT_STYLE)
        idx (DEGDO--string-index-ci wanted *DEGDO_DTT_TEXT_STYLES*))
  (if (null idx)
    (setq idx (DEGDO--string-index-ci "Standard" *DEGDO_DTT_TEXT_STYLES*))
  )
  (set_tile "dtt_att_text_style" (itoa (if idx idx 0)))
)

(defun DEGDO--save-dtt (/ idx style)
  (DEG:CFG-SET 'DTT_OUTSIDE_GAP (DEGDO--dtt-store "dtt_outside_gap"))
  (DEG:CFG-SET 'DTT_RECT_WIDTH (DEGDO--dtt-store "dtt_rect_width"))
  (DEG:CFG-SET 'DTT_RECT_HEIGHT (DEGDO--dtt-store "dtt_rect_height"))
  (DEG:CFG-SET 'DTT_ATT_TEXT_HEIGHT (DEGDO--dtt-store "dtt_att_text_height"))
  (setq idx (atoi (get_tile "dtt_att_text_style"))
        style (nth idx *DEGDO_DTT_TEXT_STYLES*))
  (DEG:CFG-SET 'DTT_ATT_TEXT_STYLE (if style style "Standard"))
  (DEG:SAVE-SETTINGS)
)

(defun DEGDO--reset-dtt ()
  (foreach k '(DTT_OUTSIDE_GAP DTT_RECT_WIDTH DTT_RECT_HEIGHT DTT_ATT_TEXT_HEIGHT DTT_ATT_TEXT_STYLE)
    (DEG:CFG-SET k "")
  )
  (DEGDO--fill-dtt)
)
(defun DEGDO--fill-dt (/ i codeKey layerKey)
  (setq i 1)
  (while (<= i 7)
    (setq codeKey  (DT--type-key i "CODE")
          layerKey (DT--type-key i "LAYER"))
    (set_tile (strcat "dt_type" (itoa i) "_code") (DEG:CFG-GET codeKey))
    (set_tile (strcat "dt_type" (itoa i) "_layer") (DEG:CFG-GET layerKey))
    (DEGDO--fill-dt-color (strcat "dt_type" (itoa i) "_color") i)
    (DEGDO--fill-dt-hatch-pattern (strcat "dt_type" (itoa i) "_hatch_pattern") i)
    (DEGDO--fill-dt-hatch-color (strcat "dt_type" (itoa i) "_hatch_color") i)
    (set_tile (strcat "dt_type" (itoa i) "_hatch_scale") (DEG:NUM->STR (DT--type-hatch-scale i)))
    (setq i (1+ i))
  )
)
(defun DEGDO--save-dt (/ i code layer colorKey hatchPatternKey hatchColorKey hatchScaleKey hatchPattern hatchScale)
  (setq i 1)
  (while (<= i 7)
    (setq code
      (strcase
        (DEGDO--trim (get_tile (strcat "dt_type" (itoa i) "_code")))
      )
    )
    (setq layer
      (DEGDO--trim (get_tile (strcat "dt_type" (itoa i) "_layer")))
    )
    (setq hatchPattern
      (DEGDO--dt-hatch-pattern-value
        (strcat "dt_type" (itoa i) "_hatch_pattern")))
    (setq hatchScale
      (DEGDO--trim (get_tile (strcat "dt_type" (itoa i) "_hatch_scale")))
    )
    (setq colorKey        (DT--type-key i "COLOR")
          hatchPatternKey (DT--type-key i "HATCH_PATTERN")
          hatchColorKey   (DT--type-key i "HATCH_COLOR")
          hatchScaleKey   (DT--type-key i "HATCH_SCALE"))
    (DEG:CFG-SET (DT--type-key i "CODE") code)
    (DEG:CFG-SET (DT--type-key i "LAYER") layer)
    (DEG:CFG-SET colorKey
      (DEGDO--dgt-color-value
        (strcat "dt_type" (itoa i) "_color")
        (DT--type-color-default i)
      )
    )
    (DEG:CFG-SET hatchPatternKey hatchPattern)
    (DEG:CFG-SET hatchColorKey
      (DEGDO--dgt-color-value
        (strcat "dt_type" (itoa i) "_hatch_color")
        (DT--type-hatch-color-default i)
      )
    )
    (DEG:CFG-SET hatchScaleKey hatchScale)
    (if (= i 1) (DEG:CFG-SET 'DT_KA_COLOR (DEG:CFG-GET colorKey)))
    (if (= i 2) (DEG:CFG-SET 'DT_ZA_COLOR (DEG:CFG-GET colorKey)))
    (setq i (1+ i))
  )
  (DEG:SAVE-SETTINGS)
  (DEGDO--apply-dt-layer-colors)
  (DT--remember-mode (DT--last-mode))
)
(defun DEGDO--reset-dt (/ i)
  (setq i 1)
  (while (<= i 7)
    (DEG:CFG-SET (DT--type-key i "CODE") "")
    (DEG:CFG-SET (DT--type-key i "LAYER") "")
    (DEG:CFG-SET (DT--type-key i "COLOR") "")
    (DEG:CFG-SET (DT--type-key i "HATCH_PATTERN") "")
    (DEG:CFG-SET (DT--type-key i "HATCH_COLOR") "")
    (DEG:CFG-SET (DT--type-key i "HATCH_SCALE") "")
    (setq i (1+ i))
  )
  (DEGDO--fill-dt)
  (DEGDO--apply-dt-layer-colors)
)
(defun DEGDO--fill-dp (/ vals idx lay)
  (if (null *DEGDO_DP_E_LAYERS*)
    (setq *DEGDO_DP_E_LAYERS* (DEGDO--plan-e-line-layer-list))
  )
  (setq vals (DEGDO--dp-e-values-alist)
        idx  1)
  (foreach lay *DEGDO_DP_E_LAYERS*
    (set_tile (strcat "dp_e_qty_" (itoa idx)) (DEGDO--dp-e-value-get vals lay))
    (setq idx (1+ idx))
  )
  (set_tile "dp_light_line" (DEGDO--join-layers (DEGP--dp-lighting-line-layers)))
  (set_tile "dp_light_comb" (DEGDO--join-layers (DEGP--dp-lighting-comb-layers)))
  (set_tile "dp_data_line" (DEGDO--join-layers (DEGP--dp-data-line-layers)))
  (set_tile "dp_data_comb" (DEGDO--join-layers (DEGP--dp-data-comb-layers)))
  (set_tile "dp_kombine_line" (DEGDO--codes-merged '(D1 D2)))
  (set_tile "dp_kombine_comb" (DEGDO--codes-merged '(D3 D4)))
)

(defun DEGDO--save-dp (/ idx lay val out)
  (if (null *DEGDO_DP_E_LAYERS*)
    (setq *DEGDO_DP_E_LAYERS* (DEGDO--plan-e-line-layer-list))
  )
  (setq idx 1
        out nil)
  (foreach lay *DEGDO_DP_E_LAYERS*
    (setq val (DEGDO--trim (get_tile (strcat "dp_e_qty_" (itoa idx)))))
    (if (/= val "")
      (setq out (append out (list (cons lay val))))
    )
    (setq idx (1+ idx))
  )
  (DEG:CFG-SET 'DP_E_LINE_VALUES  (DEGDO--dp-e-values-pack out))
  (DEG:CFG-SET 'DP_LIGHTING_LINE_LAYERS (DEGDO--trim (get_tile "dp_light_line")))
  (DEG:CFG-SET 'DP_LIGHTING_COMB_LAYERS (DEGDO--trim (get_tile "dp_light_comb")))
  (DEG:CFG-SET 'DP_DATA_LINE_LAYERS (DEGDO--trim (get_tile "dp_data_line")))
  (DEG:CFG-SET 'DP_DATA_COMB_LAYERS (DEGDO--trim (get_tile "dp_data_comb")))
  (DEG:SET 'D1 (DEGDO--trim (get_tile "dp_kombine_line")))
  (DEG:SET 'D2 "")
  (DEG:SET 'D3 (DEGDO--trim (get_tile "dp_kombine_comb")))
  (DEG:SET 'D4 "")
  (DEG:SAVE-SETTINGS)
)

(defun DEGDO--reset-dp ()
  (DEG:CFG-SET 'DP_E_LINE_VALUES "")
  (DEG:CFG-SET 'DP_LIGHTING_LINE_LAYERS "E_AYDINLATMA_LINYE,E_LIGHTING_LINE,E_AYDINLATMA_KNX_HATTI,E_AYDINLATMA_BUTON_HATTI,E_ANAHTAR_HATTI,E_ACIL_AYDINLATMA_KIT_SINYAL_HATTI")
  (DEG:CFG-SET 'DP_LIGHTING_COMB_LAYERS "E_AYDINLATMA_LINYE_KOMBINE,E_LIGHTING_MULTI_LINE")
  (DEG:CFG-SET 'DP_DATA_LINE_LAYERS "E_DATA_HATTI,E_DATA_LINE")
  (DEG:CFG-SET 'DP_DATA_COMB_LAYERS "E_DATA_MULTI_LINE,E_DATA_KOMBINE_HATTI")
  (foreach k '(D1 D2 D3 D4)
    (DEG:SET k "")
  )
  (DEGDO--fill-dp)
)

(defun DEGDO--fill-blocklar (/ bvals bidx blk)
  (if (null *DEGDO_DP_E_BLOCKS*)
    (setq *DEGDO_DP_E_BLOCKS* (DEGDO--plan-e-block-list))
  )
  (setq bvals (DEGDO--dp-e-block-values-alist)
        bidx  1)
  (foreach blk *DEGDO_DP_E_BLOCKS*
    (set_tile (strcat "dp_e_blk_data_" (itoa bidx)) (DEGDO--dp-e-block-value-get bvals blk 0))
    (set_tile (strcat "dp_e_blk_tel_"  (itoa bidx)) (DEGDO--dp-e-block-value-get bvals blk 1))
    (set_tile (strcat "dp_e_blk_tv_"   (itoa bidx)) (DEGDO--dp-e-block-value-get bvals blk 2))
    (setq bidx (1+ bidx))
  )
)

(defun DEGDO--save-blocklar (/ bidx blk data tel tv bout)
  (if (null *DEGDO_DP_E_BLOCKS*)
    (setq *DEGDO_DP_E_BLOCKS* (DEGDO--plan-e-block-list))
  )
  (setq bidx 1
        bout nil)
  (foreach blk *DEGDO_DP_E_BLOCKS*
    (setq data (DEGDO--trim (get_tile (strcat "dp_e_blk_data_" (itoa bidx))))
          tel  (DEGDO--trim (get_tile (strcat "dp_e_blk_tel_"  (itoa bidx))))
          tv   (DEGDO--trim (get_tile (strcat "dp_e_blk_tv_"   (itoa bidx)))))
    (if (or (/= data "") (/= tel "") (/= tv ""))
      (setq bout (append bout (list (list blk data tel tv))))
    )
    (setq bidx (1+ bidx))
  )
  (DEG:CFG-SET 'DP_E_BLOCK_VALUES (DEGDO--dp-e-block-values-pack bout))
  (DEG:SAVE-SETTINGS)
)

(defun DEGDO--reset-blocklar ()
  (DEG:CFG-SET 'DP_E_BLOCK_VALUES "")
  (DEGDO--fill-blocklar)
)

(defun DEGDO--fill-tol ()
  (set_tile "dg_knx_start_tol" (DEGDO--tol-display 'DG_KNX_START_TOL))
  (set_tile "dg_knx_block_tol" (DEGDO--tol-display 'DG_KNX_BLOCK_TOL))
  (set_tile "dg_knx_end_tol"   (DEGDO--tol-display 'DG_KNX_END_TOL))
  (set_tile "dg_ref_tol"       (DEGDO--tol-display 'DG_REF_TOL))
  (set_tile "dg_chain_tol"     (DEGDO--tol-display 'DG_CHAIN_TOL))
  (set_tile "dg_report_tol"    (DEGDO--tol-display 'DG_REPORT_TOL))
  (set_tile "dg_ref_dal_tol"   (DEGDO--tol-display 'DG_REF_DAL_TOL))
  (set_tile "dg_dal_single_tol" (DEGDO--tol-display 'DG_DAL_SINGLE_TOL))
  (set_tile "dg_p1_tol"        (DEGDO--tol-display 'DG_P1_TOL))
  (set_tile "dn_chain_tol"     (DEGDO--tol-display 'DN_CHAIN_TOL))
  (set_tile "dn_block_tol"     (DEGDO--tol-display 'DN_BLOCK_TOL))
  (set_tile "dn_doseme_tol"    (DEGDO--tol-display 'DN_DOSEME_TOL))
  (set_tile "dn_modl_tol"      (DEGDO--tol-display 'DN_MODL_TOL))
  (set_tile "dw_touch_tol"     (DEGDO--tol-display 'DW_TOUCH_TOL))
  (set_tile "dr_tree_tol"      (DEGDO--tol-display 'DR_TREE_TOL))
)

(defun DEGDO--save-tol ()
  (DEG:CFG-SET 'DG_KNX_START_TOL (DEGDO--tol-store "dg_knx_start_tol"))
  (DEG:CFG-SET 'DG_KNX_BLOCK_TOL (DEGDO--tol-store "dg_knx_block_tol"))
  (DEG:CFG-SET 'DG_KNX_END_TOL (DEGDO--tol-store "dg_knx_end_tol"))
  (DEG:CFG-SET 'DG_REF_TOL (DEGDO--tol-store "dg_ref_tol"))
  (DEG:CFG-SET 'DG_CHAIN_TOL (DEGDO--tol-store "dg_chain_tol"))
  (DEG:CFG-SET 'DG_REPORT_TOL (DEGDO--tol-store "dg_report_tol"))
  (DEG:CFG-SET 'DG_REF_DAL_TOL (DEGDO--tol-store "dg_ref_dal_tol"))
  (DEG:CFG-SET 'DG_DAL_SINGLE_TOL (DEGDO--tol-store "dg_dal_single_tol"))
  (DEG:CFG-SET 'DG_P1_TOL (DEGDO--tol-store "dg_p1_tol"))
  (DEG:CFG-SET 'DN_CHAIN_TOL (DEGDO--tol-store "dn_chain_tol"))
  (DEG:CFG-SET 'DN_BLOCK_TOL (DEGDO--tol-store "dn_block_tol"))
  (DEG:CFG-SET 'DK_TOUCH_TOL (DEGDO--tol-store "dn_block_tol"))
  (DEG:CFG-SET 'DKX_TOUCH_TOL (DEGDO--tol-store "dn_block_tol"))
  (DEG:CFG-SET 'DN_DOSEME_TOL (DEGDO--tol-store "dn_doseme_tol"))
  (DEG:CFG-SET 'DN_MODL_TOL (DEGDO--tol-store "dn_modl_tol"))
  (DEG:CFG-SET 'DW_TOUCH_TOL (DEGDO--tol-store "dw_touch_tol"))
  (DEG:CFG-SET 'DR_TREE_TOL (DEGDO--tol-store "dr_tree_tol"))
  (DEG:TOL-REFRESH-DN-GLOBALS)
  (DEG:SAVE-SETTINGS)
)

(defun DEGDO--reset-tol ()
  (foreach k '(DG_KNX_START_TOL DG_KNX_BLOCK_TOL DG_KNX_END_TOL DG_REF_TOL DG_CHAIN_TOL DG_REPORT_TOL DG_REF_DAL_TOL DG_DAL_SINGLE_TOL DG_P1_TOL DK_TOUCH_TOL DKX_TOUCH_TOL DN_CHAIN_TOL DN_BLOCK_TOL DN_DOSEME_TOL DN_MODL_TOL DW_TOUCH_TOL DR_TREE_TOL)
    (DEG:CFG-SET k "")
  )
  (DEG:TOL-REFRESH-DN-GLOBALS)
  (DEGDO--fill-tol)
)

(defun DEGDO--fill-dk ()
  (set_tile "dk_normal_area_layers" (DEG:CFG-GET 'DK_NORMAL_AREA_LAYERS))
  (set_tile "dk_combined_riser_layers" (DEG:CFG-GET 'DK_COMBINED_RISER_LAYERS))
  (set_tile "dk_normal_group_spacing" (DEGDO--dk-display 'DK_NORMAL_GROUP_SPACING))
  (set_tile "dk_normal_floor_spacing" (DEGDO--dk-display 'DK_NORMAL_FLOOR_SPACING))
  (set_tile "dk_data_layers"    (DEGDO--codes-merged '(C1 C2 C3 C4)))
  (set_tile "dk_data_pattern"   (DEGDO--codes-merged '(C9)))
  (set_tile "dk_data_keyword"   (DEGDO--codes-merged '(C10)))
  (set_tile "dkx_data_shift_y" (DEGDO--dk-display 'DKX_DATA_SHIFT_Y))
  (set_tile "dkx_data_shift_blocks" (DEG:CFG-GET 'DKX_DATA_SHIFT_BLOCKS))
  (set_tile "dk_cctv_layers"    (DEGDO--codes-merged '(D1 D2 D3 D4)))
  (set_tile "dk_cctv_pattern"   (DEGDO--codes-merged '(D5)))
  (set_tile "dk_cctv_keyword"   (DEGDO--codes-merged '(D6)))
  (set_tile "dk_kolon_no_layer" (DEGDO--codes-merged '(O1)))
  (set_tile "dk_kolon_sembol_layer" (DEGDO--codes-merged '(O2)))
  (set_tile "dk_doseme_block"   (DEGDO--codes-merged '(M1)))
  (set_tile "dk_doseme_patterns" (DEGDO--codes-merged '(M2 M3 M4)))
  (set_tile "dk_ignore_pattern" (DEGDO--codes-merged '(N2)))
  (set_tile "dk_terminal_keywords" (DEGDO--codes-merged '(L1 L2)))
  (set_tile "dk_copy_spacing"    (DEGDO--dk-display 'DK_COPY_SPACING))
  (set_tile "dk_text_height"     (DEGDO--dk-display 'DK_TEXT_HEIGHT))
  (set_tile "dk_text_offset_y"   (DEGDO--dk-display 'DK_TEXT_OFFSET_Y))
  (set_tile "dk_under_x1"        (DEGDO--dk-display 'DK_UNDER_X1))
  (set_tile "dk_under_x2"        (DEGDO--dk-display 'DK_UNDER_X2))
  (set_tile "dk_under_w"         (DEGDO--dk-display 'DK_UNDER_W))
  (set_tile "dk_under_h"         (DEGDO--dk-display 'DK_UNDER_H))
  (set_tile "dk_under_y_offset" (DEGDO--dk-display 'DK_UNDER_Y_OFFSET))
  (set_tile "dk_loop_text_height"   (DEGDO--dk-display 'DK_LOOP_TEXT_HEIGHT))
  (set_tile "dk_loop_text_x_offset" (DEGDO--dk-display 'DK_LOOP_TEXT_X_OFFSET))
  (set_tile "dk_loop_text_y_margin" (DEGDO--dk-display 'DK_LOOP_TEXT_Y_MARGIN))
  (set_tile "dk_loop_line_shift_x"  (DEGDO--dk-display 'DK_LOOP_LINE_SHIFT_X))
  (set_tile "dk_loop_line_rise"     (DEGDO--dk-display 'DK_LOOP_LINE_RISE))
  (set_tile "dk_loop_line_run"      (DEGDO--dk-display 'DK_LOOP_LINE_RUN))
  (set_tile "dk_loop_mark_length"   (DEGDO--dk-display 'DK_LOOP_MARK_LENGTH))
  (set_tile "dkx_copy_spacing"   (DEGDO--dk-display 'DKX_COPY_SPACING))
  (set_tile "dkx_firststart_x"   (DEGDO--dk-display 'DKX_FIRSTSTART_X))
  (set_tile "dkx_firststart_y"   (DEGDO--dk-display 'DKX_FIRSTSTART_Y))
  (set_tile "dkx_lastbottom_x"   (DEGDO--dk-display 'DKX_LASTBOTTOM_X))
  (set_tile "dkx_lastbottom_y"   (DEGDO--dk-display 'DKX_LASTBOTTOM_Y))
  (set_tile "dkx_text_offset_y"  (DEGDO--dk-display 'DKX_TEXT_OFFSET_Y))
  (set_tile "dkx_text_height"    (DEGDO--dk-display 'DKX_TEXT_HEIGHT))
  (set_tile "dkx_multi_dx"       (DEGDO--dk-display 'DKX_MULTI_DX))
  (set_tile "dkx_multi_drop_y"   (DEGDO--dk-display 'DKX_MULTI_DROP_Y))
  (set_tile "dkx_vlen_main"      (DEGDO--dk-display 'DKX_VLEN_MAIN))
  (set_tile "dkx_vlen_secondary" (DEGDO--dk-display 'DKX_VLEN_SECONDARY))
  (set_tile "dkx_hlen_default"   (DEGDO--dk-display 'DKX_HLEN_DEFAULT))
  (set_tile "dkx_hlen_last2"     (DEGDO--dk-display 'DKX_HLEN_LAST2))
  (set_tile "dkx_hlen_last3_left"  (DEGDO--dk-display 'DKX_HLEN_LAST3_LEFT))
  (set_tile "dkx_hlen_last3_right" (DEGDO--dk-display 'DKX_HLEN_LAST3_RIGHT))
)

(defun DEGDO--dk-set-group (codes tile / k)
  (if codes
    (progn
      (DEG:SET (car codes) (DEGDO--trim (get_tile tile)))
      (foreach k (cdr codes) (DEG:SET k ""))
    )
  )
)

(defun DEGDO--save-dk ()
  (DEG:CFG-SET 'DK_NORMAL_AREA_LAYERS (DEGDO--trim (get_tile "dk_normal_area_layers")))
  (DEG:CFG-SET 'DK_COMBINED_RISER_LAYERS (DEGDO--trim (get_tile "dk_combined_riser_layers")))
  (DEG:CFG-SET 'DK_NORMAL_GROUP_SPACING (DEGDO--dk-store "dk_normal_group_spacing"))
  (DEG:CFG-SET 'DK_NORMAL_FLOOR_SPACING (DEGDO--dk-store "dk_normal_floor_spacing"))
  (DEGDO--dk-set-group '(C1 C2 C3 C4) "dk_data_layers")
  (DEGDO--dk-set-group '(C9) "dk_data_pattern")
  (DEGDO--dk-set-group '(C10) "dk_data_keyword")
  (DEG:CFG-SET 'DKX_DATA_SHIFT_Y (DEGDO--dk-store "dkx_data_shift_y"))
  (DEG:CFG-SET 'DKX_DATA_SHIFT_BLOCKS (DEGDO--trim (get_tile "dkx_data_shift_blocks")))
  (DEGDO--dk-set-group '(D1 D2 D3 D4) "dk_cctv_layers")
  (DEGDO--dk-set-group '(D5) "dk_cctv_pattern")
  (DEGDO--dk-set-group '(D6) "dk_cctv_keyword")
  (DEGDO--dk-set-group '(O1) "dk_kolon_no_layer")
  (DEGDO--dk-set-group '(O2) "dk_kolon_sembol_layer")
  (DEGDO--dk-set-group '(M1) "dk_doseme_block")
  (DEGDO--dk-set-group '(M2 M3 M4) "dk_doseme_patterns")
  (DEGDO--dk-set-group '(N2) "dk_ignore_pattern")
  (DEGDO--dk-set-group '(L1 L2) "dk_terminal_keywords")
  (DEG:CFG-SET 'DK_COPY_SPACING   (DEGDO--dk-store "dk_copy_spacing"))
  (DEG:CFG-SET 'DK_TEXT_HEIGHT    (DEGDO--dk-store "dk_text_height"))
  (DEG:CFG-SET 'DK_TEXT_OFFSET_Y  (DEGDO--dk-store "dk_text_offset_y"))
  (DEG:CFG-SET 'DK_UNDER_X1       (DEGDO--dk-store "dk_under_x1"))
  (DEG:CFG-SET 'DK_UNDER_X2       (DEGDO--dk-store "dk_under_x2"))
  (DEG:CFG-SET 'DK_UNDER_W        (DEGDO--dk-store "dk_under_w"))
  (DEG:CFG-SET 'DK_UNDER_H        (DEGDO--dk-store "dk_under_h"))
  (DEG:CFG-SET 'DK_UNDER_Y_OFFSET (DEGDO--dk-store "dk_under_y_offset"))
  (DEG:CFG-SET 'DK_LOOP_TEXT_HEIGHT   (DEGDO--dk-store "dk_loop_text_height"))
  (DEG:CFG-SET 'DK_LOOP_TEXT_X_OFFSET (DEGDO--dk-store "dk_loop_text_x_offset"))
  (DEG:CFG-SET 'DK_LOOP_TEXT_Y_MARGIN (DEGDO--dk-store "dk_loop_text_y_margin"))
  (DEG:CFG-SET 'DK_LOOP_LINE_SHIFT_X  (DEGDO--dk-store "dk_loop_line_shift_x"))
  (DEG:CFG-SET 'DK_LOOP_LINE_RISE     (DEGDO--dk-store "dk_loop_line_rise"))
  (DEG:CFG-SET 'DK_LOOP_LINE_RUN      (DEGDO--dk-store "dk_loop_line_run"))
  (DEG:CFG-SET 'DK_LOOP_MARK_LENGTH   (DEGDO--dk-store "dk_loop_mark_length"))
  (DEG:CFG-SET 'DKX_COPY_SPACING   (DEGDO--dk-store "dkx_copy_spacing"))
  (DEG:CFG-SET 'DKX_FIRSTSTART_X   (DEGDO--dk-store "dkx_firststart_x"))
  (DEG:CFG-SET 'DKX_FIRSTSTART_Y   (DEGDO--dk-store "dkx_firststart_y"))
  (DEG:CFG-SET 'DKX_LASTBOTTOM_X   (DEGDO--dk-store "dkx_lastbottom_x"))
  (DEG:CFG-SET 'DKX_LASTBOTTOM_Y   (DEGDO--dk-store "dkx_lastbottom_y"))
  (DEG:CFG-SET 'DKX_TEXT_OFFSET_Y  (DEGDO--dk-store "dkx_text_offset_y"))
  (DEG:CFG-SET 'DKX_TEXT_HEIGHT    (DEGDO--dk-store "dkx_text_height"))
  (DEG:CFG-SET 'DKX_MULTI_DX       (DEGDO--dk-store "dkx_multi_dx"))
  (DEG:CFG-SET 'DKX_MULTI_DROP_Y   (DEGDO--dk-store "dkx_multi_drop_y"))
  (DEG:CFG-SET 'DKX_VLEN_MAIN      (DEGDO--dk-store "dkx_vlen_main"))
  (DEG:CFG-SET 'DKX_VLEN_SECONDARY (DEGDO--dk-store "dkx_vlen_secondary"))
  (DEG:CFG-SET 'DKX_HLEN_DEFAULT   (DEGDO--dk-store "dkx_hlen_default"))
  (DEG:CFG-SET 'DKX_HLEN_LAST2     (DEGDO--dk-store "dkx_hlen_last2"))
  (DEG:CFG-SET 'DKX_HLEN_LAST3_LEFT  (DEGDO--dk-store "dkx_hlen_last3_left"))
  (DEG:CFG-SET 'DKX_HLEN_LAST3_RIGHT (DEGDO--dk-store "dkx_hlen_last3_right"))
  (DEG:SAVE-SETTINGS)
)

(defun DEGDO--reset-dk ()
  (foreach k '(C1 C2 C3 C4 C9 C10 D1 D2 D3 D4 D5 D6 O1 O2 M1 M2 M3 M4 N2 L1 L2)
    (DEG:SET k "")
  )
  (foreach k '(DK_NORMAL_AREA_LAYERS DK_COMBINED_RISER_LAYERS DK_NORMAL_GROUP_SPACING DK_NORMAL_FLOOR_SPACING
               DK_COPY_SPACING DK_UNDER_X1 DK_UNDER_X2 DK_UNDER_W DK_UNDER_H DK_TEXT_HEIGHT DK_TEXT_OFFSET_Y DK_UNDER_Y_OFFSET
               DK_LOOP_TEXT_HEIGHT DK_LOOP_TEXT_X_OFFSET DK_LOOP_TEXT_Y_MARGIN
               DK_LOOP_LINE_SHIFT_X DK_LOOP_LINE_RISE DK_LOOP_LINE_RUN DK_LOOP_MARK_LENGTH
               DKX_COPY_SPACING DKX_FIRSTSTART_X DKX_FIRSTSTART_Y
               DKX_LASTBOTTOM_X DKX_LASTBOTTOM_Y DKX_TEXT_OFFSET_Y DKX_TEXT_HEIGHT
               DKX_MULTI_DX DKX_MULTI_DROP_Y DKX_VLEN_MAIN DKX_VLEN_SECONDARY
               DKX_HLEN_DEFAULT DKX_HLEN_LAST2 DKX_HLEN_LAST3_LEFT DKX_HLEN_LAST3_RIGHT
               DKX_DATA_SHIFT_Y DKX_DATA_SHIFT_BLOCKS)
    (DEG:CFG-SET k "")
  )
  (DEGDO--fill-dk)
)

(defun DEGDO--dn-cfg-or-codes (key codes / s)
  (setq s (DEGDO--trim (DEG:CFG-GET key)))
  (if (/= s "") s (DEGDO--codes-merged codes))
)

(defun DEGDO--dn-cfg-or-mix (key codes extra / s base)
  (setq s (DEGDO--trim (DEG:CFG-GET key)))
  (if (/= s "")
    s
    (progn
      (setq base (DEGDO--codes-merged codes))
      (if (= (DEGDO--trim extra) "")
        base
        (if (= base "") extra (strcat base "," extra))
      )
    )
  )
)

(defun DEGDO--fill-dn ()
  (set_tile "dn_data_pattern"    (DEGDO--codes-merged '(C9)))
  (set_tile "dn_cctv_layers"     (DEGDO--codes-merged '(D1 D2 D3 D4)))
  (set_tile "dn_cctv_pattern"    (DEGDO--codes-merged '(D5)))
  (set_tile "dn_cctv_keyword"    (DEGDO--codes-merged '(D6)))
  (set_tile "dn_tel_pattern"     (DEGDO--codes-merged '(E4)))
  (set_tile "dn_tv_pattern"      (DEGDO--codes-merged '(F5)))
  (set_tile "dn_kartli_pattern"  (DEGDO--codes-merged '(H5)))
  (set_tile "dn_doseme_block"    (DEGDO--codes-merged '(M1)))
  (set_tile "dn_doseme_patterns" (DEGDO--codes-merged '(M2 M3 M4)))
  (set_tile "dn_not_block"       (DEGDO--codes-merged '(N1)))
  (set_tile "dn_ignore_pattern"  (DEGDO--codes-merged '(N2)))
  (set_tile "dn_kolon_no_layer"  (DEGDO--codes-merged '(O1)))
  (set_tile "dn_kolon_sembol_layer" (DEGDO--codes-merged '(O2)))
  (set_tile "dn_buat_blocks"     (DEGDO--codes-merged '(I1 I2)))
  (set_tile "dn_buat_patterns"   (DEGDO--codes-merged '(I3 I4)))
  (set_tile "dn_pano_blocks"     (DEGDO--codes-merged '(J1 J2 J3)))
  (set_tile "dn_pano_pattern"    (DEGDO--codes-merged '(J4)))
  (set_tile "dn_linye_block"     (DEGDO--codes-merged '(P1)))
  (set_tile "dn_mahal_block"     (DEGDO--codes-merged '(P2)))
  (set_tile "dn_flasor_layer"    (DEGDO--codes-merged '(K1)))
  (set_tile "dn_yangin_blocks"   (DEGDO--codes-merged '(K2 K3 K4 K5 K6 K7 K18 K19)))
  (set_tile "dn_yangin_patterns" (DEGDO--codes-merged '(K8 K9 K10 K11 K12 K13 K14 K15)))
  (set_tile "dn_flasor_keywords" (DEGDO--codes-merged '(K16 K17)))
  (set_tile "dn_terminal_keywords" (DEGDO--codes-merged '(L1 L2)))
  (set_tile "dn_skip_blocks" (DEGDO--dn-cfg-or-codes 'DN_SKIP_BLOCKS '(K5 K18 K3 K4)))
  (set_tile "dn_skip_layer_patterns" (DEGDO--dn-cfg-or-mix 'DN_SKIP_LAYER_PATTERNS '(K13 K14 K15) "*KARBONMONOKSIT*"))
  (set_tile "dn_skip_layer_blocks" (DEGDO--dn-cfg-or-codes 'DN_SKIP_LAYER_BLOCKS '(K6 K19)))
  (set_tile "dn_filter_ignore_blocks" (DEGDO--dn-cfg-or-codes 'DN_FILTER_IGNORE_BLOCKS '(N1 K2 N2)))
  (set_tile "dn_filter_co_layers" (DEGDO--dn-cfg-or-codes 'DN_FILTER_CO_LAYER_PATTERNS '(K8)))
  (set_tile "dn_filter_co_blocks" (DEGDO--dn-cfg-or-codes 'DN_FILTER_CO_BLOCKS '(K7)))
  (set_tile "dn_filter_flasor_layers" (DEGDO--dn-cfg-or-codes 'DN_FILTER_FLASOR_LAYERS '(K1)))
  (set_tile "dn_filter_flasor_blocks" (DEGDO--dn-cfg-or-codes 'DN_FILTER_FLASOR_BLOCKS '(K12)))
  (set_tile "dn_filter_sound_layers" (DEGDO--dn-cfg-or-codes 'DN_FILTER_SOUND_LAYER_PATTERNS '(K13 K14 K15)))
  (set_tile "dn_filter_sound_blocks" (DEGDO--dn-cfg-or-codes 'DN_FILTER_SOUND_BLOCK_PATTERNS '(K13 K14 K15)))
  (set_tile "dn_filter_fire_layers" (DEGDO--dn-cfg-or-codes 'DN_FILTER_FIRE_LAYER_PATTERNS '(K11 K10 K9)))
  (set_tile "dn_filter_fire_exclude_blocks" (DEGDO--dn-cfg-or-codes 'DN_FILTER_FIRE_BLOCK_EXCLUDES '(K13 K14 K15)))
)

(defun DEGDO--dn-set-group (codes tile / k)
  (if codes
    (progn
      (DEG:SET (car codes) (DEGDO--trim (get_tile tile)))
      (foreach k (cdr codes) (DEG:SET k ""))
    )
  )
)

(defun DEGDO--save-dn ()
  (DEGDO--dn-set-group '(C9) "dn_data_pattern")
  (DEGDO--dn-set-group '(D1 D2 D3 D4) "dn_cctv_layers")
  (DEGDO--dn-set-group '(D5) "dn_cctv_pattern")
  (DEGDO--dn-set-group '(D6) "dn_cctv_keyword")
  (DEGDO--dn-set-group '(E4) "dn_tel_pattern")
  (DEGDO--dn-set-group '(F5) "dn_tv_pattern")
  (DEGDO--dn-set-group '(H5) "dn_kartli_pattern")
  (DEGDO--dn-set-group '(M1) "dn_doseme_block")
  (DEGDO--dn-set-group '(M2 M3 M4) "dn_doseme_patterns")
  (DEGDO--dn-set-group '(N1) "dn_not_block")
  (DEGDO--dn-set-group '(N2) "dn_ignore_pattern")
  (DEGDO--dn-set-group '(O1) "dn_kolon_no_layer")
  (DEGDO--dn-set-group '(O2) "dn_kolon_sembol_layer")
  (DEGDO--dn-set-group '(I1 I2) "dn_buat_blocks")
  (DEGDO--dn-set-group '(I3 I4) "dn_buat_patterns")
  (DEGDO--dn-set-group '(J1 J2 J3) "dn_pano_blocks")
  (DEGDO--dn-set-group '(J4) "dn_pano_pattern")
  (DEGDO--dn-set-group '(P1) "dn_linye_block")
  (DEGDO--dn-set-group '(P2) "dn_mahal_block")
  (DEGDO--dn-set-group '(K1) "dn_flasor_layer")
  (DEGDO--dn-set-group '(K2 K3 K4 K5 K6 K7 K18 K19) "dn_yangin_blocks")
  (DEGDO--dn-set-group '(K8 K9 K10 K11 K12 K13 K14 K15) "dn_yangin_patterns")
  (DEGDO--dn-set-group '(K16 K17) "dn_flasor_keywords")
  (DEGDO--dn-set-group '(L1 L2) "dn_terminal_keywords")
  (DEG:CFG-SET 'DN_SKIP_BLOCKS (DEGDO--trim (get_tile "dn_skip_blocks")))
  (DEG:CFG-SET 'DN_SKIP_LAYER_PATTERNS (DEGDO--trim (get_tile "dn_skip_layer_patterns")))
  (DEG:CFG-SET 'DN_SKIP_LAYER_BLOCKS (DEGDO--trim (get_tile "dn_skip_layer_blocks")))
  (DEG:CFG-SET 'DN_FILTER_IGNORE_BLOCKS (DEGDO--trim (get_tile "dn_filter_ignore_blocks")))
  (DEG:CFG-SET 'DN_FILTER_CO_LAYER_PATTERNS (DEGDO--trim (get_tile "dn_filter_co_layers")))
  (DEG:CFG-SET 'DN_FILTER_CO_BLOCKS (DEGDO--trim (get_tile "dn_filter_co_blocks")))
  (DEG:CFG-SET 'DN_FILTER_FLASOR_LAYERS (DEGDO--trim (get_tile "dn_filter_flasor_layers")))
  (DEG:CFG-SET 'DN_FILTER_FLASOR_BLOCKS (DEGDO--trim (get_tile "dn_filter_flasor_blocks")))
  (DEG:CFG-SET 'DN_FILTER_SOUND_LAYER_PATTERNS (DEGDO--trim (get_tile "dn_filter_sound_layers")))
  (DEG:CFG-SET 'DN_FILTER_SOUND_BLOCK_PATTERNS (DEGDO--trim (get_tile "dn_filter_sound_blocks")))
  (DEG:CFG-SET 'DN_FILTER_FIRE_LAYER_PATTERNS (DEGDO--trim (get_tile "dn_filter_fire_layers")))
  (DEG:CFG-SET 'DN_FILTER_FIRE_BLOCK_EXCLUDES (DEGDO--trim (get_tile "dn_filter_fire_exclude_blocks")))
  (DEG:SAVE-SETTINGS)
)

(defun DEGDO--reset-dn ()
  (foreach k '(C9 D1 D2 D3 D4 D5 D6 E4 F5 H5 M1 M2 M3 M4 N1 N2 O1 O2 I1 I2 I3 I4 J1 J2 J3 J4 P1 P2 K1 K2 K3 K4 K5 K6 K7 K8 K9 K10 K11 K12 K13 K14 K15 K16 K17 K18 K19 L1 L2)
    (DEG:SET k "")
  )
  (foreach k '(DN_SKIP_BLOCKS DN_SKIP_LAYER_PATTERNS DN_SKIP_LAYER_BLOCKS DN_FILTER_IGNORE_BLOCKS DN_FILTER_CO_LAYER_PATTERNS DN_FILTER_CO_BLOCKS DN_FILTER_FLASOR_LAYERS DN_FILTER_FLASOR_BLOCKS DN_FILTER_SOUND_LAYER_PATTERNS DN_FILTER_SOUND_BLOCK_PATTERNS DN_FILTER_FIRE_LAYER_PATTERNS DN_FILTER_FIRE_BLOCK_EXCLUDES)
    (DEG:CFG-SET k "")
  )
  (DEGDO--fill-dn)
)
(defun DEGDO--fill-dg ()
  (set_tile "light_line"   (DEGDO--codes-merged '(A2 A4)))
  (set_tile "light_comb"   (DEGDO--codes-merged '(A3 A5)))
  (set_tile "priz_line"    (DEGDO--codes-merged '(B1 B3)))
  (set_tile "priz_comb"    (DEGDO--codes-merged '(B2 B4)))
  (set_tile "knx_layers"   (DEGDO--codes-merged '(A1)))
  (set_tile "buton_layers" (DEGDO--codes-merged '(A7)))
  (set_tile "anahtar_layers" (DEGDO--join-layers (DEG:CFG-LIST 'DG_ANAHTAR_LAYER)))
  (set_tile "kit_layers"     (DEGDO--join-layers (DEG:CFG-LIST 'DG_KIT_LAYER)))
  (set_tile "data_line"    (DEGDO--codes-merged '(C1 C2)))
  (set_tile "data_comb"    (DEGDO--codes-merged '(C3 C4)))
  (set_tile "fiber_line"   (DEGDO--codes-merged '(C6)))
  (set_tile "fiber_comb"   (DEGDO--codes-merged '(C7 C8)))
  (set_tile "tel_line"     (DEGDO--codes-merged '(E1 E2)))
  (set_tile "tel_comb"     (DEGDO--codes-merged '(E3 E5)))
  (set_tile "tv_line"      (DEGDO--codes-merged '(F1 F3)))
  (set_tile "tv_comb"      (DEGDO--codes-merged '(F2 F4)))
  (set_tile "ups_line"     (DEGDO--codes-merged '(G1 G3)))
  (set_tile "ups_comb"     (DEGDO--codes-merged '(G2 G4)))
  (set_tile "kartli_line"  (DEGDO--codes-merged '(H1 H3)))
  (set_tile "kartli_comb"  (DEGDO--codes-merged '(H2 H4)))
  (set_tile "dg_extra" (DEG:CFG-GET 'DG_EXTRA_LIGHTING_LAYERS))
)

(defun DEGDO--save-dg ()
  (DEG:SET 'A2 (DEGDO--trim (get_tile "light_line")))
  (DEG:SET 'A4 "")
  (DEG:SET 'A3 (DEGDO--trim (get_tile "light_comb")))
  (DEG:SET 'A5 "")
  (DEG:SET 'B1 (DEGDO--trim (get_tile "priz_line")))
  (DEG:SET 'B3 "")
  (DEG:SET 'B2 (DEGDO--trim (get_tile "priz_comb")))
  (DEG:SET 'B4 "")
  (DEG:SET 'A1 (DEGDO--trim (get_tile "knx_layers")))
  (DEG:SET 'A7 (DEGDO--trim (get_tile "buton_layers")))
  (DEG:CFG-SET 'DG_ANAHTAR_LAYER (DEGDO--trim (get_tile "anahtar_layers")))
  (DEG:CFG-SET 'DG_KIT_LAYER (DEGDO--trim (get_tile "kit_layers")))
  (DEG:SET 'C1 (DEGDO--trim (get_tile "data_line")))
  (DEG:SET 'C2 "")
  (DEG:SET 'C3 (DEGDO--trim (get_tile "data_comb")))
  (DEG:SET 'C4 "")
  (DEG:SET 'C6 (DEGDO--trim (get_tile "fiber_line")))
  (DEG:SET 'C7 (DEGDO--trim (get_tile "fiber_comb")))
  (DEG:SET 'C8 "")
  (DEG:SET 'E1 (DEGDO--trim (get_tile "tel_line")))
  (DEG:SET 'E2 "")
  (DEG:SET 'E3 (DEGDO--trim (get_tile "tel_comb")))
  (DEG:SET 'E5 "")
  (DEG:SET 'F1 (DEGDO--trim (get_tile "tv_line")))
  (DEG:SET 'F3 "")
  (DEG:SET 'F2 (DEGDO--trim (get_tile "tv_comb")))
  (DEG:SET 'F4 "")
  (DEG:SET 'G1 (DEGDO--trim (get_tile "ups_line")))
  (DEG:SET 'G3 "")
  (DEG:SET 'G2 (DEGDO--trim (get_tile "ups_comb")))
  (DEG:SET 'G4 "")
  (DEG:SET 'H1 (DEGDO--trim (get_tile "kartli_line")))
  (DEG:SET 'H3 "")
  (DEG:SET 'H2 (DEGDO--trim (get_tile "kartli_comb")))
  (DEG:SET 'H4 "")
  (DEG:CFG-SET 'DG_EXTRA_LIGHTING_LAYERS (DEGDO--trim (get_tile "dg_extra")))
  (DEG:SAVE-SETTINGS)
)

(defun DEGDO--reset-dg ()
  (foreach k '(A1 A2 A3 A4 A5 A7 B1 B2 B3 B4 C1 C2 C3 C4 C6 C7 C8 E1 E2 E3 E5 F1 F2 F3 F4 G1 G2 G3 G4 H1 H2 H3 H4)
    (DEG:SET k "")
  )
  (DEG:CFG-SET 'DG_KIT_LAYER "")
  (DEG:CFG-SET 'DG_ANAHTAR_LAYER "")
  (DEG:CFG-SET 'DG_EXTRA_LIGHTING_LAYERS "")
  (DEGDO--fill-dg)
)

(defun DEGDO--fill-ds ()
  (set_tile "ds_row_spacing" (DEGDO--dk-display 'DS_ROW_SPACING))
  (set_tile "ds_symbol_dx" (DEGDO--dk-display 'DS_SYMBOL_DX))
  (set_tile "ds_count_dx" (DEGDO--dk-display 'DS_COUNT_DX))
  (set_tile "ds_table_block_w" (DEGDO--dk-display 'DS_TABLE_BLOCK_W))
  (set_tile "ds_table_symbol_w" (DEGDO--dk-display 'DS_TABLE_SYMBOL_W))
  (set_tile "ds_table_count_w" (DEGDO--dk-display 'DS_TABLE_COUNT_W))
  (set_tile "ds_text_height" (DEGDO--dk-display 'DS_TEXT_HEIGHT))
  (set_tile "ds_exclude_blocks" (DEG:CFG-GET 'DS_EXCLUDE_BLOCKS))
)

(defun DEGDO--save-ds ()
  (DEG:CFG-SET 'DS_ROW_SPACING (DEGDO--dk-store "ds_row_spacing"))
  (DEG:CFG-SET 'DS_SYMBOL_DX (DEGDO--dk-store "ds_symbol_dx"))
  (DEG:CFG-SET 'DS_COUNT_DX (DEGDO--dk-store "ds_count_dx"))
  (DEG:CFG-SET 'DS_TABLE_BLOCK_W (DEGDO--dk-store "ds_table_block_w"))
  (DEG:CFG-SET 'DS_TABLE_SYMBOL_W (DEGDO--dk-store "ds_table_symbol_w"))
  (DEG:CFG-SET 'DS_TABLE_COUNT_W (DEGDO--dk-store "ds_table_count_w"))
  (DEG:CFG-SET 'DS_TEXT_HEIGHT (DEGDO--dk-store "ds_text_height"))
  (DEG:CFG-SET 'DS_EXCLUDE_BLOCKS (DEGDO--trim (get_tile "ds_exclude_blocks")))
  (DEG:SAVE-SETTINGS)
)

(defun DEGDO--reset-ds ()
  (foreach k '(DS_ROW_SPACING DS_SYMBOL_DX DS_COUNT_DX DS_TABLE_BLOCK_W DS_TABLE_SYMBOL_W DS_TABLE_COUNT_W DS_TEXT_HEIGHT DS_EXCLUDE_BLOCKS)
    (DEG:CFG-SET k "")
  )
  (DEGDO--fill-ds)
)

(defun DEGDO--fill-cmds ()
  (set_tile "cmd_dg"  (DEG:CFG-GET 'CMD_DG))
  (set_tile "cmd_dgt" (DEG:CFG-GET 'CMD_DGT))
  (set_tile "cmd_dn"  (DEG:CFG-GET 'CMD_DN))
  (set_tile "cmd_dk"  (DEG:CFG-GET 'CMD_DK))
  (set_tile "cmd_dkk" (DEG:CFG-GET 'CMD_DKK))
  (set_tile "cmd_dp"  (DEG:CFG-GET 'CMD_DP))
  (set_tile "cmd_dz"  (DEG:CFG-GET 'CMD_DZ))
  (set_tile "cmd_dd"  (DEG:CFG-GET 'CMD_DD))
  (set_tile "cmd_df"  (DEG:CFG-GET 'CMD_DF))
  (set_tile "cmd_dw"  (DEG:CFG-GET 'CMD_DW))
  (set_tile "cmd_dm"  (DEG:CFG-GET 'CMD_DM))
  (set_tile "cmd_ds"  (DEG:CFG-GET 'CMD_DS))
  (set_tile "cmd_dt"  (DEG:CFG-GET 'CMD_DT))
  (set_tile "cmd_dtm" (DEG:CFG-GET 'CMD_DTM))
  (set_tile "cmd_dtt" (DEG:CFG-GET 'CMD_DTT))
  (set_tile "cmd_do"  (DEG:CFG-GET 'CMD_DO))
  (set_tile "cmd_ucs" (DEG:CFG-GET 'CMD_UCS))
)

(defun DEGDO--save-cmds ()
  (DEG:CFG-SET 'CMD_DG  (DEGDO--trim (get_tile "cmd_dg")))
  (DEG:CFG-SET 'CMD_DGT (DEGDO--trim (get_tile "cmd_dgt")))
  (DEG:CFG-SET 'CMD_DN  (DEGDO--trim (get_tile "cmd_dn")))
  (DEG:CFG-SET 'CMD_DK  (DEGDO--trim (get_tile "cmd_dk")))
  (DEG:CFG-SET 'CMD_DKK (DEGDO--trim (get_tile "cmd_dkk")))
  (DEG:CFG-SET 'CMD_DP  (DEGDO--trim (get_tile "cmd_dp")))
  (DEG:CFG-SET 'CMD_DZ  (DEGDO--trim (get_tile "cmd_dz")))
  (DEG:CFG-SET 'CMD_DD  (DEGDO--trim (get_tile "cmd_dd")))
  (DEG:CFG-SET 'CMD_DF  (DEGDO--trim (get_tile "cmd_df")))
  (DEG:CFG-SET 'CMD_DW  (DEGDO--trim (get_tile "cmd_dw")))
  (DEG:CFG-SET 'CMD_DM  (DEGDO--trim (get_tile "cmd_dm")))
  (DEG:CFG-SET 'CMD_DS  (DEGDO--trim (get_tile "cmd_ds")))
  (DEG:CFG-SET 'CMD_DT  (DEGDO--trim (get_tile "cmd_dt")))
  (DEG:CFG-SET 'CMD_DTM (DEGDO--trim (get_tile "cmd_dtm")))
  (DEG:CFG-SET 'CMD_DTT (DEGDO--trim (get_tile "cmd_dtt")))
  (DEG:CFG-SET 'CMD_DO  (DEGDO--trim (get_tile "cmd_do")))
  (DEG:CFG-SET 'CMD_UCS (DEGDO--trim (get_tile "cmd_ucs")))
  (DEG:SAVE-SETTINGS)
  (DEG:CMD-APPLY-ALIASES)
)

(defun DEGDO--reset-cmds ()
  (foreach k '(CMD_DG CMD_DGT CMD_DN CMD_DK CMD_DKK CMD_DP CMD_DZ CMD_DD CMD_DF CMD_DW CMD_DM CMD_DS CMD_DT CMD_DTM CMD_DTT CMD_DO CMD_UCS)
    (DEG:CFG-SET k "")
  )
  (DEGDO--fill-cmds)
  (DEG:SAVE-SETTINGS)
  (DEG:CMD-APPLY-ALIASES)
)

(defun DEGDO--prepare-page (page)
  (DEGDO--bind-tabs page)
  (action_tile "cancel" "(done_dialog 0)")
  (cond
    ((= page "do_dd")
      (DEGDO--fill-dd)
      (mode_tile "defaults" 0)
      (action_tile "defaults" "(DEGDO--reset-dd)")
      (action_tile "accept" "(DEGDO--save-dd) (done_dialog 1)")
    )
    ((= page "do_df")
      (DEGDO--fill-df)
      (mode_tile "defaults" 0)
      (action_tile "defaults" "(DEGDO--reset-df)")
      (action_tile "accept" "(DEGDO--save-df) (done_dialog 1)")
    )
    ((= page "do_dg")
      (DEGDO--fill-dg)
      (mode_tile "defaults" 0)
      (action_tile "defaults" "(DEGDO--reset-dg)")
      (action_tile "accept" "(DEGDO--save-dg) (done_dialog 1)")
    )
    ((= page "do_dgt")
      (DEGDO--fill-dgt)
      (mode_tile "defaults" 0)
      (action_tile "defaults" "(DEGDO--reset-dgt)")
      (action_tile "dgt_reset" "(DEG-DGT-RESET)")
      (action_tile "accept" "(DEGDO--save-dgt) (done_dialog 1)")
    )
    ((= page "do_dt")
      (DEGDO--fill-dt)
      (mode_tile "defaults" 0)
      (action_tile "defaults" "(DEGDO--reset-dt)")
      (action_tile "accept" "(DEGDO--save-dt) (done_dialog 1)")
    )
    ((= page "do_dtt")
      (DEGDO--fill-dtt)
      (mode_tile "defaults" 0)
      (action_tile "defaults" "(DEGDO--reset-dtt)")
      (action_tile "accept" "(DEGDO--save-dtt) (done_dialog 1)")
    )
    ((= page "do_dn")
      (DEGDO--fill-dn)
      (mode_tile "defaults" 0)
      (action_tile "defaults" "(DEGDO--reset-dn)")
      (action_tile "dn_clear_sira" "(DEGDO--save-dn) (done_dialog 3)")
      (action_tile "accept" "(DEGDO--save-dn) (done_dialog 1)")
    )
    ((= page "do_dp")
      (DEGDO--fill-dp)
      (mode_tile "defaults" 0)
      (action_tile "defaults" "(DEGDO--reset-dp)")
      (action_tile "accept" "(DEGDO--save-dp) (done_dialog 1)")
    )
    ((= page "do_blocklar")
      (DEGDO--fill-blocklar)
      (mode_tile "defaults" 0)
      (action_tile "defaults" "(DEGDO--reset-blocklar)")
      (action_tile "accept" "(DEGDO--save-blocklar) (done_dialog 1)")
    )
    ((= page "do_dk")
      (DEGDO--fill-dk)
      (mode_tile "defaults" 0)
      (action_tile "defaults" "(DEGDO--reset-dk)")
      (action_tile "accept" "(DEGDO--save-dk) (done_dialog 1)")
    )
    ((= page "do_dz")
      (DEGDO--fill-dz)
      (mode_tile "defaults" 0)
      (action_tile "defaults" "(DEGDO--reset-dz)")
      (action_tile "accept" "(DEGDO--save-dz) (done_dialog 1)")
    )
    ((= page "do_dc")
      (DEGDO--fill-dc)
      (mode_tile "defaults" 0)
      (action_tile "defaults" "(DEGDO--reset-dc)")
      (action_tile "accept" "(DEGDO--save-dc) (done_dialog 1)")
    )
    ((= page "do_plan")
      (DEGDO--fill-plan)
      (mode_tile "defaults" 0)
      (action_tile "defaults" "(DEGDO--reset-plan)")
      (action_tile "accept" "(DEGDO--save-plan) (done_dialog 1)")
    )
    ((= page "do_kayit")
      (DEGDO--fill-kayit)
      (mode_tile "defaults" 0)
      (action_tile "defaults" "(DEGDO--reset-kayit)")
      (action_tile "kayit_browse" "(DEGDO--browse-kayit)")
      (action_tile "accept" "(DEGDO--save-kayit) (done_dialog 1)")
    )
    ((= page "do_tol")
      (DEGDO--fill-tol)
      (mode_tile "defaults" 0)
      (action_tile "defaults" "(DEGDO--reset-tol)")
      (action_tile "accept" "(DEGDO--save-tol) (done_dialog 1)")
    )
    ((= page "do_ds")
      (DEGDO--fill-ds)
      (mode_tile "defaults" 0)
      (action_tile "defaults" "(DEGDO--reset-ds)")
      (action_tile "accept" "(DEGDO--save-ds) (done_dialog 1)")
    )
    ((= page "do_cmds")
      (DEGDO--fill-cmds)
      (mode_tile "defaults" 0)
      (action_tile "defaults" "(DEGDO--reset-cmds)")
      (action_tile "accept" "(DEGDO--save-cmds) (done_dialog 1)")
    )
    (T
      (mode_tile "defaults" 1)
      (action_tile "defaults" "")
      (action_tile "accept" "(done_dialog 0)")
    )
  )
)

(defun DO_DCL_ORIG (/ dclFn dclId page rc)
  (vl-catch-all-apply 'vl-load-com '())
  (setq dclFn (DEGDO--write-dcl))
  (if (null dclFn)
    (princ "\nDO: DCL dosyasi olusturulamadi.")
    (progn
      (setq dclId (load_dialog dclFn))
      (if (or (null dclId) (< dclId 0))
        (princ "\nDO: Dialog yuklenemedi.")
        (progn
          (setq page "do_plan")
          (while page
            (setq *DEGDO_NEXT* nil)
            (if (not (new_dialog page dclId))
              (setq page nil)
              (progn
                (DEGDO--prepare-page page)
                (setq rc (start_dialog))
                (cond
                  ((= rc 2) (setq page *DEGDO_NEXT*))
                  ((= rc 3) (c:DO_DN_CLEAR_SIRA) (setq page "do_dn"))
                  (T        (setq page nil))
                )
              )
            )
          )
          (unload_dialog dclId)
        )
      )
    )
  )
  (princ)
)

(defun DEGDO--win-quote (value)
  (strcat "\"" (if value value "") "\"")
)

(defun DEGDO--win-vbs-string (value / index char out)
  (setq index 1
        out "")
  (repeat (strlen value)
    (setq char (substr value index 1)
          out  (strcat out (if (= char "\"") "\"\"" char))
          index (1+ index)))
  out
)

(defun DEGDO--win-run-hidden (executable arguments / launcher file commandLine result)
  ;; WScript dis surecte calisir: PowerShell konsolu gorunmez ve CAD icinde
  ;; WScript.Shell COM nesnesi acilmadigi icin GstarCAD erisim ihlali riski yoktur.
  (setq launcher
    (DEG:RUNTIME-FILE
      (strcat
        "deg_hidden_"
        (itoa (DEGDO--win-process-id))
        "_"
        (itoa (getvar "MILLISECS"))
        ".vbs"))
    commandLine (strcat (DEGDO--win-quote executable) " " arguments)
    file (open launcher "w"))
  (if file
    (progn
      (write-line "On Error Resume Next" file)
      (write-line "Dim shell, fso" file)
      (write-line "Set shell = CreateObject(\"WScript.Shell\")" file)
      (write-line
        (strcat "shell.Run \"" (DEGDO--win-vbs-string commandLine) "\", 0, False")
        file)
      (write-line "Set fso = CreateObject(\"Scripting.FileSystemObject\")" file)
      (write-line "fso.DeleteFile WScript.ScriptFullName, True" file)
      (close file)
      (setq result
        (vl-catch-all-apply
          'startapp
          (list "wscript.exe" (DEGDO--win-quote launcher))))
      (if (or (vl-catch-all-error-p result) (null result))
        (progn
          (vl-catch-all-apply 'vl-file-delete (list launcher))
          nil)
        T))
    nil)
)

(defun DEGDO--win-script-path (/ self dir found path)
  (setq self (DEG:SELF-FILE))
  (if self
    (progn
      (setq dir (vl-filename-directory self))
      (if dir
        (setq found (findfile (strcat dir "\\DG_WINDOWS_UI.ps1"))))))
  (if (not found)
    (setq found (findfile "DG_WINDOWS_UI.ps1")))
  (if (not found)
    (progn
      (setq path (strcat (getenv "USERPROFILE") "\\Documents\\metraj\\DEG\\DG_WINDOWS_UI.ps1"))
      (if (findfile path) (setq found path))))
  found
)

(defun DEGDO--win-process-id (/ value)
  (setq value (vl-catch-all-apply 'getvar (list "PROCESSID")))
  (if (and (not (vl-catch-all-error-p value)) (numberp value))
    (fix value)
    0
  )
)

(defun DEGDO--win-window-handle (/ value)
  ;; ActiveX cagirmadan CAD ana pencere kimligini al.
  (setq value (vl-catch-all-apply 'getvar (list "HWND")))
  (if (and value (not (vl-catch-all-error-p value)) (numberp value))
    (fix value)
    0
  )
)

(defun DEGDO--win-id-text (value)
  (cond
    ((= (type value) 'INT) (itoa value))
    ((= (type value) 'REAL) (rtos value 2 0))
    (T "0"))
)

(defun DEGDO--win-state-path (/ pid hwnd key)
  (setq pid (DEGDO--win-process-id)
        hwnd (if (> pid 0) 0 (DEGDO--win-window-handle))
        key (if (> pid 0) pid hwnd))
  (DEG:RUNTIME-FILE
    (strcat "deg_do_windows_" (DEGDO--win-id-text key) ".tsv"))
)

(defun DEGDO--win-request-path ()
  (strcat (DEGDO--win-state-path) ".request")
)

(defun DEGDO--win-status-path ()
  (strcat (DEGDO--win-state-path) ".status")
)

(defun DEGDO--win-safe-field (value)
  (vl-string-translate "\t\r\n" "   " (if value (vl-princ-to-string value) ""))
)

(defun DEGDO--win-prefix-p (prefix value)
  (equal (vl-string-search prefix value) 0)
)

(defun DEGDO--win-add-key (key keys)
  (if (member key keys) keys (append keys (list key)))
)

(defun DEGDO--win-extra-cfg-defaults ()
  '(
    (DN_SKIP_BLOCKS . "")
    (DN_SKIP_LAYER_PATTERNS . "")
    (DN_SKIP_LAYER_BLOCKS . "")
    (DN_FILTER_IGNORE_BLOCKS . "")
    (DN_FILTER_CO_LAYER_PATTERNS . "")
    (DN_FILTER_CO_BLOCKS . "")
    (DN_FILTER_FLASOR_LAYERS . "")
    (DN_FILTER_FLASOR_BLOCKS . "")
    (DN_FILTER_SOUND_LAYER_PATTERNS . "")
    (DN_FILTER_SOUND_BLOCK_PATTERNS . "")
    (DN_FILTER_FIRE_LAYER_PATTERNS . "")
    (DN_FILTER_FIRE_BLOCK_EXCLUDES . "")
  )
)

(defun DEGDO--win-cfg-keys (/ keys rec)
  (setq keys nil)
  (foreach rec *DEG_CFG_DEFAULTS*
    (setq keys (DEGDO--win-add-key (car rec) keys))
  )
  (foreach rec (DEGDO--win-extra-cfg-defaults)
    (setq keys (DEGDO--win-add-key (car rec) keys))
  )
  keys
)

(defun DEGDO--win-hidden-cfg-key-p (key)
  (member key
    '(DC_SIDE_LEN DD_DZ_ORTHO DK_TOUCH_TOL DKX_TOUCH_TOL
      DT_KA_COLOR DT_ZA_COLOR DP_E_LINE_VALUES DP_E_BLOCK_VALUES))
)

(defun DEGDO--win-scaled-key-p (key)
  (or
    (member key
      '(DD_OFFSET DD_AGIZ_ARAMA DD_BLOK_YAKINLIK DD_DIRSEK_DIST DD_DIRSEK_KACIS
        DF_OFFSET DF_AGIZ_ARAMA DF_BLOK_YAKINLIK DF_DIRSEK_DIST DF_DIRSEK_KACIS
        DZ_OFFSET DZ_AGIZ_ARAMA DZ_BLOK_YAKINLIK DZ_DIRSEK_DIST DZ_DIRSEK_KACIS
        DZ_COCUK_HAT_MESAFE
        DG_KNX_START_TOL DG_KNX_BLOCK_TOL DG_KNX_END_TOL DG_REF_TOL
        DG_CHAIN_TOL DG_REPORT_TOL DG_REF_DAL_TOL DG_DAL_SINGLE_TOL DG_P1_TOL
        DN_CHAIN_TOL DN_BLOCK_TOL DN_DOSEME_TOL DN_MODL_TOL
        DK_TOUCH_TOL DKX_TOUCH_TOL DW_TOUCH_TOL DR_TREE_TOL
        DK_NORMAL_GROUP_SPACING DK_NORMAL_FLOOR_SPACING
        DK_COPY_SPACING DK_UNDER_X1 DK_UNDER_X2 DK_UNDER_W DK_UNDER_H
        DK_TEXT_HEIGHT DK_TEXT_OFFSET_Y DK_UNDER_Y_OFFSET
        DK_LOOP_TEXT_HEIGHT DK_LOOP_TEXT_X_OFFSET DK_LOOP_TEXT_Y_MARGIN
        DK_LOOP_LINE_SHIFT_X DK_LOOP_LINE_RISE DK_LOOP_LINE_RUN DK_LOOP_MARK_LENGTH
        DKX_COPY_SPACING DKX_FIRSTSTART_X DKX_FIRSTSTART_Y
        DKX_LASTBOTTOM_X DKX_LASTBOTTOM_Y DKX_TEXT_OFFSET_Y DKX_TEXT_HEIGHT
        DKX_MULTI_DX DKX_MULTI_DROP_Y DKX_VLEN_MAIN DKX_VLEN_SECONDARY
        DKX_HLEN_DEFAULT DKX_HLEN_LAST2 DKX_HLEN_LAST3_LEFT DKX_HLEN_LAST3_RIGHT
        DKX_DATA_SHIFT_Y
        DS_ROW_SPACING DS_SYMBOL_DX DS_COUNT_DX
        DS_TABLE_BLOCK_W DS_TABLE_SYMBOL_W DS_TABLE_COUNT_W
        DS_TEXT_HEIGHT
        DTT_OUTSIDE_GAP DTT_RECT_WIDTH DTT_RECT_HEIGHT DTT_ATT_TEXT_HEIGHT))
  )
)

(defun DEGDO--win-dn-effective (key / value)
  (setq value
    (cond
      ((= key 'DN_SKIP_BLOCKS)
        (DEGDO--dn-cfg-or-codes key '(K5 K18 K3 K4)))
      ((= key 'DN_SKIP_LAYER_PATTERNS)
        (DEGDO--dn-cfg-or-mix key '(K13 K14 K15) "*KARBONMONOKSIT*"))
      ((= key 'DN_SKIP_LAYER_BLOCKS)
        (DEGDO--dn-cfg-or-codes key '(K6 K19)))
      ((= key 'DN_FILTER_IGNORE_BLOCKS)
        (DEGDO--dn-cfg-or-codes key '(N1 K2 N2)))
      ((= key 'DN_FILTER_CO_LAYER_PATTERNS)
        (DEGDO--dn-cfg-or-codes key '(K8)))
      ((= key 'DN_FILTER_CO_BLOCKS)
        (DEGDO--dn-cfg-or-codes key '(K7)))
      ((= key 'DN_FILTER_FLASOR_LAYERS)
        (DEGDO--dn-cfg-or-codes key '(K1)))
      ((= key 'DN_FILTER_FLASOR_BLOCKS)
        (DEGDO--dn-cfg-or-codes key '(K12)))
      ((= key 'DN_FILTER_SOUND_LAYER_PATTERNS)
        (DEGDO--dn-cfg-or-codes key '(K13 K14 K15)))
      ((= key 'DN_FILTER_SOUND_BLOCK_PATTERNS)
        (DEGDO--dn-cfg-or-codes key '(K13 K14 K15)))
      ((= key 'DN_FILTER_FIRE_LAYER_PATTERNS)
        (DEGDO--dn-cfg-or-codes key '(K11 K10 K9)))
      ((= key 'DN_FILTER_FIRE_BLOCK_EXCLUDES)
        (DEGDO--dn-cfg-or-codes key '(K13 K14 K15)))
      (T nil)
    )
  )
  value
)

(defun DEGDO--win-cfg-current (key / value pair)
  (cond
    ((setq value (DEGDO--win-dn-effective key)) value)
    ((and (member key '(DD_DIRSEK_DIST DD_DIRSEK_KACIS
                       DF_DIRSEK_DIST DF_DIRSEK_KACIS
                       DZ_DIRSEK_DIST DZ_DIRSEK_KACIS))
          (= (DEGDO--trim (DEG:CFG-GET key)) ""))
      (cdr (assoc key (DEGDO--win-extra-cfg-defaults))))
    ((DEGDO--win-scaled-key-p key)
      (DEGDO--dk-display key))
    (T (DEG:CFG-GET key))
  )
)

(defun DEGDO--win-cfg-default (key / pair value scale)
  (cond
    ((setq value (DEGDO--win-dn-effective key)) value)
    ((setq pair (assoc key (DEGDO--win-extra-cfg-defaults)))
      (cdr pair))
    ((setq pair (assoc key *DEG_CFG_DEFAULTS*))
      (setq value (DEG:CFG-DEFAULT key))
      (if (and (DEGDO--win-scaled-key-p key) (/= (DEGDO--trim value) ""))
        (progn
          (setq scale (DEG:PLAN-UNIT-SCALE))
          (DEG:NUM->STR (* (atof value) scale)))
        value
      )
    )
    (T "")
  )
)

(defun DEGDO--win-cfg-group (key / name)
  (setq name (vl-symbol-name key))
  (cond
    ((DEGDO--win-prefix-p "CMD_" name) "KOMUTLAR")
    ((= name "PLAN_UNIT") "PLAN")
    ((= name "DO_KAYIT_PATH") "KAYIT")
    ((DEGDO--win-prefix-p "DGT_" name) "DGT")
    ((or (DEGDO--win-prefix-p "DG_" name)
         (DEGDO--win-prefix-p "DN_" name)
         (= name "DW_TOUCH_TOL")
         (= name "DR_TREE_TOL")
         (= name "DK_TOUCH_TOL")
         (= name "DKX_TOUCH_TOL"))
      (if (or (vl-string-search "_TOL" name)
              (= name "DW_TOUCH_TOL")
              (= name "DR_TREE_TOL")
              (= name "DK_TOUCH_TOL")
              (= name "DKX_TOUCH_TOL"))
        "TOL"
        (if (DEGDO--win-prefix-p "DN_" name) "DN" "DG")))
    ((DEGDO--win-prefix-p "DD_" name) "DD")
    ((DEGDO--win-prefix-p "DF_" name) "DF")
    ((DEGDO--win-prefix-p "DZ_" name) "DZ")
    ((DEGDO--win-prefix-p "DC_" name) "DC")
    ((DEGDO--win-prefix-p "DK" name) "DK")
    ((DEGDO--win-prefix-p "DP_E_BLOCK" name) "BLOCKLAR")
    ((DEGDO--win-prefix-p "DP_" name) "DP")
    ((DEGDO--win-prefix-p "DS_" name) "DS")
    ((DEGDO--win-prefix-p "DTT_" name) "DTT")
    ((or (DEGDO--win-prefix-p "DT_" name)
         (= name "DT_KA_COLOR")
         (= name "DT_ZA_COLOR")) "DT")
    (T "GENEL")
  )
)

(defun DEGDO--win-code-group (code / name first)
  (setq name (vl-symbol-name code)
        first (substr name 1 1))
  (cond
    ((member first '("A" "B" "C" "E" "F" "G" "H")) "DG")
    ((= first "D") "DP")
    ((member first '("I" "J" "K" "L" "M" "N" "O" "P")) "DN")
    (T "GENEL")
  )
)

(defun DEGDO--win-label (key)
  (cond
    ((= key 'DK_NORMAL_AREA_LAYERS) "Normal Loop Polyline Layerlari")
    ((= key 'DK_COMBINED_RISER_LAYERS) "Kombine Polyline Layerlari")
    ((= key 'DK_NORMAL_GROUP_SPACING) "Ayni Kat Loop Araligi")
    ((= key 'DK_NORMAL_FLOOR_SPACING) "Katlar Arasi Mesafe")
    ((= key 'DK_LOOP_TEXT_HEIGHT) "Loop Text Height")
    ((= key 'DK_LOOP_TEXT_X_OFFSET) "Loop Text X Ofset")
    ((= key 'DK_LOOP_TEXT_Y_MARGIN) "Loop Text Y Bosluk")
    ((= key 'DK_LOOP_LINE_SHIFT_X) "Loop Cizgi X Kaydirma")
    ((= key 'DK_LOOP_LINE_RISE) "Loop Cizgi Dikey Uzunluk")
    ((= key 'DK_LOOP_LINE_RUN) "Loop Cizgi Yatay Uzunluk")
    ((= key 'DK_LOOP_MARK_LENGTH) "Loop 45 Derece Isaret Boyu")
    ((member key '(DD_OFFSET DF_OFFSET DZ_OFFSET)) "Ofset")
    ((member key '(DD_AGIZ_ARAMA DF_AGIZ_ARAMA DZ_AGIZ_ARAMA)) "Ana Hat Agiz Arama Mesafesi")
    ((member key '(DD_BLOK_YAKINLIK DF_BLOK_YAKINLIK DZ_BLOK_YAKINLIK)) "Blok Yakinlik Mesafesi")
    ((member key '(DD_DIRSEK_DIST DF_DIRSEK_DIST DZ_DIRSEK_DIST)) "Dirsek Baslama Mesafesi")
    ((member key '(DD_DIRSEK_KACIS DF_DIRSEK_KACIS DZ_DIRSEK_KACIS)) "Dirsek Kacis Mesafesi")
    ((= key 'DZ_COCUK_HAT_MESAFE) "Cocuk Hat Baglanti Mesafesi")
    (T (vl-string-translate "_" " " (vl-symbol-name key)))
  )
)

(defun DEGDO--win-cfg-type (key / name)
  (setq name (vl-symbol-name key))
  (cond
    ((= key 'PLAN_UNIT) "CHOICE")
    ((= key 'DO_KAYIT_PATH) "PATH")
    ((or (vl-string-search "_LAYERS" name)
         (vl-string-search "_BLOCKS" name)
         (vl-string-search "_PATTERN" name)
         (= key 'DP_E_LINE_VALUES)
         (= key 'DP_E_BLOCK_VALUES)) "LONG")
    ((or (vl-string-search "_COLOR" name)
         (vl-string-search "HATCH_PATTERN" name)
         (= key 'DTT_ATT_TEXT_STYLE)) "CHOICE")
    (T "TEXT")
  )
)

(defun DEGDO--win-cfg-options (key / name)
  (setq name (vl-symbol-name key))
  (cond
    ((= key 'PLAN_UNIT) "mm|cm|metre")
    ((vl-string-search "_COLOR" name) "1|2|3|4|5|6|7|8|9")
    ((vl-string-search "HATCH_PATTERN" name) "SOLID|HEX")
    ((= key 'DTT_ATT_TEXT_STYLE)
      (DT--palette-join (DEGDO--text-style-names)))
    (T "")
  )
)

(defun DEGDO--win-write-record (file kind key group label value default type options)
  (write-line
    (strcat
      (DEGDO--win-safe-field kind) "\t"
      (DEGDO--win-safe-field key) "\t"
      (DEGDO--win-safe-field group) "\t"
      (DEGDO--win-safe-field label) "\t"
      (DEGDO--win-safe-field value) "\t"
      (DEGDO--win-safe-field default) "\t"
      (DEGDO--win-safe-field type) "\t"
      (DEGDO--win-safe-field options))
    file
  )
)

(defun DEGDO--win-write-schema (path / file key rec layer vals row block data tel tv)
  (setq file (open path "w"))
  (if file
    (progn
      (write-line (strcat "META\tREV\t" (itoa (getvar "MILLISECS")) "\t\t\t\t\t") file)
      (foreach key (DEGDO--win-cfg-keys)
        (if (not (DEGDO--win-hidden-cfg-key-p key))
          (DEGDO--win-write-record
            file "CFG" (vl-symbol-name key) (DEGDO--win-cfg-group key)
            (DEGDO--win-label key)
            (DEGDO--win-cfg-current key)
            (DEGDO--win-cfg-default key)
            (DEGDO--win-cfg-type key)
            (DEGDO--win-cfg-options key))
        )
      )
      (foreach rec *DEG_CODEMAP*
        (DEGDO--win-write-record
          file "CODE" (vl-symbol-name (car rec)) (DEGDO--win-code-group (car rec))
          (strcat (vl-symbol-name (car rec)) " - " (vl-princ-to-string (cadr rec)))
          (DEG:VAL (car rec)) (caddr rec) "LONG" "")
      )
      (setq *DEGDO_DP_E_LAYERS* (DEGDO--plan-e-line-layer-list)
            vals (DEGDO--dp-e-values-alist))
      (foreach layer *DEGDO_DP_E_LAYERS*
        (DEGDO--win-write-record
          file "DPLINE" layer "DP" (strcat layer " - Carpan")
          (DEGDO--dp-e-value-get vals layer) "" "TEXT" "")
      )
      (setq *DEGDO_DP_E_BLOCKS* (DEGDO--plan-e-block-list)
            vals (DEGDO--dp-e-block-values-alist))
      (foreach block *DEGDO_DP_E_BLOCKS*
        (setq row (DEGDO--dp-e-block-row-get vals block)
              data (if row (nth 1 row) "")
              tel  (if row (nth 2 row) "")
              tv   (if row (nth 3 row) ""))
        (DEGDO--win-write-record file "DPBLOCK" (strcat block "^DATA") "BLOCKLAR" (strcat block " - Data") data "" "TEXT" "")
        (DEGDO--win-write-record file "DPBLOCK" (strcat block "^TEL")  "BLOCKLAR" (strcat block " - Telefon") tel "" "TEXT" "")
        (DEGDO--win-write-record file "DPBLOCK" (strcat block "^TV")   "BLOCKLAR" (strcat block " - TV") tv "" "TEXT" "")
      )
      (DEGDO--win-write-record file "ACTION" "DGT_RESET" "DGT" "DGT cember ve renklerini sifirla" "DO Reset" "" "ACTION" "")
      (close file)
      T
    )
    nil
  )
)

(defun DEGDO--win-store-cfg-value (key value / scale)
  (setq value (DEGDO--trim value))
  (if (and (DEGDO--win-scaled-key-p key) (/= value ""))
    (progn
      (setq scale (DEG:PLAN-UNIT-SCALE))
      (if (<= scale 0.0) (setq scale 1.0))
      (DEG:NUM->STR (/ (atof value) scale))
    )
    value
  )
)

(defun DEGDO--win-remove-layer-value (items layer / out item)
  (foreach item items
    (if (/= (norm-layer (car item)) (norm-layer layer))
      (setq out (append out (list item)))
    )
  )
  out
)

(defun DEGDO--win-put-layer-value (items layer value / out)
  (setq out (DEGDO--win-remove-layer-value items layer)
        value (DEGDO--trim value))
  (if (/= value "")
    (setq out (append out (list (cons (norm-layer layer) value)))))
  out
)

(defun DEGDO--win-remove-block-row (items block / out row)
  (foreach row items
    (if (/= (strcase (car row)) (strcase block))
      (setq out (append out (list row)))
    )
  )
  out
)

(defun DEGDO--win-put-block-value (items key value / parts block field row data tel tv out)
  (setq parts (DEGDO--split-delim key "^")
        block (car parts)
        field (strcase (if (cadr parts) (cadr parts) ""))
        row   (DEGDO--dp-e-block-row-get items block)
        data  (if row (nth 1 row) "")
        tel   (if row (nth 2 row) "")
        tv    (if row (nth 3 row) "")
        value (DEGDO--trim value))
  (cond
    ((= field "DATA") (setq data value))
    ((= field "TEL")  (setq tel value))
    ((= field "TV")   (setq tv value))
  )
  (setq out (DEGDO--win-remove-block-row items block))
  (if (or (/= data "") (/= tel "") (/= tv ""))
    (setq out (append out (list (list (strcase block) data tel tv)))))
  out
)

(defun DEGDO--win-write-status (ok message statePath / file statusPath)
  (setq statusPath
    (if statePath
      (strcat statePath ".status")
      (DEGDO--win-status-path)))
  (if (setq file (open statusPath "w"))
    (progn
      (write-line (strcat "OK=" (if ok "1" "0")) file)
      (write-line (strcat "MESSAGE=" (DEGDO--win-safe-field message)) file)
      (write-line (strcat "REV=" (itoa (getvar "MILLISECS"))) file)
      (close file)
      T
    )
    nil
  )
)

(defun DEGDO--win-trace (message / file result)
  (setq result
    (vl-catch-all-apply 'open
      (list (DEG:RUNTIME-FILE "DO_SAVE_TRACE.log") "a")))
  (if (and result (not (vl-catch-all-error-p result)))
    (progn
      (setq file result)
      (vl-catch-all-apply 'write-line
        (list (strcat (itoa (getvar "MILLISECS")) "\t" message) file))
      (vl-catch-all-apply 'close (list file))))
  nil
)

(defun DEGDO--WIN-APPLY-FILE (path / statePath file line parts op kind keyText key value planOp planValue dpLines dpBlocks actionDone dtChanged cmdChanged saveOk)
  (DEGDO--win-trace (strcat "APPLY_START path=" (if path path "nil")))
  (setq statePath
          (if (and path (wcmatch (strcase path) "*.REQUEST"))
            (substr path 1 (- (strlen path) 8))
            (DEGDO--win-state-path))
        dpLines (DEGDO--dp-e-values-alist)
        dpBlocks (DEGDO--dp-e-block-values-alist))
  (if (not (setq file (open path "r")))
    ;; PowerShell, CAD mesgulken ayni geri cagridan birkac tane kuyruga
    ;; koyabilir. Ilk cagri request'i isleyip sildiyse sonrakiler basarili
    ;; durumu hata ile ezmemeli.
    (DEGDO--win-trace "REQUEST_MISSING_OR_ALREADY_HANDLED")
    (progn
      (while (setq line (read-line file))
        (setq parts (DEGDO--split-delim line "\t")
              op (strcase (if (car parts) (car parts) ""))
              kind (strcase (if (cadr parts) (cadr parts) ""))
              keyText (if (nth 2 parts) (nth 2 parts) "")
              value (if (nth 3 parts) (nth 3 parts) ""))
        (if (member op '("SET" "RESET" "ACTION"))
          (cond
            ((= kind "CFG")
              (setq key (read (strcase keyText)))
              (if (DEGDO--win-prefix-p "DT_TYPE" (vl-symbol-name key)) (setq dtChanged T))
              (if (DEGDO--win-prefix-p "CMD_" (vl-symbol-name key)) (setq cmdChanged T))
              (if (= key 'PLAN_UNIT)
                (setq planOp op planValue value)
                (progn
                  (if (= op "RESET")
                    (DEG:CFG-SET key "")
                    (DEG:CFG-SET key (DEGDO--win-store-cfg-value key value)))
                  (if (= key 'DN_BLOCK_TOL)
                    (progn
                      (if (= op "RESET")
                        (progn
                          (DEG:CFG-SET 'DK_TOUCH_TOL "")
                          (DEG:CFG-SET 'DKX_TOUCH_TOL ""))
                        (progn
                          (DEG:CFG-SET 'DK_TOUCH_TOL (DEGDO--win-store-cfg-value key value))
                          (DEG:CFG-SET 'DKX_TOUCH_TOL (DEGDO--win-store-cfg-value key value)))))
                  )
                  (if (= key 'DT_TYPE1_COLOR) (DEG:CFG-SET 'DT_KA_COLOR (DEG:CFG-GET key)))
                  (if (= key 'DT_TYPE2_COLOR) (DEG:CFG-SET 'DT_ZA_COLOR (DEG:CFG-GET key)))
                )
              )
            )
            ((= kind "CODE")
              (setq key (read (strcase keyText)))
              (DEG:SET key (if (= op "RESET") "" value))
            )
            ((= kind "DPLINE")
              (setq dpLines (DEGDO--win-put-layer-value dpLines keyText (if (= op "RESET") "" value)))
            )
            ((= kind "DPBLOCK")
              (setq dpBlocks (DEGDO--win-put-block-value dpBlocks keyText (if (= op "RESET") "" value)))
            )
            ((and (= kind "ACTION") (= keyText "DGT_RESET"))
              (setq actionDone T)
            )
          )
        )
      )
      (close file)
      (DEGDO--win-trace "REQUEST_READ_OK")
      (DEG:CFG-SET 'DP_E_LINE_VALUES (DEGDO--dp-e-values-pack dpLines))
      (DEG:CFG-SET 'DP_E_BLOCK_VALUES (DEGDO--dp-e-block-values-pack dpBlocks))
      (if planOp
        (DEG:CFG-SET 'PLAN_UNIT (if (= planOp "RESET") "" planValue)))
      (DEG:CFG-SET 'DD_DZ_ORTHO "0")
      (DEG:TOL-REFRESH-DN-GLOBALS)
      (DEGDO--win-trace (strcat "SAVE_START file=" (DEG:SETTINGS-FILE)))
      (setq saveOk (DEG:SAVE-SETTINGS))
      (DEGDO--win-trace (strcat "SAVE_DONE ok=" (if saveOk "1" "0")))
      (if dtChanged
        (progn
          (vl-catch-all-apply 'DEGDO--apply-dt-layer-colors '())
          (vl-catch-all-apply 'DT--palette-refresh-type-options '())))
      (if cmdChanged (vl-catch-all-apply 'DEG:CMD-APPLY-ALIASES '()))
      (if actionDone (vl-catch-all-apply 'DEG-DGT-RESET '()))
      (DEGDO--win-write-schema statePath)
      (if saveOk
        (DEGDO--win-write-status T "Ayarlar kaydedildi." statePath)
        (DEGDO--win-write-status nil
          (strcat "Ayarlar uygulandi fakat dosyaya kaydedilemedi: "
                  (DEG:SETTINGS-FILE))
          statePath))
      (if (findfile path) (vl-file-delete path))
    )
  )
  (princ)
)

(defun DEGDO--clear-sira-values (/ ss i blk att data count failed)
  (setq count 0 failed 0
        ss (ssget "_X" '((0 . "INSERT") (66 . 1) (410 . "Model"))))
  (if ss
    (progn
      (setq i 0)
      (repeat (sslength ss)
        (setq blk (ssname ss i) i (1+ i) att (entnext blk))
        (while (and att (setq data (entget att)) (= (cdr (assoc 0 data)) "ATTRIB"))
          (if (and (= (strcase (cdr (assoc 2 data))) "SIRA_NO")
                   (/= (cdr (assoc 1 data)) ""))
            (if (entmod (subst '(1 . "") (assoc 1 data) data))
              (setq count (1+ count))
              (setq failed (1+ failed))))
          (setq att (entnext att)))
        (entupd blk))))
  (list count failed))

(defun c:DO_DN_CLEAR_SIRA (/ *error* locked row en data result)
  (defun *error* (msg)
    (foreach data locked (entmod data))
    (command-s "_.UNDO" "_End")
    (princ (strcat "\nSIRA_NO temizleme durdu: " msg))
    (princ))
  (command-s "_.UNDO" "_Begin")
  ;; Restore the original layer records on success and on cancellation.
  (setq locked nil row (tblnext "LAYER" T))
  (while row
    (if (/= 0 (logand 4 (cdr (assoc 70 row))))
      (progn
        (setq en (tblobjname "LAYER" (cdr (assoc 2 row))) data (entget en))
        (setq locked (cons data locked))
        (entmod (subst (cons 70 (- (cdr (assoc 70 data)) 4)) (assoc 70 data) data))))
    (setq row (tblnext "LAYER")))
  (setq result (DEGDO--clear-sira-values))
  (foreach data locked (entmod data))
  (command-s "_.UNDO" "_End")
  (princ (strcat "\nSIRA_NO temizlenen: " (itoa (car result))
                 ", temizlenemeyen: " (itoa (cadr result))))
  (princ))

(defun C:DO_WINDOWS_APPLY ()
  (DEGDO--WIN-APPLY-FILE (DEGDO--win-request-path))
  (princ)
)

(defun DEG:WIN-MESSAGE-TITLED (title message / script path file pid hwnd args result)
  (setq script (DEGDO--win-script-path)
        path (DEG:RUNTIME-FILE
               (strcat "deg_message_" (itoa (DEGDO--win-process-id)) "_" (itoa (getvar "MILLISECS")) ".txt")))
  (if (and script (setq file (open path "w")))
    (progn
      (write-line (if title title "DEG") file)
      (write-line (if message message "") file)
      (close file)
      (setq pid (DEGDO--win-process-id)
            hwnd (DEGDO--win-window-handle)
            args
              (strcat
                "-NoProfile -ExecutionPolicy Bypass -STA -WindowStyle Hidden -File "
                (DEGDO--win-quote script)
                " -Mode Message -StatePath " (DEGDO--win-quote path)
                " -HostPid " (DEGDO--win-id-text pid)
                " -HostHwnd " (DEGDO--win-id-text hwnd))
            result (DEGDO--win-run-hidden "powershell.exe" args))
      (if (not result)
        (princ (strcat "\n" (if title title "DEG") ": " (if message message ""))))
      result
    )
    (progn
      (princ (strcat "\n" (if title title "DEG") ": " (if message message "")))
      nil
    )
  )
)

(defun DEG:WIN-MESSAGE (message)
  (DEG:WIN-MESSAGE-TITLED "DEG" message)
)

(defun DO_ORIG (/ script state pid hwnd args result)
  (setq script (DEGDO--win-script-path)
        state (DEGDO--win-state-path))
  (if (and script (DEGDO--win-write-schema state))
    (progn
      (setq pid (DEGDO--win-process-id)
            hwnd (DEGDO--win-window-handle)
            args
              (strcat
                "-NoProfile -ExecutionPolicy Bypass -STA -WindowStyle Hidden -File "
                (DEGDO--win-quote script)
                " -Mode Settings -StatePath " (DEGDO--win-quote state)
                " -HostPid " (DEGDO--win-id-text pid)
                " -HostHwnd " (DEGDO--win-id-text hwnd))
            result (DEGDO--win-run-hidden "powershell.exe" args))
      (if (not result)
        (progn
          (princ "\nDO: Windows ayar paneli acilamadi; DCL yedegi aciliyor.")
          (DO_DCL_ORIG)))
    )
    (DO_DCL_ORIG)
  )
  (princ)
)

(defun UCS_ORIG ()
  (initcommandversion)
  (command "_.UCS")
  (while (> (getvar "CMDACTIVE") 0)
    (command pause)
  )
  (princ)
)
(defun DEG:CMD-VALID-P (s / u i ch ok)
  (setq u (strcase (vl-string-trim " \t\r\n" (if s s ""))))
  (setq ok (and (> (strlen u) 0) (<= (strlen u) 31)))
  (setq i 1)
  (while (and ok (<= i (strlen u)))
    (setq ch (substr u i 1))
    (if (not (wcmatch ch "[A-Z0-9_?]"))
      (setq ok nil)
    )
    (setq i (1+ i))
  )
  ok
)

(defun DEG:CMD-NORM (s)
  (strcase (vl-string-trim " \t\r\n" (if s (vl-princ-to-string s) "")))
)

(defun DEG:CMD-DEFAULT-ALIASES ()
  '("DG" "DGT" "DN" "DK" "DKK" "DP" "DZ" "DD" "DF" "DR" "DW" "DM" "DS" "DT" "DTM" "DTT" "DO" "UCS")
)

(defun DEG:CMD-PAIR-LIST ()
  (list
    (cons (DEG:CFG-GET 'CMD_DG)  'DG_ORIG)
    (cons (DEG:CFG-GET 'CMD_DGT) 'DGT_ORIG)
    (cons (DEG:CFG-GET 'CMD_DN)  'DN_ORIG)
    (cons (DEG:CFG-GET 'CMD_DK)  'DK_ORIG)
    (cons (DEG:CFG-GET 'CMD_DKK) 'DKK_ORIG)
    (cons (DEG:CFG-GET 'CMD_DP)  'DP_ORIG)
    (cons (DEG:CFG-GET 'CMD_DZ)  'DZ_ORIG)
    (cons (DEG:CFG-GET 'CMD_DD)  'DD_ORIG)
    (cons (DEG:CFG-GET 'CMD_DF)  'DF_ORIG)
    (cons (DEG:CFG-GET 'CMD_DR)  'DR_ORIG)
    (cons (DEG:CFG-GET 'CMD_DW)  'DW_ORIG)
    (cons (DEG:CFG-GET 'CMD_DM)  'DM_ORIG)
    (cons (DEG:CFG-GET 'CMD_DS)  'DS_ORIG)
    (cons (DEG:CFG-GET 'CMD_DT)  'DT_ORIG)
    (cons (DEG:CFG-GET 'CMD_DTM) 'DTM_ORIG)
    (cons (DEG:CFG-GET 'CMD_DTT) 'DTT_ORIG)
    (cons (DEG:CFG-GET 'CMD_DO)  'DO_ORIG)
    (cons (DEG:CFG-GET 'CMD_UCS) 'UCS_ORIG)
  )
)

(defun DEG:CMD-ADD-UNIQUE (x lst)
  (if (and x (/= x "") (not (member x lst)))
    (cons x lst)
    lst
  )
)

(defun DEG:CMD-UNREGISTER (alias / a)
  (setq a (DEG:CMD-NORM alias))
  (if (DEG:CMD-VALID-P a)
    (set (read (strcat "C:" a)) nil)
  )
)

(defun DEG:CMD-REGISTER (alias fnsym / a)
  (setq a (DEG:CMD-NORM alias))
  (if (DEG:CMD-VALID-P a)
    (eval
      (list 'defun
            (read (strcat "C:" a))
            '()
            (list
              'if
              '(KC:InitLicense)
              (list
                'progn
                '(DEG:AUTO-PLAN-UNIT-FROM-INSUNITS)
                (list fnsym))
              '(KC:Blocked))
      )
    )
  )
)

(defun DEG:CMD-CLEAR-ALIASES (/ aliases p a)
  (setq aliases (DEG:CMD-DEFAULT-ALIASES))
  (if (and (boundp '*DEG_CMD_ACTIVE_ALIASES*) *DEG_CMD_ACTIVE_ALIASES*)
    (foreach a *DEG_CMD_ACTIVE_ALIASES*
      (setq aliases (DEG:CMD-ADD-UNIQUE (DEG:CMD-NORM a) aliases))
    )
  )
  (foreach p (DEG:CMD-PAIR-LIST)
    (setq aliases (DEG:CMD-ADD-UNIQUE (DEG:CMD-NORM (car p)) aliases))
  )
  (foreach a aliases
    (DEG:CMD-UNREGISTER a)
  )
)

(defun DEG:CMD-APPLY-ALIASES (/ pairs p active a)
  (setq pairs (DEG:CMD-PAIR-LIST))
  (DEG:CMD-CLEAR-ALIASES)
  (setq active nil)
  (foreach p pairs
    (setq a (DEG:CMD-NORM (car p)))
    (if (DEG:CMD-VALID-P a)
      (progn
        (DEG:CMD-REGISTER a (cdr p))
        (setq active (DEG:CMD-ADD-UNIQUE a active))
      )
    )
  )
  (if (not (member "DC" active))
    (DEG:CMD-REGISTER "DC" 'DC_ORIG)
  )
  (setq *DEG_CMD_ACTIVE_ALIASES* active)
  T
)

(defun c:DG  () (if (KC:InitLicense) (progn (DEG:AUTO-PLAN-UNIT-FROM-INSUNITS) (DG_ORIG))  (KC:Blocked)))
(defun c:DGT () (if (KC:InitLicense) (progn (DEG:AUTO-PLAN-UNIT-FROM-INSUNITS) (DGT_ORIG)) (KC:Blocked)))
(defun c:DN  () (if (KC:InitLicense) (progn (DEG:AUTO-PLAN-UNIT-FROM-INSUNITS) (DN_ORIG))  (KC:Blocked)))
(defun c:DK  () (if (KC:InitLicense) (progn (DEG:AUTO-PLAN-UNIT-FROM-INSUNITS) (DK_ORIG))  (KC:Blocked)))
(defun c:DKK () (if (KC:InitLicense) (progn (DEG:AUTO-PLAN-UNIT-FROM-INSUNITS) (DKK_ORIG)) (KC:Blocked)))

(defun c:DP  () (if (KC:InitLicense) (progn (DEG:AUTO-PLAN-UNIT-FROM-INSUNITS) (DP_ORIG))  (KC:Blocked)))
(defun c:DZ ()
  (prompt "\nDZ bu sürümden kaldýrýldý.")
  (princ)
)

(defun c:DD  () (if (KC:InitLicense) (progn (DEG:AUTO-PLAN-UNIT-FROM-INSUNITS) (DD_ORIG))  (KC:Blocked)))
(defun c:DF  () (if (KC:InitLicense) (progn (DEG:AUTO-PLAN-UNIT-FROM-INSUNITS) (DF_ORIG))  (KC:Blocked)))
(defun c:DR  () (if (KC:InitLicense) (progn (DEG:AUTO-PLAN-UNIT-FROM-INSUNITS) (DR_ORIG))  (KC:Blocked)))
(defun c:DW  () (if (KC:InitLicense) (progn (DEG:AUTO-PLAN-UNIT-FROM-INSUNITS) (DW_ORIG))  (KC:Blocked)))
(defun c:DM  () (if (KC:InitLicense) (progn (DEG:AUTO-PLAN-UNIT-FROM-INSUNITS) (DM_ORIG))  (KC:Blocked)))
(defun c:DS  () (if (KC:InitLicense) (progn (DEG:AUTO-PLAN-UNIT-FROM-INSUNITS) (DS_ORIG))  (KC:Blocked)))
(defun c:DT  () (if (KC:InitLicense) (progn (DEG:AUTO-PLAN-UNIT-FROM-INSUNITS) (DT_ORIG))  (KC:Blocked)))
(defun c:DTM () (if (KC:InitLicense) (progn (DEG:AUTO-PLAN-UNIT-FROM-INSUNITS) (DTM_ORIG)) (KC:Blocked)))
(defun c:DTT () (if (KC:InitLicense) (progn (DEG:AUTO-PLAN-UNIT-FROM-INSUNITS) (DTT_ORIG)) (KC:Blocked)))
(defun c:DO  () (if (KC:InitLicense) (progn (DEG:AUTO-PLAN-UNIT-FROM-INSUNITS) (DO_ORIG))  (KC:Blocked)))

(defun KC:UpdateResultDetail (result / pos)
  (setq pos (if result (vl-string-search "|" result) nil))
  (if (and pos (< (1+ pos) (strlen result)))
    (KC:Trim (substr result (+ pos 2)))
    "")
)

(defun c:DUPDATE (/ result detail upper)
  (princ "\n[KC] Guncellemeler kontrol ediliyor-...")
  (setq result (KC:CheckForUpdates T)
        upper  (if result (strcase result) ""))
  (cond
    ((and result (wcmatch upper "UPDATED|PENDING|*"))
      (DEG:WIN-MESSAGE-TITLED
        "DEG Güncelleme"
        "Dosyalar indirildi.\nKurulum AutoCAD kapatýldýðýnda otomatik tamamlanacak."))
    ((and result (wcmatch upper "UPDATED|*"))
      (DEG:WIN-MESSAGE-TITLED
        "DEG Güncelleme"
        "Güncelleme tamamlandý.\nCAD programýný yeniden baþlatýn."))
    ((and result (wcmatch upper "CURRENT|*"))
      (princ "\n[KC] DEG dosyalari zaten guncel."))
    ((and result (wcmatch upper "FAILED|*"))
      (setq detail (KC:UpdateResultDetail result))
      (princ
        (strcat
          "\n[KC] Guncelleme tamamlanamadi"
          (if (/= detail "") (strcat ": " detail) "."))))
    (T
      (princ "\n[KC] Guncelleme denetimi baslatilamadi."))
  )
  (princ)
)

(defun c:DUPDATETEST ()
  (DEG:WIN-MESSAGE-TITLED "DUPDATE TEST" "net test 1.1")
  (princ)
)

(defun c:KCKOD (/ code)
  (setq code (KC:GetDeviceCode))
  (princ (strcat "\n[KC] Cihaz erisim kodu: " (if code code "<KOD_OLUSTURULAMADI>")))
  (princ)
)

;; Lisans kontrolu ilk DEG komutunda yapilir; VLX yuklenirken ag beklenmez.
(DEG:CMD-APPLY-ALIASES)
(foreach s (list (strcat "C:D" "?") (strcat "D" "?_ORIG") (strcat "C:D" "?_ORIG"))
  (set (read s) nil)
)

(princ)


(defun DW_ORIG
  (/ ss blockSs i ent ed typ lay len lenPair curveSums
     blkObj blkName
     symPairs adet adetUse pair sym
     aggAssoc existing
     emList hasEM
     matrix rowOrder anyMahalHit
     key line col mahalName mahalObjs mPair qty
     pageName tmp filepath csvfile alanNo areaMatrix areaCols areaRowOrder
     lengthMatrix lengthAreaCols lengthRows dpVals gap)

  (degw-ensure-vlax)

  ;; Mahal listesi (global)
  (setq emList (degw-get-emahal-unique))
  (setq hasEM (and emList (> (length emList) 0)))

  (setq pageName (getstring T "\nDW - CSV dosya ismini yazýn (boþ = iptal): "))
  (if (or (null pageName) (= pageName ""))
    (progn (princ "\n\nÝptal edildi.") (princ))
    (progn
      (setq pageName (degw-sanitize-filename pageName))

      ;; Klasör seçimi (1 kere)
      (setq *degwFolder*
        (DEGDO--csv-folder *degwFolder* pageName "DW - CSV kaydedilecek konumu secin")
      )
      (if (not *degwFolder*)
        (princ "\n\nDO > KAYIT sayfasinda klasor lokasyonu girin.")
        (progn
          (setq filepath (DEGDO--csv-filepath *degwFolder* pageName))
          (setq csvfile (open filepath "w"))

          (if (not csvfile)
            (princ (strcat "\nDosya açýlamadý/oluþturulamadý: " filepath))
            (progn
              (setq alanNo 1)
              (setq areaMatrix nil)
              (setq areaCols nil)
              (setq areaRowOrder nil)
              (setq lengthMatrix nil)
              (setq lengthAreaCols nil)
              (setq lengthRows nil)
              (setq dpVals (DEGDO--dp-e-values-alist))

              ;; Coklu alan seçimi (ENTER = bitir)
              (while
                (progn
                  (princ (strcat "\n\nAlan " (itoa alanNo) " seçin (pencere, crossing vs. serbest seçim) <ENTER=bitir>: "))
                  (setq ss
                    (ssget
                      '((0 . "INSERT,LINE,LWPOLYLINE,POLYLINE,SPLINE,ARC,CIRCLE,ELLIPSE,HELIX,MLINE"))))
                )

                (if ss
                  (progn
                    ;; Her alan için sifirla
                    (setq aggAssoc '())
                    (setq matrix '())
                    (setq rowOrder '())
                    (setq curveSums '())

                    ;; Ayni alan secimindeki bloklari ve sonlu cizgi/egrileri ayir.
                    (setq blockSs (ssadd))
                    (setq i 0)
                    (while (< i (sslength ss))
                      (setq ent (ssname ss i)
                            ed  (entget ent)
                            typ (cdr (assoc 0 ed)))
                      (if (= typ "INSERT")
                        (ssadd ent blockSs)
                        (progn
                          (setq lay (cdr (assoc 8 ed))
                                len (degp--length ent))
                          (if (> len 0.0)
                            (progn
                              ;; DP'de bu layer icin adet tanimliysa ayni carpani uygula.
                              (setq qty (degp--numstr (DEGDO--dp-e-value-get dpVals lay)))
                              (if qty (setq len (* len qty)))
                              (setq curveSums (degp--alist-add curveSums lay len))
                            )
                          )
                        )
                      )
                      (setq i (1+ i))
                    )

                    (setq lengthAreaCols (append lengthAreaCols (list alanNo)))
                    (foreach lenPair curveSums
                      (setq lay (car lenPair))
                      (setq lengthRows (degw-roworder-add lengthRows lay))
                      (setq lengthMatrix
                        (degw-matrix-inc lengthMatrix lay alanNo (cdr lenPair)))
                    )
                    (setq ss blockSs)

                    (setq i 0)
                    (while (< i (sslength ss))
                      (setq ent    (ssname ss i))
                      (setq blkObj (vlax-ename->vla-object ent))
                      (setq blkName (deg-block-name blkObj))

                                            (if (not (vl-string-search "_OK_" (strcase blkName)))
                        (progn
(if (and
                            (not (wcmatch (strcase (degw-block-effective-name blkObj)) "*E_MAHAL*"))
                            (not (wcmatch (strcase blkName) "*E_MAHAL*"))
                          )
                        (progn
                          (if (not (deg-member blkName (DEG:VALS '(P1 I2 M1 J1 J2 J3))))
                            (progn
                              (setq symPairs (get-sembol-adi-from-block blkObj))
                              (setq adet     (get-adet-from-block blkObj))

                              (setq adetUse
                                    (cond
                                      ((> adet 0) adet)
                                      ((and symPairs (> (cdr (car symPairs)) 0))
                                       (cdr (car symPairs)))
                                      (T 1)
                                    )
                              )

                              (if (not symPairs)
                                (setq symPairs (list (cons "" adetUse)))
                              )

                              (foreach pair symPairs
                                (setq sym (car pair))

                                (if (not hasEM)
                                  (progn
                                    (setq existing
                                          (vl-some
                                            (function
                                              (lambda (x)
                                                (if (and (= (car x) blkName)
                                                         (= (cadr x) sym))
                                                  x
                                                )
                                              )
                                            )
                                            aggAssoc
                                          )
                                    )
                                    (if existing
                                      (setq aggAssoc
                                            (subst
                                              (list blkName sym (+ adetUse (caddr existing)))
                                              existing
                                              aggAssoc
                                            )
                                      )
                                      (setq aggAssoc (cons (list blkName sym adetUse) aggAssoc))
                                    )
                                  )
                                  (progn
                                    (setq anyMahalHit nil)
                                    (setq key (list blkName sym))
                                    (setq rowOrder (degw-roworder-add rowOrder key))

                                    (foreach em emList
                                      (setq mahalName (car em))
                                      (setq mahalObjs (cdr em)) ; obj listesi
                                      (setq mPair nil)

                                      (foreach mo mahalObjs
                                        (if (and (not mPair) (degw-touch-p blkObj mo))
                                          (setq mPair T)
                                        )
                                      )

                                      (if mPair
                                        (progn
                                          (setq anyMahalHit T)
                                          (setq matrix (degw-matrix-inc matrix key mahalName adetUse))
                                        )
                                      )
                                    )

                                    (if (not anyMahalHit)
                                      (setq matrix (degw-matrix-inc matrix key "MAHALSIZ" adetUse))
                                    )
                                  )
                                )
                              )
                            )
                          )
                        )
                      )

                        )
                      )
                      (setq i (1+ i))
                    )

                    ;; --- CSV yazimi / biriktirme ---
                    (if (not hasEM)
                      (progn
                        ;; Mahal bloðu yoksa: alanlari kolon yapacak sekilde biriktir
                        (setq areaCols (append areaCols (list alanNo)))
                        (foreach p (reverse aggAssoc)
                          (setq key (list (car p) (cadr p)))
                          (setq areaRowOrder (degw-roworder-add areaRowOrder key))
                          (setq areaMatrix (degw-matrix-inc areaMatrix key alanNo (caddr p)))
                        )
                      )
                      (progn
                        ;; Mahal bloðu varsa: mevcut format (alan bazlý)
                        (write-line (strcat "ALAN;" (itoa alanNo)) csvfile)

                        (setq line "BlokAdi;SembolAdi")
                        (foreach em emList
                          (setq line (strcat line ";" (car em)))
                        )
                        (setq line (strcat line ";MAHALSIZ"))
                        (write-line line csvfile)

                        (foreach key (reverse rowOrder)
                          (setq line (strcat (car key) ";" (cadr key)))
                          (foreach em emList
                            (setq col (car em))
                            (setq mPair (assoc key matrix))
                            (if mPair
                              (progn
                                (setq qty (assoc col (cdr mPair)))
                                (setq qty (if qty (cdr qty) 0))
                              )
                              (setq qty 0)
                            )
                            (setq line (strcat line ";" (itoa qty)))
                          )

                          (setq mPair (assoc key matrix))
                          (if mPair
                            (progn
                              (setq qty (assoc "MAHALSIZ" (cdr mPair)))
                              (setq qty (if qty (cdr qty) 0))
                            )
                            (setq qty 0)
                          )
                          (setq line (strcat line ";" (itoa qty)))

                          (write-line line csvfile)
                        )

                        ;; Alanlar arasýi boþ satir
                        (write-line "" csvfile)
                      )
                    )
                    (setq alanNo (1+ alanNo))
                  )
                )
              )

              
              ;; Mahal bloðu yoksa: tum alanlari tek tabloda yaz
              (if (not hasEM)
                (progn
                  (if areaCols
                    (progn
                      (setq line "BlokAdi;SembolAdi")
                      (foreach col areaCols
                        (setq line (strcat line ";ALAN" (itoa col)))
                      )
                      (write-line line csvfile)

                      (foreach key (reverse areaRowOrder)
                        (setq line (strcat (car key) ";" (cadr key)))
                        (foreach col areaCols
                          (setq mPair (assoc key areaMatrix))
                          (if mPair
                            (progn
                              (setq qty (assoc col (cdr mPair)))
                              (setq qty (if qty (cdr qty) 0))
                            )
                            (setq qty 0)
                          )
                          (setq line (strcat line ";" (itoa qty)))
                        )
                        (write-line line csvfile)
                      )
                    )
                    (if (not areaMatrix) (write-line "BlokAdi;SembolAdi" csvfile))
                  )
                )
              )

              ;; Son adet satirindan sonra tam 3 bos satir ve alan bazli uzunluklar.
              (if lengthMatrix
                (progn
                  ;; Mahal formatinda son alan tablosu zaten 1 bos satir birakir.
                  (setq gap (if hasEM 2 3))
                  (repeat gap (write-line "" csvfile))
                  (write-line "LAYER UZUNLUKLARI" csvfile)

                  ;; Ustteki BlokAdi;SembolAdi kolonlarini koru; ALAN kolonlari hizali kalsin.
                  (setq line "Layer;")
                  (foreach col lengthAreaCols
                    (setq line
                      (strcat line ";ALAN" (itoa col) " (metre)"))
                  )
                  (write-line line csvfile)

                  (setq lengthRows
                    (vl-sort lengthRows
                      (function
                        (lambda (a b) (< (strcase a) (strcase b))))))
                  (foreach lay lengthRows
                    (setq line (strcat lay ";"))
                    (setq mPair (assoc lay lengthMatrix))
                    (foreach col lengthAreaCols
                      (setq qty (if mPair (assoc col (cdr mPair)) nil))
                      (setq len (if qty (cdr qty) 0.0))
                      (setq line (strcat line ";" (DEG:DP-LEN-STR len)))
                    )
                    (write-line line csvfile)
                  )
                )
              )
(close csvfile)
              (princ (strcat "\nDEGW: Olüstürulan dosya: " filepath))
            )
          )
        )
      )
    )
  )

  (princ)
)

(defun degm-csv-cell (s)
  (if (null s) (setq s ""))
  (setq s (vl-string-subst "\"\"" "\"" s))
  (if (or (vl-string-search ";" s)
          (vl-string-search "\"" s)
          (vl-string-search "\n" s)
          (vl-string-search "\r" s))
    (strcat "\"" s "\"")
    s
  )
)

(defun degm-get-sembol-adi (blkObj / symPairs)
  (setq symPairs (get-sembol-adi-from-block blkObj))
  (if (and symPairs (car symPairs))
    (degm-clean-text (car (car symPairs)))
    ""
  )
)

(defun degm-xref-blockref-p (ent / edata blkDef blkName flags)
  (setq edata (entget ent))
  (setq blkName (cdr (assoc 2 edata)))
  (or
    (and blkName (vl-string-search "|" blkName))
    (and
      blkName
      (setq blkDef (tblsearch "BLOCK" blkName))
      (setq flags (cdr (assoc 70 blkDef)))
      (/= 0 (logand flags 124))
    )
  )
)



(defun degm-delete-selection (ss / i ent obj)
  (if ss
    (progn
      (setq i 0)
      (while (< i (sslength ss))
        (setq ent (ssname ss i))
        (if ent
          (progn
            (setq obj (vlax-ename->vla-object ent))
            (vl-catch-all-apply 'vla-delete (list obj))
          )
        )
        (setq i (1+ i))
      )
    )
  )
  T
)

(defun degm-write-room-row
  (filepath mahalName ss / counts allPairs matrix colCount roomRow rowPair key cnt colIdx)

  (setq counts   (degm-collect-selection-counts ss))
  (setq allPairs (degm-collect-all-pairs))
  (setq matrix   (degm-normalize-matrix (if (findfile filepath) (degm-read-csv-matrix filepath) nil)))

  (if (< (length matrix) 2)
    (setq matrix (list (list "BLOCK ADI") (list "SEMBOL ADI")))
  )

  (setq colCount (max 1 (degm-maxcols matrix)))
  (setq matrix   (degm-pad-matrix matrix colCount))
  (setq matrix   (degm-set-nth 0 (degm-set-nth 0 "BLOCK ADI" (nth 0 matrix)) matrix))
  (setq matrix   (degm-set-nth 1 (degm-set-nth 0 "SEMBOL ADI" (nth 1 matrix)) matrix))

  (foreach rowPair allPairs
    (if (null (degm-find-pair-col matrix (car rowPair) (cadr rowPair)))
      (setq matrix (degm-add-pair-col matrix (car rowPair) (cadr rowPair)))
    )
  )

  (setq colCount (max 1 (degm-maxcols matrix)))
  (setq matrix   (degm-pad-matrix matrix colCount))
  (setq roomRow  (degm-pad-row (list mahalName) colCount))

  (foreach rowPair allPairs
    (setq key    (degm-pair-key (degm-clean-text (car rowPair)) (degm-clean-text (cadr rowPair))))
    (setq cnt    (cdr (assoc key counts)))
    (setq colIdx (degm-find-pair-col matrix (degm-clean-text (car rowPair)) (degm-clean-text (cadr rowPair))))
    (if (and colIdx cnt (> cnt 0))
      (setq roomRow (degm-set-nth colIdx (itoa cnt) roomRow))
    )
  )

  (setq matrix (append matrix (list roomRow)))
  (degm-write-matrix filepath matrix)
)

(defun degm-clean-text (s / out)
  (setq out (if s s ""))
  (setq out (vl-string-translate (strcat (chr 9) (chr 10) (chr 13)) " " out))
  (setq out (vl-string-trim " " out))
  out
)

(defun degm-pair-key (blk sym)
  (strcat (strcase (degm-clean-text blk)) " " (strcase (degm-clean-text sym)))
)

(defun degm-inc-count (alist key / a)
  (if (setq a (assoc key alist))
    (subst (cons key (1+ (cdr a))) a alist)
    (cons (cons key 1) alist)
  )
)

(defun degm-valid-block-ent-p (ent / ed blkObj blkName)
  (and ent
       (setq ed (entget ent))
       (= (cdr (assoc 0 ed)) "INSERT")
       (= (cdr (assoc 410 ed)) "Model")
       (not (degm-xref-blockref-p ent))
       (setq blkObj (vlax-ename->vla-object ent))
       (setq blkName (degm-clean-text (deg-block-name blkObj)))
       (/= blkName "")
       (not (vl-string-search "_OK_" (strcase blkName)))
       (not (vl-string-search "LINYE" (strcase blkName)))
  )
)

(defun degm-collect-all-pairs (/ ss i ent blkObj blkName sym key seen out)
  (setq seen '())
  (setq out  '())
  (setq ss (ssget "_X" '((0 . "INSERT") (410 . "Model"))))
  (if ss
    (progn
      (setq i 0)
      (while (< i (sslength ss))
        (setq ent (ssname ss i))
        (if (degm-valid-block-ent-p ent)
          (progn
            (setq blkObj  (vlax-ename->vla-object ent))
            (setq blkName (degm-clean-text (deg-block-name blkObj)))
            (setq sym     (degm-clean-text (degm-get-sembol-adi blkObj)))
            (setq key (degm-pair-key blkName sym))
            (if (not (member key seen))
              (progn
                (setq seen (cons key seen))
                (setq out  (append out (list (list blkName sym))))
              )
            )
          )
        )
        (setq i (1+ i))
      )
    )
  )
  out
)

(defun degm-collect-selection-counts (ss / i ent blkObj blkName sym key counts)
  (setq counts '())
  (if ss
    (progn
      (setq i 0)
      (while (< i (sslength ss))
        (setq ent (ssname ss i))
        (if (degm-valid-block-ent-p ent)
          (progn
            (setq blkObj  (vlax-ename->vla-object ent))
            (setq blkName (degm-clean-text (deg-block-name blkObj)))
            (setq sym     (degm-clean-text (degm-get-sembol-adi blkObj)))
            (setq key    (degm-pair-key blkName sym))
            (setq counts (degm-inc-count counts key))
          )
        )
        (setq i (1+ i))
      )
    )
  )
  counts
)

(defun degm-csv-parse-line (line / i len ch field fields inQ nxt)
  (setq i 1
        len (strlen line)
        field ""
        fields '()
        inQ nil)
  (while (<= i len)
    (setq ch (substr line i 1))
    (cond
      ((= ch "\"")
       (if inQ
         (progn
           (setq nxt (if (< i len) (substr line (1+ i) 1) ""))
           (if (= nxt "\"")
             (progn
               (setq field (strcat field "\""))
               (setq i (1+ i))
             )
             (setq inQ nil)
           )
         )
         (setq inQ T)
       )
      )
      ((and (not inQ) (= ch ";"))
       (setq fields (append fields (list field)))
       (setq field "")
      )
      (T
       (setq field (strcat field ch))
      )
    )
    (setq i (1+ i))
  )
  (append fields (list field))
)

(defun degm-read-lines (path / fh ln out)
  (setq out '())
  (if (setq fh (open path "r"))
    (progn
      (while (setq ln (read-line fh))
        (setq out (append out (list ln)))
      )
      (close fh)
    )
  )
  out
)

(defun degm-read-csv-matrix (path / lines matrix)
  (setq lines  (degm-read-lines path))
  (setq matrix '())
  (foreach ln lines
    (setq matrix (append matrix (list (degm-csv-parse-line ln))))
  )
  matrix
)

(defun degm-make-list (n val / out)
  (setq out '())
  (while (> n 0)
    (setq out (cons val out))
    (setq n (1- n))
  )
  out
)

(defun degm-maxcols (matrix / m)
  (setq m 0)
  (foreach row matrix
    (if (> (length row) m)
      (setq m (length row))
    )
  )
  m
)

(defun degm-pad-row (row n / diff)
  (setq diff (- n (length row)))
  (if (> diff 0)
    (append row (degm-make-list diff ""))
    row
  )
)

(defun degm-pad-matrix (matrix n / out)
  (setq out '())
  (foreach row matrix
    (setq out (append out (list (degm-pad-row row n))))
  )
  out
)

(defun degm-horizontal-matrix-p (matrix / r1 r2)
  (and matrix
       (>= (length matrix) 2)
       (setq r1 (car matrix))
       (setq r2 (cadr matrix))
       (= (strcase (if (car r1) (car r1) "")) "BLOCK ADI")
       (= (strcase (if (car r2) (car r2) "")) "SEMBOL ADI")
  )
)

(defun degm-vertical-matrix-p (matrix / r1)
  (and matrix
       (setq r1 (car matrix))
       (>= (length r1) 2)
       (= (strcase (if (nth 0 r1) (nth 0 r1) "")) "BLOCK ADI")
       (= (strcase (if (nth 1 r1) (nth 1 r1) "")) "SEMBOL ADI")
  )
)

(defun degm-convert-vertical-to-horizontal (matrix / header pairRows row1 row2 out roomIdx roomName roomRow pairRow maxc)
  (setq header   (car matrix))
  (setq pairRows (cdr matrix))
  (setq row1 (list "BLOCK ADI"))
  (setq row2 (list "SEMBOL ADI"))

  (foreach pairRow pairRows
    (setq row1 (append row1 (list (if (nth 0 pairRow) (nth 0 pairRow) ""))))
    (setq row2 (append row2 (list (if (nth 1 pairRow) (nth 1 pairRow) ""))))
  )

  (setq out (list row1 row2))
  (setq roomIdx 2)
  (while (< roomIdx (length header))
    (setq roomName (nth roomIdx header))
    (setq roomRow (list (if roomName roomName "")))
    (foreach pairRow pairRows
      (setq roomRow (append roomRow (list (if (nth roomIdx pairRow) (nth roomIdx pairRow) ""))))
    )
    (setq out (append out (list roomRow)))
    (setq roomIdx (1+ roomIdx))
  )

  (setq maxc (max 1 (degm-maxcols out)))
  (degm-pad-matrix out maxc)
)

(defun degm-normalize-matrix (matrix)
  (cond
    ((null matrix)
     (list (list "BLOCK ADI") (list "SEMBOL ADI"))
    )
    ((degm-horizontal-matrix-p matrix)
     (degm-pad-matrix matrix (max 1 (degm-maxcols matrix)))
    )
    ((degm-vertical-matrix-p matrix)
     (degm-convert-vertical-to-horizontal matrix)
    )
    (T
     (list (list "BLOCK ADI") (list "SEMBOL ADI"))
    )
  )
)

(defun degm-find-pair-col (matrix blk sym / row1 row2 idx found)
  (setq row1  (car matrix)
        row2  (cadr matrix)
        idx   1
        found nil)
  (setq blk (degm-clean-text blk)
        sym (degm-clean-text sym))
  (while (and (< idx (length row1)) (not found))
    (if (and (= (strcase (degm-clean-text (if (nth idx row1) (nth idx row1) ""))) (strcase blk))
             (= (strcase (degm-clean-text (if (nth idx row2) (nth idx row2) ""))) (strcase sym)))
      (setq found idx)
    )
    (setq idx (1+ idx))
  )
  found
)

(defun degm-set-nth (idx val lst / out i)
  (setq out '()
        i   0)
  (foreach x lst
    (if (= i idx)
      (setq out (append out (list val)))
      (setq out (append out (list x)))
    )
    (setq i (1+ i))
  )
  out
)

(defun degm-add-pair-col (matrix blk sym / out row idx)
  (setq out '()
        idx 0)
  (foreach row matrix
    (cond
      ((= idx 0)
       (setq out (append out (list (append row (list (if blk blk ""))))))
      )
      ((= idx 1)
       (setq out (append out (list (append row (list (if sym sym ""))))))
      )
      (T
       (setq out (append out (list (append row (list "")))))
      )
    )
    (setq idx (1+ idx))
  )
  out
)

(defun degm-join-semi (lst / out)
  (setq out "")
  (foreach x lst
    (if (= out "")
      (setq out (degm-csv-cell (if x x "")))
      (setq out (strcat out ";" (degm-csv-cell (if x x ""))))
    )
  )
  out
)

(defun degm-write-matrix (path matrix / fh)
  (if (setq fh (open path "w"))
    (progn
      (foreach row matrix
        (write-line (degm-join-semi row) fh)
      )
      (close fh)
      T
    )
    nil
  )
)

(defun DM_ORIG
  (/ pageName tmp filepath ss mahalName done emptySelCount emptyMahCount writeOk)

  (degw-ensure-vlax)

  (setq pageName (getstring T "\nDM - CSV dosya ismini yazýn (boþ = iptal): "))
  (if (or (null pageName) (= pageName ""))
    (progn
      (princ "\n\nÝptal edildi.")
      (princ)
    )
    (progn
      (setq pageName (degw-sanitize-filename pageName))

      (setq *degmFolder*
        (DEGDO--csv-folder *degmFolder* pageName "DM - CSV kaydedilecek konumu secin")
      )
      (if (not *degmFolder*)
        (princ "\n\nDO > KAYIT sayfasinda klasor lokasyonu girin.")
        (progn
          (setq filepath (DEGDO--csv-filepath *degmFolder* pageName))
          (setq done nil)
          (setq emptySelCount 0)

          (while (not done)
            (princ "\nBloklarý seçin: ")
            (setq ss (ssget '((0 . "INSERT"))))

            (if (not ss)
              (progn
                (setq emptySelCount (1+ emptySelCount))
                (if (>= emptySelCount 2)
                  (setq done T)
                  (princ "\nDM: Devam için blok seçin, bitirmek için tekrar Enter.")
                )
              )
              (progn
                (setq emptySelCount 0)
                (setq mahalName nil)
                (setq emptyMahCount 0)

                (while (and (not done) (null mahalName))
                  (setq mahalName (getstring T "\nMahal ismini yazýn: "))
                  (if (or (null mahalName) (= mahalName ""))
                    (progn
                      (setq mahalName nil)
                      (setq emptyMahCount (1+ emptyMahCount))
                      (if (>= emptyMahCount 2)
                        (setq done T)
                        (princ "\nDM: Devam için mahal ismi yazýn, çýkmak için tekrar Enter.")
                      )
                    )
                    (setq mahalName (degm-clean-text mahalName))
                  )
                )

                (if (and (not done) mahalName (/= mahalName ""))
                  (progn
                    (setq writeOk (degm-write-room-row filepath mahalName ss))
                    (if writeOk
                      (progn
                        (degm-delete-selection ss)
                        (princ (strcat "\nDM: Satýr yazýldý ve seçili bloklar silindi -> " mahalName))
                      )
                      (princ (strcat "\nDosya yazýlamadý: " filepath))
                    )
                  )
                )
              )
            )
          )

          (princ (strcat "\nDM tamamlandý: " filepath))
        )
      )
    )
  )

  (princ)
)

;;; ===== Standalone DZ override =====
(defun dzo418_drop_last (pts / out)
  (if (and pts (> (length pts) 0))
    (reverse (cdr (reverse pts)))
    pts
  )
)

(defun g419_entmake_open_poly (lay pts / n data e p)
  (setq n (length pts))
  (if (and n (> n 1))
    (progn
      (setq data (list
        (cons 0 "LWPOLYLINE")
        (cons 100 "AcDbEntity")
        (cons 8 lay)
        (cons 100 "AcDbPolyline")
        (cons 90 n)
        (cons 70 0)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g419_main_tangent (pts idx / n i0 i1 p0 p1 v)
  (setq n (length pts))
  (if (< n 2)
    (list 0.0 0.0)
    (progn
      (setq i0 (max 0 (1- idx)))
      (setq i1 (min (1- n) (1+ idx)))
      (setq p0 (nth i0 pts))
      (setq p1 (nth i1 pts))
      (setq v (list (- (car p1) (car p0)) (- (cadr p1) (cadr p0))))
      (g365_unit (car v) (cadr v))
    )
  )
)

(defun g419_best_cap_start_index (outPts pMain uMain dist / n i a b mid v u dotv len d score best bestI)
  (setq n (length outPts))
  (setq i 0 best 1e99 bestI 0)
  (while (< i n)
    (setq a (nth i outPts))
    (setq b (nth (rem (1+ i) n) outPts))
    (setq mid (list (/ (+ (car a) (car b)) 2.0) (/ (+ (cadr a) (cadr b)) 2.0) 0.0))
    (setq v (list (- (car b) (car a)) (- (cadr b) (cadr a))))
    (setq len (sqrt (+ (* (car v) (car v)) (* (cadr v) (cadr v)))))
    (setq u (if (> len 1e-9) (list (/ (car v) len) (/ (cadr v) len)) (list 0.0 0.0)))
    (setq dotv (g365_abs (g365_dot (car u) (cadr u) (car uMain) (cadr uMain))))
    (setq d (distance mid pMain))
    (setq score (+ d (* dotv (* 10.0 dist)) (g365_abs (- len (* 2.0 dist)))))
    (if (< score best)
      (progn (setq best score) (setq bestI i))
    )
    (setq i (1+ i))
  )
  (rem (1+ bestI) n)
)

(defun dzo418_rebuild_outline_seam (outline lay pick mainPts dist / outPts nearV iMain pMain uMain k pts2 newEnt)
  (if (and outline (entget outline))
    (progn
      (setq outPts (g365_get_pts outline))
      (if (and outPts (>= (length outPts) 3) (g376_is_closed outPts))
        (setq outPts (dzo418_drop_last outPts))
      )
      (if (and outPts (>= (length outPts) 3) pick mainPts dist)
        (progn
          (setq nearV (g417_nearest_vertex pick mainPts))
          (setq iMain (car nearV))
          (setq pMain (cadr nearV))
          (setq uMain (g419_main_tangent mainPts iMain))
          (setq k (g419_best_cap_start_index outPts pMain uMain dist))
          (setq pts2 (g417_rotate outPts k))
          (setq newEnt (g419_entmake_open_poly lay pts2))
          (if newEnt
            (progn
              (entdel outline)
              newEnt
            )
            outline
          )
        )
        outline
      )
    )
    outline
  )
)

(defun g387_dist_pt_seg (p a b / res)
  (setq res (g365_closest_on_seg p a b))
  (if res (nth 2 res) 1e99)
)

(defun g387_on_seg (a b p / u)
  (setq u (g365_seg_param a b p))
  (and u (>= u -0.001) (<= u 1.001))
)

(defun g387_attach_inter (poly a b bpt maxd / p0 p1 ip)
  (setq p0 (nth 0 poly) p1 (nth 1 poly))
  (setq ip (if (and p0 p1 a b) (g377_valid_inter p0 p1 a b bpt maxd) nil))
  ip
)

(defun g388_pen (pt dist)
  (if pt 0.0 dist)
)

(defun g388_best_snap (p a b c d tol / r1 r2 d1 d2)
  (setq r1 (if (and a b) (g365_closest_on_seg p a b) nil))
  (setq r2 (if (and c d) (g365_closest_on_seg p c d) nil))
  (setq d1 (if r1 (nth 2 r1) 1e99))
  (setq d2 (if r2 (nth 2 r2) 1e99))
  (cond
    ((and r1 (<= d1 tol) (<= d1 d2)) (nth 0 r1))
    ((and r2 (<= d2 tol)) (nth 0 r2))
    (t p)
  )
)

(defun g372_colorize_assigned (aci) nil)

(defun g405_safe_entdel (e)
  (if (and e (entget e))
    (vl-catch-all-apply 'entdel (list e))
  )
)

(defun g372_delete_assigned (keepEnt / scan pair ent delCnt skipCnt)
  (setq delCnt 0)
  (setq skipCnt 0)
  (setq scan g372_assigned)
  (while scan
    (setq pair (car scan))
    (setq ent (car pair))
    (if (and ent (/= ent keepEnt) (entget ent))
      (progn
        (if (vl-catch-all-error-p (vl-catch-all-apply 'entdel (list ent)))
          (setq skipCnt (1+ skipCnt))
          (setq delCnt (1+ delCnt))
        )
      )
    )
    (setq scan (cdr scan))
  )
  T
)

(defun g405_on_seg (a b p / u)
  (setq u (g365_seg_param a b p))
  (and u (>= u -0.001) (<= u 1.001))
)

(defun g405_closest_pt (p a b / r)
  (setq r (g365_closest_on_seg p a b))
  (if r (car r) p)
)

(defun g405_dist_pt_seg (p a b / r)
  (setq r (g365_closest_on_seg p a b))
  (if r (nth 2 r) 1e99)
)

(defun g405_clamp_leg (p a b bpt maxLen / cp)
  (setq cp (g405_closest_pt p a b))
  (if (> (distance cp bpt) maxLen)
    (g378_pt_towards bpt cp maxLen)
    cp
  )
)

(defun g405_attach_score (aS aE prevPt bpt nextPt dist / pen)
  (setq pen 0.0)
  (if (and prevPt (not (g405_on_seg prevPt bpt aS)))
    (setq pen (+ pen (* 50.0 dist)))
  )
  (if (and nextPt (not (g405_on_seg bpt nextPt aE)))
    (setq pen (+ pen (* 50.0 dist)))
  )
  (+ pen (distance aS bpt) (distance aE bpt))
)

(defun g406_pt_ok (p)
  (and (listp p)
       (numberp (car p))
       (numberp (cadr p)))
)

(defun g406_to3 (p)
  (if (g406_pt_ok p)
    (list (car p) (cadr p)
          (if (and (caddr p) (numberp (caddr p))) (caddr p) 0.0))
    nil
  )
)

(defun g406_mid (p q / p3 q3)
  (setq p3 (g406_to3 p))
  (setq q3 (g406_to3 q))
  (if (and p3 q3)
    (list (/ (+ (car p3) (car q3)) 2.0)
          (/ (+ (cadr p3) (cadr q3)) 2.0)
          0.0)
    nil
  )
)

(defun g406_get_v (pts i / isClosed)
  (setq isClosed (g376_is_closed pts))
  (if isClosed (g376_nth_wrap pts i) (g376_nth_safe pts i))
)

(defun g406_best_corner_idx (boundaryPts idx step seed / cand bestI bestD i p s3 d)
  (setq s3 (g406_to3 seed))
  (if (null s3)
    idx
    (progn
      (setq cand (list idx
                       (- idx step) (+ idx step)
                       (- idx (* 2 step)) (+ idx (* 2 step))))
      (setq bestI idx)
      (setq bestD 1e99)
      (foreach i cand
        (setq p (g406_get_v boundaryPts i))
        (if (g406_pt_ok p)
          (progn
            (setq d (distance s3 (g406_to3 p)))
            (if (< d bestD) (setq bestD d bestI i))
          )
        )
      )
      bestI
    )
  )
)

(defun g407_ptdist (p q / p3 q3)
  (setq p3 (g406_to3 p))
  (setq q3 (g406_to3 q))
  (if (and p3 q3) (distance p3 q3) 1e99)
)

(defun g408_min2 (a b) (if (< a b) a b))
(defun g408_min3 (a b c) (g408_min2 (g408_min2 a b) c))

(defun g408_swap2 (a b / t) (setq t a) (setq a b) (setq b t) (list a b))

(defun g408_fix_side_order (side aug0 / s0 se)
  (if (and side aug0 (> (length side) 1))
    (progn
      (setq s0 (car side))
      (setq se (g365_last side))
      (if (< (distance (g406_to3 se) (g406_to3 aug0))
             (distance (g406_to3 s0) (g406_to3 aug0)))
        (g365_rev side)
        side
      )
    )
    side
  )
)

(defun g409_p2 (p)
  (and (listp p) (numberp (car p)) (numberp (cadr p)))
)

(defun g409_to3 (p)
  (if (g409_p2 p)
    (list (car p) (cadr p) (if (numberp (caddr p)) (caddr p) 0.0))
    nil
  )
)

(defun g409_dist (a b / aa bb)
  (setq aa (g409_to3 a))
  (setq bb (g409_to3 b))
  (if (and aa bb) (distance aa bb) 1e99)
)

(defun g409_find_p1 (pts p0 / i p1)
  (setq i 1 p1 nil)
  (while (and (< i (length pts)) (null p1))
    (if (> (g409_dist (nth i pts) p0) 1e-6)
      (setq p1 (nth i pts))
    )
    (setq i (1+ i))
  )
  (if p1 p1 (nth 1 pts))
)

(defun g410_ptp (p)
  (and p (listp p) (numberp (car p)) (numberp (cadr p)))
)

(defun g410_find_p1_safe (pts p0 / p1)
  (setq p1 (g409_find_p1 pts p0))
  (if (g410_ptp p1)
    p1
    (if (and pts (> (length pts) 1) (g410_ptp (nth 1 pts)))
      (nth 1 pts)
      p0
    )
  )
)

(defun g411_min (a b) (if (< a b) a b))

(defun g411_orient_triplet_to_bpt (aug brL brR bpt / a0 aN)
  (setq a0 (car aug))
  (setq aN (g365_last aug))
  (if (and a0 aN bpt (> (distance a0 bpt) (distance aN bpt)))
    (list (g365_rev aug) (g365_rev brL) (g365_rev brR))
    (list aug brL brR)
  )
)

(defun g412_wrap_index (i n)
  (if (and n (> n 0))
    (rem (+ i (* n 1000)) n)
    i
  )
)

(defun g412_seek_leg_point (pts idx dir bpt minD isClosed / n j k cand)
  (setq n (length pts))
  (setq j 1)
  (setq cand nil)
  (while (and (null cand) (< j (min 12 n)))
    (setq k (+ idx (* dir j)))
    (if isClosed
      (setq k (g412_wrap_index k n))
      (if (or (< k 0) (>= k n)) (setq k nil))
    )
    (if k
      (progn
        (setq cand (nth k pts))
        (if (or (null cand) (<= (distance cand bpt) minD))
          (setq cand nil)
        )
      )
    )
    (setq j (1+ j))
  )
  (if cand cand (if isClosed (g376_nth_wrap pts (+ idx dir)) (g376_nth_safe pts (+ idx dir))))
)

(defun g413_inter_line (a b c d / x1 y1 x2 y2 x3 y3 x4 y4 den t1 t2 x y)
  (if (and a b c d)
    (progn
      (setq x1 (car a)  y1 (cadr a))
      (setq x2 (car b)  y2 (cadr b))
      (setq x3 (car c)  y3 (cadr c))
      (setq x4 (car d)  y4 (cadr d))
      (setq den (- (* (- x1 x2) (- y3 y4)) (* (- y1 y2) (- x3 x4))))
      (if (< (abs den) 1e-12)
        nil
        (progn
          (setq t1 (- (* x1 y2) (* y1 x2)))
          (setq t2 (- (* x3 y4) (* y3 x4)))
          (setq x (/ (- (* t1 (- x3 x4)) (* (- x1 x2) t2)) den))
          (setq y (/ (- (* t1 (- y3 y4)) (* (- y1 y2) t2)) den))
          (list x y)
        )
      )
    )
    nil
  )
)

(defun g413_attach_on_bound (a b c d dist / ip cp1 cp2 tol)
  (setq tol (* 0.6 dist))
  (setq ip (g413_inter_line a b c d))
  (if ip
    (progn
      (setq cp1 (g365_closest_on_seg ip a b))
      (setq cp2 (g365_closest_on_seg ip c d))
      (if (and cp1 cp2 (<= (nth 2 cp1) tol) (<= (nth 2 cp2) tol))
        ip
        nil
      )
    )
    nil
  )
)

(defun g377_bump_vertex_cap (boundaryPts idx step childId dist /
                                   childAug brL brR childBM bpt isClosed prevPt nextPt
                                   lenPrev lenNext minLen capD minD trip
                                   enter exit
                                   brL0 brR0 side1 side2 tag1 tag2
                                   attIn attOut
                                   n jj idxCur key brList tmp rec bump didBump kk2 farOther seq)

  (setq childAug (g372_node childId 'aug))
  (setq brL      (g372_node childId 'left))
  (setq brR      (g372_node childId 'right))
  (setq childBM  (g372_node childId 'branchMap))

  (setq isClosed (g376_is_closed boundaryPts))
  (setq bpt (g377_get_bpt boundaryPts idx))

  (if (or (null bpt) (null childAug) (< (length childAug) 2)
          (null brL) (null brR) (< (length brL) 2) (< (length brR) 2))
    nil
    (progn
      (setq minD (max (* 0.15 dist) 0.001))
      (setq prevPt (g412_seek_leg_point boundaryPts idx -1 bpt minD isClosed))
      (setq nextPt (g412_seek_leg_point boundaryPts idx  1 bpt minD isClosed))

      (setq trip (g411_orient_triplet_to_bpt childAug brL brR bpt))
      (setq childAug (nth 0 trip))
      (setq brL      (nth 1 trip))
      (setq brR      (nth 2 trip))

      (setq lenPrev (if prevPt (distance bpt prevPt) 0.0))
      (setq lenNext (if nextPt (distance bpt nextPt) 0.0))
      (cond
        ((and prevPt nextPt) (setq minLen (min lenPrev lenNext)))
        (prevPt             (setq minLen lenPrev))
        (nextPt             (setq minLen lenNext))
        (t                  (setq minLen 0.0))
      )

      (setq capD (min (* 0.7 dist) (* 0.45 minLen)))
      (if (< capD (* 0.05 dist)) (setq capD (* 0.05 dist)))

      (setq enter (if prevPt (g378_pt_towards bpt prevPt capD) bpt))
      (setq exit  (if nextPt (g378_pt_towards bpt nextPt capD) bpt))

      (setq brL0 (car brL))
      (setq brR0 (car brR))

      (if (and brL0 brR0 prevPt (< (distance brL0 prevPt) (distance brR0 prevPt)))
        (progn
          (setq side1 brL  tag1  1)
          (setq side2 brR  tag2 -1)
        )
        (progn
          (setq side1 brR  tag1 -1)
          (setq side2 brL  tag2  1)
        )
      )

      (setq attIn  (if prevPt (g413_attach_on_bound (nth 0 side1) (nth 1 side1) prevPt bpt dist) bpt))
      (setq attOut (if nextPt (g413_attach_on_bound (nth 0 side2) (nth 1 side2) bpt nextPt dist) bpt))
      (if (null attIn)  (setq attIn bpt))
      (if (null attOut) (setq attOut bpt))

      (setq side1 (cons attIn  (cdr side1)))
      (setq side2 (cons attOut (cdr side2)))

      (setq n (length childAug))
      (if (or (< n 2) (/= (length side1) n) (/= (length side2) n))
        nil
        (progn
          (setq seq nil)

          (setq seq (g365_append_pt seq enter))
          (if prevPt
            (progn
              (if (and (not (g387_on_seg prevPt bpt attIn)) (not (g365_closep attIn bpt)))
                (setq seq (g365_append_pt seq bpt))
              )
              (setq seq (g365_append_pt seq attIn))
            )
            (setq seq (g365_append_pt seq attIn))
          )

          (setq jj 1)
          (while (< jj n)
            (setq key (g365_ptkey (nth jj childAug)))
            (setq brList (if childBM (cdr (assoc key childBM)) nil))
            (setq didBump nil)

            (if (and brList (> jj 0) (< jj (1- n)))
              (progn
                (setq tmp brList)
                (while tmp
                  (setq rec (car tmp))
                  (if (= (car rec) tag1)
                    (progn
                      (setq bump (g377_bump_force_rec side1 jj 1 (cadr rec) dist))
                      (if bump
                        (progn
                          (setq kk2 0)
                          (while (< kk2 (length bump))
                            (setq seq (g365_append_pt seq (nth kk2 bump)))
                            (setq kk2 (1+ kk2))
                          )
                          (setq didBump 1)
                        )
                      )
                    )
                  )
                  (setq tmp (cdr tmp))
                )
              )
            )

            (if (not didBump)
              (setq seq (g365_append_pt seq (nth jj side1)))
            )
            (setq jj (1+ jj))
          )

          (setq farOther (nth (1- n) side2))
          (setq seq (g365_append_pt seq farOther))

          (setq idxCur (- n 2))
          (while (>= idxCur 0)
            (setq key (g365_ptkey (nth idxCur childAug)))
            (setq brList (if childBM (cdr (assoc key childBM)) nil))
            (setq didBump nil)

            (if (and brList (> idxCur 0) (< idxCur (1- n)))
              (progn
                (setq tmp brList)
                (while tmp
                  (setq rec (car tmp))
                  (if (= (car rec) tag2)
                    (progn
                      (setq bump (g377_bump_force_rec side2 idxCur -1 (cadr rec) dist))
                      (if bump
                        (progn
                          (setq kk2 0)
                          (while (< kk2 (length bump))
                            (setq seq (g365_append_pt seq (nth kk2 bump)))
                            (setq kk2 (1+ kk2))
                          )
                          (setq didBump 1)
                        )
                      )
                    )
                  )
                  (setq tmp (cdr tmp))
                )
              )
            )

            (if (not didBump)
              (setq seq (g365_append_pt seq (nth idxCur side2)))
            )
            (setq idxCur (1- idxCur))
          )

          (if nextPt
            (progn
              (if (and (not (g387_on_seg bpt nextPt attOut)) (not (g365_closep attOut bpt)))
                (setq seq (g365_append_pt seq bpt))
              )
              (setq seq (g365_append_pt seq exit))
            )
            (setq seq (g365_append_pt seq exit))
          )

          seq
        )
      )
    )
  )
)

(defun dzo415_entmake_closed_poly (lay pts / n data e p)
  (setq n (length pts))
  (if (and n (> n 2))
    (progn
      (setq data (list
        (cons 0 "LWPOLYLINE")
        (cons 100 "AcDbEntity")
        (cons 8 lay)
        (cons 100 "AcDbPolyline")
        (cons 90 n)
        (cons 70 1)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun dzo418_flush_cmd (/ i)
  (setq i 0)
  (while (and (> (getvar "CMDACTIVE") 0) (< i 80))
    (vl-cmdf "")
    (setq i (1+ i))
  )
  (setq i 0)
  (while (and (> (getvar "CMDACTIVE") 0) (< i 10))
    (vl-cmdf "\003") 
    (setq i (1+ i))
  )
  (setq i 0)
  (while (and (> (getvar "CMDACTIVE") 0) (< i 10))
    (vl-cmdf "_.CANCEL")
    (setq i (1+ i))
  )
  T
)

(defun dzo415_ss_from_list (lst / ss)
  (setq ss (ssadd))
  (while lst
    (if (and (car lst) (entget (car lst)))
      (ssadd (car lst) ss)
    )
    (setq lst (cdr lst))
  )
  ss
)

(defun dzo415_collect_new_ents (afterEnt / e out)
  (setq out nil)
  (setq e (if afterEnt (entnext afterEnt) (entnext nil)))
  (while e
    (setq out (cons e out))
    (setq e (entnext e))
  )
  (reverse out)
)

(defun dzo415_poly_closed_p (e / ed flg)
  (setq ed (entget e))
  (setq flg (cdr (assoc 70 ed)))
  (and flg (= 1 (logand 1 flg)))
)

(defun dzo415_poly_area (e / o a)
  (vl-load-com)
  (setq o (vlax-ename->vla-object e))
  (setq a (vl-catch-all-apply 'vla-get-Area (list o)))
  (if (vl-catch-all-error-p a) 0.0 a)
)

(defun dzo415_pick_largest_closed_poly (cand / best bestA e a)
  (setq best nil bestA 0.0)
  (while cand
    (setq e (car cand))
    (if (and (entget e) (= (cdr (assoc 0 (entget e))) "LWPOLYLINE") (dzo415_poly_closed_p e))
      (progn
        (setq a (dzo415_poly_area e))
        (if (> a bestA)
          (progn (setq best e) (setq bestA a))
        )
      )
    )
    (setq cand (cdr cand))
  )
  best
)

(defun dzo415_delete_ents (lst)
  (while lst
    (if (and (car lst) (entget (car lst)))
      (entdel (car lst))
    )
    (setq lst (cdr lst))
  )
  T
)

(defun dzo415_get_assigned_original_ents (allEnts / out scan e)
  (setq out nil)
  (setq scan allEnts)
  (while scan
    (setq e (car scan))
    (if (and e (g372_assigned_p e))
      (setq out (cons e out))
    )
    (setq scan (cdr scan))
  )
  (reverse out)
)

(defun dzo415_make_tube_poly_from_ent (ent dist lay / pts left right path)
  (setq pts (g365_get_pts ent))
  (if (and pts (>= (length pts) 2))
    (progn
      (setq left  (g365_offset_open_pts pts dist  1))
      (setq right (g365_offset_open_pts pts dist -1))
      (if (and left right (= (length left) (length pts)) (= (length right) (length pts)))
        (progn
          (setq path (append left (reverse right)))
          (dzo415_entmake_closed_poly lay path)
        )
        nil
      )
    )
    nil
  )
)

(defun dzo415_pick_any_poly (cand / e typ)
  (setq e nil)
  (while (and cand (null e))
    (setq typ (cdr (assoc 0 (entget (car cand)))))
    (if (member typ '("LWPOLYLINE" "POLYLINE"))
      (setq e (car cand))
    )
    (setq cand (cdr cand))
  )
  e
)

(defun dzo415_pt_close_p (p q tol)
  (and p q (<= (distance p q) tol))
)

(defun dzo415_seg_reversed (seg)
  (list (cons 'sp (cdr (assoc 'ep seg)))
        (cons 'ep (cdr (assoc 'sp seg)))
        (cons 'bul (- (cdr (assoc 'bul seg)))))
)

(defun dzo415_arc_bulge (ed / a1 a2 da)
  (setq a1 (cdr (assoc 50 ed))
        a2 (cdr (assoc 51 ed))
        da (- a2 a1))
  (while (< da 0.0) (setq da (+ da (* 2.0 pi))))
  (while (>= da (* 2.0 pi)) (setq da (- da (* 2.0 pi))))
  (tan (/ da 4.0))
)

(defun dzo415_curve_to_seg (e / ed typ c r a1 a2)
  (setq ed (entget e)
        typ (cdr (assoc 0 ed)))
  (cond
    ((= typ "LINE")
      (list (cons 'sp (cdr (assoc 10 ed)))
            (cons 'ep (cdr (assoc 11 ed)))
            (cons 'bul 0.0)))
    ((= typ "ARC")
      (setq c (cdr (assoc 10 ed))
            r (cdr (assoc 40 ed))
            a1 (cdr (assoc 50 ed))
            a2 (cdr (assoc 51 ed)))
      (list (cons 'sp (polar c a1 r))
            (cons 'ep (polar c a2 r))
            (cons 'bul (dzo415_arc_bulge ed))))
    (T nil)
  )
)

(defun dzo415_order_segs (segs tol / ordered rest cur idx orig matched)
  (if (null segs)
    nil
    (progn
      (setq ordered (list (car segs))
            rest    (cdr segs)
            cur     (cdr (assoc 'ep (car segs))))
      (while rest
        (setq matched nil idx 0)
        (while (and (< idx (length rest)) (null matched))
          (setq orig (nth idx rest))
          (cond
            ((dzo415_pt_close_p (cdr (assoc 'sp orig)) cur tol)
              (setq matched orig))
            ((dzo415_pt_close_p (cdr (assoc 'ep orig)) cur tol)
              (setq matched (dzo415_seg_reversed orig))))
          (setq idx (1+ idx))
        )
        (if matched
          (progn
            (setq ordered (append ordered (list matched)))
            (setq cur (cdr (assoc 'ep matched)))
            (setq rest (vl-remove orig rest)))
          (setq rest nil)
        )
      )
      ordered
    )
  )
)

(defun dzo415_build_lwpoly_from_curves (curves layer / segs seg ord tol pts buls firstp lastseg lastp data pt i)
  (setq segs nil)
  (foreach e curves
    (setq seg (dzo415_curve_to_seg e))
    (if seg (setq segs (append segs (list seg)))))
  (setq tol 1e-4)
  (setq ord (dzo415_order_segs segs tol))
  (if (and ord (= (length ord) (length segs)))
    (progn
      (setq firstp (cdr (assoc 'sp (car ord)))
            lastseg (car (last ord))
            lastp (cdr (assoc 'ep lastseg)))
      (if (dzo415_pt_close_p firstp lastp tol)
        (progn
          (setq pts nil buls nil)
          (foreach seg ord
            (setq pts (append pts (list (cdr (assoc 'sp seg)))))
            (setq buls (append buls (list (cdr (assoc 'bul seg))))))
          (setq data (list '(0 . "LWPOLYLINE")
                           '(100 . "AcDbEntity")
                           (cons 8 layer)
                           '(100 . "AcDbPolyline")
                           (cons 90 (length pts))
                           '(70 . 1)))
          (setq i 0)
          (while (< i (length pts))
            (setq pt (nth i pts))
            (setq data (append data
                               (list (cons 10 (list (car pt) (cadr pt)))
                                     (cons 42 (nth i buls)))))
            (setq i (1+ i))
          )
          (entmakex data)
        )
      )
    )
  )
)

(defun dzo415_force_close_poly (e / ed old70)
  (if (and e (entget e))
    (progn
      (setq ed (entget e))
      (setq old70 (cdr (assoc 70 ed)))
      (if (null old70) (setq old70 0))
      (if (= 0 (logand old70 1))
        (progn
          (setq ed (subst (cons 70 (boole 7 old70 1)) (assoc 70 ed) ed))
          (entmod ed)
          (entupd e)
        )
      )
    )
  )
  e
)

(defun dzo415_union_tubes_to_outline (tubePls lay / oldCm oldPe oldOsm oldCl beforeR regEnts ssReg beforeU uniEnts regU beforeX curves ssC beforeP newEnts cand best)
  (setq best nil)
  (if (null tubePls)
    nil
    (progn
      (setq oldCm (getvar "CMDECHO"))
      (setq oldPe (getvar "PEDITACCEPT"))
      (setq oldOsm (getvar "OSMODE"))
      (setq oldCl (getvar "CLAYER"))
      (setvar "CMDECHO" 0)
      (setvar "PEDITACCEPT" 1)
      (setvar "OSMODE" 0)

      (setq beforeR (entlast))
      (vl-cmdf "_.REGION" (dzo415_ss_from_list tubePls) "")
      (setq regEnts (dzo415_collect_new_ents beforeR))

      (if regEnts
        (progn
          (setq ssReg (dzo415_ss_from_list regEnts))
          (setq beforeU (entlast))
          (vl-cmdf "_.UNION" ssReg "")
          (setq uniEnts (dzo415_collect_new_ents beforeU))
          (if uniEnts
            (setq regU (car (last uniEnts)))
            (setq regU (entlast))
          )

          (if (and regU (entget regU))
            (progn
              (setq beforeX (entlast))
              (vl-cmdf "_.EXPLODE" regU)
              (setq curves (dzo415_collect_new_ents beforeX))

              (if curves
                (progn
                  (setq ssC (dzo415_ss_from_list curves))
                  (setq beforeP (entlast))
                  (setq oldPEDITACCEPT (getvar "PEDITACCEPT"))
                  (setvar "PEDITACCEPT" 1)
                  (vl-cmdf "_.PEDIT" "_M" ssC "" "_J" 0.0 "")
                  (setvar "PEDITACCEPT" oldPEDITACCEPT)
                  (dzo418_flush_cmd)
                  (setq newEnts (dzo415_collect_new_ents beforeP))
                  (setq cand (append curves newEnts))
                  (setq best (dzo415_pick_largest_closed_poly cand))
                  (if (null best)
                    (setq best (dzo415_pick_any_poly cand))
                  )
                  (if (null best)
                    (setq best (dzo415_build_lwpoly_from_curves curves lay))
                  )
                  (if best
                    (progn
                      (dzo415_force_close_poly best)
                      (dzo415_delete_ents (vl-remove best cand))
                    )
                  )
                )
              )
            )
          )
        )
      )

      (dzo418_flush_cmd)
      (setvar "CMDECHO" oldCm)
      (setvar "PEDITACCEPT" oldPe)
      (setvar "OSMODE" oldOsm)
      (setvar "CLAYER" oldCl)

      best
    )
  )
)

(defun g417_take (lst n / out i)
  (setq out nil i 0)
  (while (and lst (< i n))
    (setq out (cons (car lst) out))
    (setq lst (cdr lst))
    (setq i (1+ i))
  )
  (reverse out)
)

(defun g417_nthcdr (n lst / i)
  (setq i 0)
  (while (and lst (< i n))
    (setq lst (cdr lst))
    (setq i (1+ i))
  )
  lst
)

(defun g417_rotate (lst k / a b)
  (if (or (null lst) (<= k 0))
    lst
    (progn
      (setq a (g417_nthcdr k lst))
      (setq b (g417_take lst k))
      (append a b)
    )
  )
)

(defun g417_set_nth (lst idx val / i out)
  (setq i 0 out nil)
  (while lst
    (setq out (cons (if (= i idx) val (car lst)) out))
    (setq lst (cdr lst))
    (setq i (1+ i))
  )
  (reverse out)
)

(defun g417_nearest_vertex (p pts / i bestI bestD d)
  (setq i 0 bestI 0 bestD 1e99)
  (while (< i (length pts))
    (setq d (distance p (nth i pts)))
    (if (< d bestD)
      (progn
        (setq bestD d)
        (setq bestI i)
      )
    )
    (setq i (1+ i))
  )
  (list bestI (nth bestI pts) bestD)
)

(defun g417_farthest_index (p pts / i bestI bestD d)
  (setq i 0 bestI 0 bestD -1.0)
  (while (< i (length pts))
    (setq d (distance p (nth i pts)))
    (if (> d bestD)
      (progn
        (setq bestD d)
        (setq bestI i)
      )
    )
    (setq i (1+ i))
  )
  bestI
)

(defun g417_lwpoly_parse (ed / pts bul sw ew curIdx pr code val)
  (setq pts nil bul nil sw nil ew nil curIdx -1)
  (while ed
    (setq pr (car ed))
    (setq code (car pr))
    (setq val (cdr pr))
    (cond
      ((= code 10)
        (setq pts (append pts (list (list (car val) (cadr val) 0.0))))
        (setq bul (append bul (list 0.0)))
        (setq sw  (append sw  (list nil)))
        (setq ew  (append ew  (list nil)))
        (setq curIdx (1- (length pts)))
      )
      ((and (>= curIdx 0) (= code 42))
        (setq bul (g417_set_nth bul curIdx val))
      )
      ((and (>= curIdx 0) (= code 40))
        (setq sw (g417_set_nth sw curIdx val))
      )
      ((and (>= curIdx 0) (= code 41))
        (setq ew (g417_set_nth ew curIdx val))
      )
    )
    (setq ed (cdr ed))
  )
  (list pts bul sw ew)
)

(defun g417_lwpoly_rebuild (pre pts bul sw ew / n i x y out)
  (setq n (length pts))
  (setq out nil)
  (while pre
    (if (= (car (car pre)) 90)
      (setq out (cons (cons 90 n) out))
      (setq out (cons (car pre) out))
    )
    (setq pre (cdr pre))
  )
  (setq out (reverse out))

  (setq i 0)
  (while (< i n)
    (setq x (car (nth i pts)))
    (setq y (cadr (nth i pts)))
    (setq out (append out (list (cons 10 (list x y)))))
    (if (nth i sw) (setq out (append out (list (cons 40 (nth i sw))))))
    (if (nth i ew) (setq out (append out (list (cons 41 (nth i ew))))))
    (if (and (nth i bul) (/= (nth i bul) 0.0))
      (setq out (append out (list (cons 42 (nth i bul)))))
    )
    (setq i (1+ i))
  )
  out
)

(defun g417_lwpoly_rotate_start (e k / ed pre rest parsed pts bul sw ew n pts2 bul2 sw2 ew2 newEd)
  (setq ed (entget e))
  (if (/= (cdr (assoc 0 ed)) "LWPOLYLINE")
    nil
    (progn
      (setq pre nil rest ed)
      (while (and rest (/= (car (car rest)) 10))
        (setq pre (append pre (list (car rest))))
        (setq rest (cdr rest))
      )
      (setq parsed (g417_lwpoly_parse ed))
      (setq pts (nth 0 parsed))
      (setq bul (nth 1 parsed))
      (setq sw  (nth 2 parsed))
      (setq ew  (nth 3 parsed))
      (setq n (length pts))
      (if (< n 3)
        nil
        (progn
          (setq k (rem k n))
          (if (< k 0) (setq k (+ k n)))
          (setq pts2 (g417_rotate pts k))
          (setq bul2 (g417_rotate bul k))
          (setq sw2  (g417_rotate sw k))
          (setq ew2  (g417_rotate ew k))
          (setq newEd (g417_lwpoly_rebuild pre pts2 bul2 sw2 ew2))
          (entmod newEd)
          (entupd e)
          T
        )
      )
    )
  )
)

(defun g417_move_outline_seam (outline pick mainPts / nearV outPts k)
  (if (and outline pick mainPts)
    (progn
      (if (= (cdr (assoc 0 (entget outline))) "LWPOLYLINE")
        (progn
          (setq nearV (g417_nearest_vertex pick mainPts))
          (setq outPts (g365_get_pts outline))
          (if (and outPts (>= (length outPts) 3))
            (progn
              (setq k (g417_farthest_index (cadr nearV) outPts))
              (g417_lwpoly_rotate_start outline k)
            )
          )
        )
      )
    )
  )
  T
)

(vl-load-com)

(defun DZO--ename (x)
  (cond
    ((= (type x) 'ENAME) x)
    ((= (type x) 'VLA-OBJECT) (vlax-vla-object->ename x))
    (t nil)
  )
)

(defun DZO--pt2d (p)
  (cond
    ((and (listp p) (>= (length p) 2)) (list (car p) (cadr p)))
    (t p)
  )
)

(defun DZO--pt3d (p)
  (setq p (DZO--pt2d p))
  (list (car p) (cadr p) 0.0)
)

(defun dzo-safe-closest-point (crv pt / e r)
  (setq e (DZO--ename crv))
  (if (not e)
    (DZO--pt2d pt)
    (progn
      (setq r (vl-catch-all-apply 'vlax-curve-getClosestPointTo (list e (DZO--pt3d pt))))
      (if (vl-catch-all-error-p r)
        (DZO--pt2d pt)
        (DZO--pt2d r)
      )
    )
  )
)

(defun dzo-safe-dist-at-point (crv pt / e cp r)
  (setq e  (DZO--ename crv))
  (if (not e)
    0.0
    (progn
      (setq cp (dzo-safe-closest-point e pt))
      (setq r  (vl-catch-all-apply 'vlax-curve-getDistAtPoint (list e (DZO--pt3d cp))))
      (if (vl-catch-all-error-p r)
        0.0
        r
      )
    )
  )
)

(defun DZO--safe-props (e / ed pr)
  (setq e  (DZO--ename e))
  (setq ed (entget e))
  (setq pr (vl-remove nil (list (assoc 8 ed) (assoc 62 ed) (assoc 6 ed) (assoc 48 ed) (assoc 370 ed))))
  pr
)

(defun DZO--get-lwpts (e / ed pts x)
  (setq e  (DZO--ename e))
  (setq ed (entget e) pts '())
  (foreach x ed
    (if (= (car x) 10)
      (cond
        ((listp (cdr x)) (setq pts (append pts (list (DZO--pt2d (cdr x))))))
        ((and (listp x) (>= (length x) 3))
         (setq pts (append pts (list (list (cadr x) (caddr x))))))
      )
    )
  )
  pts
)

(defun DZO--entmakex-lwpoly (pts props closed70 / lst e)
  (if (null closed70) (setq closed70 0))
  (setq lst
    (append
      (list (cons 0 "LWPOLYLINE") (cons 100 "AcDbEntity"))
      props
      (list (cons 100 "AcDbPolyline") (cons 90 (length pts)) (cons 70 closed70))
      (apply 'append (mapcar '(lambda (p) (list (cons 10 (DZO--pt2d p)))) pts))
    )
  )
  (entmake lst)
  (setq e (entlast))
  e
)

(defun DZO--ensure-last (lst pt)
  (if (or (null lst) (> (distance (DZO--pt2d (last lst)) (DZO--pt2d pt)) 1e-6))
    (append lst (list (DZO--pt2d pt)))
    lst
  )
)

(defun DZO--unit (vx vy / l)
  (setq l (sqrt (+ (* vx vx) (* vy vy))))
  (if (> l 1e-12)
    (list (/ vx l) (/ vy l) l)
    (list 0.0 0.0 0.0)
  )
)


(defun DZO--perp-axis-from-curve (crv pt / obj par der dx dy)
  ;; ORTHO: curve tangent -> choose dominant axis, return perpendicular unit (rx ry)
  (setq obj (if (vlax-objectp crv) crv (vlax-ename->vla-object crv)))
  (setq par (vl-catch-all-apply 'vlax-curve-getParamAtPoint (list obj pt)))
  (if (vl-catch-all-error-p par)
    (progn
      (list 1.0 0.0)
    )
    (progn
      (setq der (vl-catch-all-apply 'vlax-curve-getFirstDeriv (list obj par)))
      (if (vl-catch-all-error-p der)
        (list 1.0 0.0)
        (progn
          (setq dx (car der) dy (cadr der))
          (if (>= (abs dx) (abs dy))
            (list 0.0 1.0)  ;; curve ~ horizontal -> perp is vertical
            (list 1.0 0.0)  ;; curve ~ vertical   -> perp is horizontal
          )
        )
      )
    )
  )
)

(defun DZO--curve-total (crv)
  (setq crv (DZO--ename crv))
  (if (not crv)
    0.0
    (vlax-curve-getDistAtParam crv (vlax-curve-getEndParam crv))
  )
)

(defun DZO--clamp (v a b)
  (cond ((< v a) a) ((> v b) b) (t v))
)

(defun DZO--distpair10 (distMid dirSign maxDist half / d1 d2)
  ;; distMid etrafýnda ±half (toplam 2*half) olacak þekilde iki mesafe üretir.
  ;; Uçlarda (0 / maxDist) 10 birimi korumak için içeri kaydýrýr.
  (setq full (* 2.0 half))
  (setq d1 (- distMid (* half dirSign)))
  (setq d2 (+ distMid (* half dirSign)))

  ;; önce kaba clamp
  (setq d1 (DZO--clamp d1 0.0 maxDist))
  (setq d2 (DZO--clamp d2 0.0 maxDist))

  ;; eðer 10 birim bozulduysa, uca göre düzelt
  (if (< (abs (- d2 d1)) (- full 1e-3))
    (cond
      ;; baþlangýca çok yakýn
      ((< distMid half)
        (if (>= dirSign 0.0)
          (progn (setq d1 0.0) (setq d2 (DZO--clamp full 0.0 maxDist)))
          (progn (setq d2 0.0) (setq d1 (DZO--clamp full 0.0 maxDist)))
        )
      )
      ;; sona çok yakýn
      ((< (- maxDist distMid) half)
        (if (>= dirSign 0.0)
          (progn (setq d2 maxDist) (setq d1 (DZO--clamp (- maxDist full) 0.0 maxDist)))
          (progn (setq d1 maxDist) (setq d2 (DZO--clamp (- maxDist full) 0.0 maxDist)))
        )
      )
    )
  )

  (list d1 d2)
)

(defun DZO--closest-on-seg (a b p / ax ay bx by px py abx aby apx apy den tt cx cy dx dy)
  (setq a (DZO--pt2d a) b (DZO--pt2d b) p (DZO--pt2d p))
  (setq ax (car a) ay (cadr a))
  (setq bx (car b) by (cadr b))
  (setq px (car p) py (cadr p))
  (setq abx (- bx ax) aby (- by ay))
  (setq apx (- px ax) apy (- py ay))
  (setq den (+ (* abx abx) (* aby aby)))
  (if (< den 1e-12)
    (list a (+ (* apx apx) (* apy apy)))
    (progn
      (setq tt (/ (+ (* apx abx) (* apy aby)) den))
      (setq tt (DZO--clamp tt 0.0 1.0))
      (setq cx (+ ax (* tt abx)))
      (setq cy (+ ay (* tt aby)))
      (setq dx (- px cx))
      (setq dy (- py cy))
      (list (list cx cy) (+ (* dx dx) (* dy dy)))
    )
  )
)

(defun DZO--poly-closest-seg-index (pts p closed70 / n lim i a b res d2 bestI bestD)
  (setq pts (mapcar 'DZO--pt2d pts))
  (setq p (DZO--pt2d p))
  (setq n (length pts))
  (if (< n 2)
    0
    (progn
      (setq lim (if (/= (logand closed70 1) 0) n (1- n)))
      (setq i 0 bestI 0 bestD 1e99)
      (while (< i lim)
        (setq a (nth i pts))
        (setq b (nth (if (= i (1- n)) 0 (1+ i)) pts))
        (setq res (DZO--closest-on-seg a b p))
        (setq d2 (cadr res))
        (if (< d2 bestD)
          (progn (setq bestD d2) (setq bestI i))
        )
        (setq i (1+ i))
      )
      bestI
    )
  )
)

(defun DZO--poly-closest-on-seg (pts segIdx p closed70 / n a b res)
  (setq pts (mapcar 'DZO--pt2d pts))
  (setq p (DZO--pt2d p))
  (setq n (length pts))
  (if (< n 2)
    p
    (progn
      (setq a (nth segIdx pts))
      (setq b (nth (if (= segIdx (1- n)) 0 (1+ segIdx)) pts))
      (setq res (DZO--closest-on-seg a b p))
      (car res)
    )
  )
)

(defun DZO--cpE-side (crv cp join rx ry / e d tot pPlus pMin v1x v1y v2x v2y s1 s2)
  (setq e (DZO--ename crv))
  (setq cp (DZO--pt2d cp))
  (if (not e)
    cp
    (progn
      (setq d   (dzo-safe-dist-at-point e cp))
      (setq tot (DZO--curve-total e))

      (setq pPlus (vlax-curve-getPointAtDist e (min tot (+ d join))))
      (setq pMin  (vlax-curve-getPointAtDist e (max 0.0 (- d join))))

      (setq pPlus (DZO--pt2d pPlus))
      (setq pMin  (DZO--pt2d pMin))

      (setq v1x (- (car pPlus) (car cp)))
      (setq v1y (- (cadr pPlus) (cadr cp)))
      (setq v2x (- (car pMin) (car cp)))
      (setq v2y (- (cadr pMin) (cadr cp)))

      (setq s1 (+ (* v1x rx) (* v1y ry)))
      (setq s2 (+ (* v2x rx) (* v2y ry)))

      (if (>= s1 s2) pPlus pMin)
    )
  )
)

(defun DZO--cpE-side-flag (crv cp join choosePlus / e d tot pPlus pMin)
  (setq e (DZO--ename crv))
  (setq cp (DZO--pt2d cp))
  (if (not e)
    cp
    (progn
      (setq d   (dzo-safe-dist-at-point e cp))
      (setq tot (DZO--curve-total e))
      (setq pPlus (DZO--pt2d (vlax-curve-getPointAtDist e (min tot (+ d join)))))
      (setq pMin  (DZO--pt2d (vlax-curve-getPointAtDist e (max 0.0 (- d join)))))
      (if choosePlus pPlus pMin)
    )
  )
)

(defun DZO--shorten-toward-cp (crv cp cpE short / e dcp dE tot dNew)
  (setq e (DZO--ename crv))
  (setq cp  (DZO--pt2d cp))
  (setq cpE (DZO--pt2d cpE))
  (if (not e)
    cpE
    (progn
      (setq dcp (dzo-safe-dist-at-point e cp))
      (setq dE  (dzo-safe-dist-at-point e cpE))
      (setq tot (DZO--curve-total e))

      (if (>= dE dcp)
        (setq dNew (max dcp (- dE short)))
        (setq dNew (min dcp (+ dE short)))
      )
      (DZO--pt2d (vlax-curve-getPointAtDist e (DZO--clamp dNew 0.0 tot)))
    )
  )
)

(defun DZO--insert-detour (crv attachA attachB midPts / e pts props pA pB tmp sIdx eIdx head tail k newPts firstPt lastPt keepScore revScore midNorm p)
  (setq e     (DZO--ename crv))
  (setq pts   (DZO--get-lwpts e))
  (setq props (DZO--safe-props e))

  (setq attachA (dzo-safe-closest-point e attachA))
  (setq attachB (dzo-safe-closest-point e attachB))

  (setq pA (vl-catch-all-apply 'vlax-curve-getParamAtPoint (list e (DZO--pt3d attachA))))
  (setq pB (vl-catch-all-apply 'vlax-curve-getParamAtPoint (list e (DZO--pt3d attachB))))
  (if (or (vl-catch-all-error-p pA) (vl-catch-all-error-p pB))
    crv
    (progn
      (if (> pA pB)
        (progn
          (setq tmp attachA attachA attachB attachB tmp)
          (setq tmp pA pA pB pB tmp)
        )
      )
      ;; midPts tek nokta ya da karisik liste gelebilir; sadece gercek noktalari kullan.
      (setq midNorm '())
      (cond
        ((null midPts)
          (setq midPts nil)
        )
        ((not (listp midPts))
          (setq midPts nil)
        )
        ((and (numberp (car midPts)) (numberp (cadr midPts)))
          (setq midPts (list (DZO--pt2d midPts)))
        )
        (T
          (foreach p midPts
            (if (and (listp p) (numberp (car p)) (numberp (cadr p)))
              (setq midNorm (append midNorm (list (DZO--pt2d p))))
            )
          )
          (setq midPts midNorm)
        )
      )

      ;; Polyline cizim yonu ters olsa bile agiz eslesmesi yakinliga gore kalsin.
      (if (and midPts (cdr midPts)
               (listp attachA) (numberp (car attachA)) (numberp (cadr attachA))
               (listp attachB) (numberp (car attachB)) (numberp (cadr attachB)))
        (progn
          (setq firstPt (DZO--pt2d (car midPts)))
          (setq lastPt  (DZO--pt2d (car (last midPts))))
          (setq keepScore (+ (distance (DZO--pt2d attachA) firstPt) (distance (DZO--pt2d attachB) lastPt)))
          (setq revScore  (+ (distance (DZO--pt2d attachA) lastPt)  (distance (DZO--pt2d attachB) firstPt)))
          (if (< revScore keepScore)
            (setq midPts (reverse midPts))
          )
        )
      )

      (setq sIdx (fix pA))
      (setq eIdx (fix pB))

      (setq head '() k 0)
      (while (<= k sIdx)
        (setq head (append head (list (nth k pts))))
        (setq k (1+ k))
      )
      (setq head (DZO--ensure-last head attachA))

      (setq tail '() k (1+ eIdx))
      (while (< k (length pts))
        (setq tail (append tail (list (nth k pts))))
        (setq k (1+ k))
      )

      (setq newPts (append head (mapcar 'DZO--pt2d midPts) (list attachB) tail))

      (entdel e)
      (DZO--entmakex-lwpoly newPts props 0)
    )
  )
)

(defun DZO--block-effective-name (en / vla nm ed)
  (setq en (DZO--ename en))
  (if (not en)
    nil
    (progn
      (setq ed (entget en))
      (setq nm (cdr (assoc 2 ed)))
      (if (and nm (= (substr nm 1 1) "*"))
        (progn
          (setq vla (vlax-ename->vla-object en))
          (if (vlax-property-available-p vla 'EffectiveName)
            (setq nm (vla-get-EffectiveName vla))
          )
        )
      )
      nm
    )
  )
)

(defun DZO--skip-block-p (blk / nm nmU)
  (setq nm  (DZO--block-effective-name blk))
  (setq nmU (strcase (if nm nm "")))
  (if (or (vl-string-search "FLASOR" nmU)
          (vl-string-search "FLAR"   nmU))
    T
    nil
  )
)

(defun DZO--floor (x)
  (if (>= x 0.0) (fix x) (1- (fix x)))
)

(defun DZO--cellkey (p cell / cx cy)
  (setq p (DZO--pt2d p))
  (setq cx (DZO--floor (/ (car p) cell)))
  (setq cy (DZO--floor (/ (cadr p) cell)))
  (list cx cy)
)

(defun DZO--cells-put (cells key val / rec)
  (if (setq rec (assoc key cells))
    (subst (cons key (cons val (cdr rec))) rec cells)
    (cons (list key val) cells)
  )
)

(defun DZO--uf-init (parents x)
  (if (assoc x parents) parents (cons (cons x x) parents))
)

(defun DZO--uf-find (parents x / p)
  (setq p (cdr (assoc x parents)))
  (if (null p) x
    (progn
      (while (and p (not (equal p x)))
        (setq x p)
        (setq p (cdr (assoc x parents)))
      )
      x
    )
  )
)

(defun DZO--uf-union (parents a b / ra rb rec)
  (setq ra (DZO--uf-find parents a))
  (setq rb (DZO--uf-find parents b))
  (if (not (equal ra rb))
    (progn
      (setq rec (assoc rb parents))
      (if rec
        (setq parents (subst (cons rb ra) rec parents))
        (setq parents (cons (cons rb ra) parents))
      )
    )
  )
  parents
)

(defun DZO--groups-build (parents data / groups blk rep r rec)
  (setq groups '())
  (foreach rec data
    (setq blk (car rec))
    (setq rep (DZO--uf-find parents blk))
    (if (setq r (assoc rep groups))
      (setq groups (subst (cons rep (cons rec (cdr r))) r groups))
      (setq groups (cons (list rep rec) groups))
    )
  )
  groups
)

(defun DZO--choosePlus-main (mainCrv ip cp join / vvx vvy uu dx dy rx ry cpE d tot pPlus)
  (setq ip (DZO--pt2d ip))
  (setq cp (DZO--pt2d cp))

  (setq vvx (- (car ip) (car cp)))
  (setq vvy (- (cadr ip) (cadr cp)))
  (setq uu (DZO--unit vvx vvy))
  (setq dx (car uu) dy (cadr uu))

  (setq rperp (DZO--perp-axis-from-curve mainTmp cpMain))
              (setq rx (car rperp))
              (setq ry (cadr rperp))

  (setq cpE (DZO--cpE-side mainCrv cp join rx ry))

  (setq d   (dzo-safe-dist-at-point mainCrv cp))
  (setq tot (DZO--curve-total mainCrv))
  (setq pPlus (DZO--pt2d (vlax-curve-getPointAtDist (DZO--ename mainCrv) (min tot (+ d join)))))

  (if (<= (distance cpE pPlus) 1e-6) T nil)
)

(defun DZO--point-toward (a b dist / a2 b2 vx vy uu)
  (setq a2 (DZO--pt2d a))
  (setq b2 (DZO--pt2d b))
  (setq vx (- (car b2) (car a2)))
  (setq vy (- (cadr b2) (cadr a2)))
  (setq uu (DZO--unit vx vy))
  (if (> (caddr uu) 1e-12)
    (list (+ (car a2) (* (car uu) dist)) (+ (cadr a2) (* (cadr uu) dist)))
    a2
  )
)

(defun DZO--calc-L-corner (S B uPerp / S2 B2 c1 c2 d1 d2)
  ;; ORTHO KÖÞE: Baðlantýlar sadece 0/90/180/270 olacak þekilde,
  ;; S -> corner -> B iki eksenli (yatay/dikey) kýrýlým üretir.
  (setq S2 (DZO--pt2d S))
  (setq B2 (DZO--pt2d B))

  ;; Ýki olasý L köþe
  (setq c1 (list (car S2) (cadr B2))) ; önce dikey, sonra yatay
  (setq c2 (list (car B2) (cadr S2))) ; önce yatay, sonra dikey

  ;; S'den daha kýsa ilk bacaðý seç
  (setq d1 (distance S2 c1))
  (setq d2 (distance S2 c2))
  (if (<= d1 d2) c1 c2)
)


(defun DZO--ortho-first-axis (ip cp / dx dy)
  ;; T => once X, NIL => once Y
  (setq dx (abs (- (car ip) (car cp))))
  (setq dy (abs (- (cadr ip) (cadr cp))))
  (< dx dy)
)

(defun DZO--axis-horiz-at (crv cp / e prm der dx dy)
  ;; Ana hattin tangent yonune gore yatay mi (T) dikey mi (NIL)
  (setq e (DZO--ename crv))
  (if (not e)
    T
    (progn
      (setq prm (vl-catch-all-apply 'vlax-curve-getParamAtPoint (list e (DZO--pt3d cp))))
      (if (vl-catch-all-error-p prm)
        T
        (progn
          (setq der (vl-catch-all-apply 'vlax-curve-getFirstDeriv (list e prm)))
          (if (vl-catch-all-error-p der)
            T
            (progn
              (setq dx (abs (car der)))
              (setq dy (abs (cadr der)))
              (>= dx dy)
            )
          )
        )
      )
    )
  )
)

;; Ana hattin yonunu, cp noktasinin hemen ilerisinden/gerisinden (choosePlus) örnekleyerek bulur.
;; Köþe (vertex) üstünde derivative belirsiz kaldýðýnda, ilk kolun gerçekten ana hat hizasýnda
;; baþlamasý için kullanýlýr.
(defun DZO--axis-horiz-at2 (crv cp choosePlus / e prm dist maxDist dist2 p2 vx vy)
  (setq e (DZO--ename crv))
  (if (not e)
    T
    (progn
      (setq prm (vl-catch-all-apply 'vlax-curve-getParamAtPoint (list e (DZO--pt3d cp))))
      (if (vl-catch-all-error-p prm)
        (DZO--axis-horiz-at crv cp)
        (progn
          (setq dist    (vlax-curve-getDistAtParam e prm))
          (setq maxDist (vlax-curve-getDistAtParam e (vlax-curve-getEndParam e)))
          ;; 1.0 birimlik örnekleme, köþe noktalarýnda yönü netleþtirir
          (setq dist2 (if choosePlus (+ dist 1.0) (- dist 1.0)))
          (setq dist2 (DZO--clamp dist2 0.0 maxDist))
          (setq p2 (DZO--pt2d (vlax-curve-getPointAtDist e dist2)))
          (setq vx (- (car p2) (car cp)))
          (setq vy (- (cadr p2) (cadr cp)))
          (if (and (< (abs vx) 1e-6) (< (abs vy) 1e-6))
            (DZO--axis-horiz-at crv cp)
            (>= (abs vx) (abs vy))
          )
        )
      )
    )
  )
)

(defun DZO--perp-axis-from-curve (crv pt / prm deriv tx ty)
  ;; ORTHO için ana hattýn tangent yönüne göre (x/y) eksen-perp döndürür.
  ;; dönüþ: (rx ry) birim vektör (mutlak eksen), iþaret sideFact ile verilir.
  (setq prm (vlax-curve-getParamAtPoint (DZO--ename crv) (DZO--pt3d pt)))
  (setq deriv (vlax-curve-getFirstDeriv (DZO--ename crv) prm))
  (setq tx (car deriv) ty (cadr deriv))
  (if (> (abs tx) (abs ty))
    (list 0.0 1.0)   ;; tangent yatay => perp dikey
    (list 1.0 0.0)   ;; tangent dikey => perp yatay
  )
)

(defun DZO--calc-L-corner-mode (S B mode / S2 B2)
  ;; ORTHO KÖÞE (MODLU): mode = 'vfirst veya 'hfirst
  ;; vfirst: (Sx, By)  -> önce dikey, sonra yatay
  ;; hfirst: (Bx, Sy)  -> önce yatay, sonra dikey
  (setq S2 (DZO--pt2d S))
  (setq B2 (DZO--pt2d B))
  (if (= mode 'vfirst)
    (list (car S2) (cadr B2))
    (list (car B2) (cadr S2))
  )
)
(defun DZO--lmode-along-main (cpA cpB / a b dx dy)
  ;; ORTHO zorlanan yerlerde ilk bacak her zaman ana hat hizasinda olsun:
  ;; cpA->cpB vektoru ana hattin tangent eksenini temsil eder.
  ;; yatay => 'hfirst (ilk bacak yatay), dikey => 'vfirst (ilk bacak dikey)
  (setq a (DZO--pt2d cpA))
  (setq b (DZO--pt2d cpB))
  (setq dx (abs (- (car b) (car a))))
  (setq dy (abs (- (cadr b) (cadr a))))
  (if (>= dx dy) 'hfirst 'vfirst)
)

;; ORTHO zorlanan baglantilarda ana hat hizasini secmek icin:
;; cpCur noktasinda egri uzerinde iki yonde (once/sonra) kucuk bir ornek alinir.
;; Blok vektoru ile daha iyi hizalanan yon secilir; bu sayede cpCur bir vertex uzerindeyken
;; "yanlis segment" baz alinmaz (blok sag/ustte kalinca gorulen bozulma).
(defun DZO--lmode-along-main-at (crv cpCur ip / e cp b d len eps d1 d2 p1 p2 v1 v2 vt dot1 dot2 vx vy)
  (setq e (DZO--ename crv))
  (setq cp (DZO--pt2d cpCur))
  (setq b  (DZO--pt2d ip))
  (setq vt (list (- (car b) (car cp)) (- (cadr b) (cadr cp)) 0.0))

  ;; dist clamp
  (setq d   (vlax-curve-getDistAtPoint e cp))
  (setq len (vlax-curve-getDistAtParam e (vlax-curve-getEndParam e)))
  (setq eps 1.0)
  (setq d1 (max 0.0 (- d eps)))
  (setq d2 (min len (+ d eps)))
  (setq p1 (DZO--pt2d (vlax-curve-getPointAtDist e d1)))
  (setq p2 (DZO--pt2d (vlax-curve-getPointAtDist e d2)))

  ;; v1: p1->cp, v2: cp->p2
  (setq v1 (list (- (car cp) (car p1)) (- (cadr cp) (cadr p1)) 0.0))
  (setq v2 (list (- (car p2) (car cp)) (- (cadr p2) (cadr cp)) 0.0))

  (setq dot1 (abs (+ (* (car v1) (car vt)) (* (cadr v1) (cadr vt)))))
  (setq dot2 (abs (+ (* (car v2) (car vt)) (* (cadr v2) (cadr vt)))))

  (if (>= dot2 dot1)
    (progn (setq vx (car v2)) (setq vy (cadr v2)))
    (progn (setq vx (car v1)) (setq vy (cadr v1)))
  )

  (if (> (abs vx) (abs vy)) 'hfirst 'vfirst)
)

(defun DZO--APPLY (crv0 ss / crv i blk ip blk2 ip2
               ptsMain propsMain mainTmp mainClosed
               joinCand short shift approach
               vvx vvy uu dx dy len rx ry ipRin
               nearLim mainFarLim mergeOff
               cell cells
               parents data
               groups
               forcedReps sideMap segMap
               anchorMap stemMap  remoteMap mergeMap
               dirMap dirRec udir mdx mdy p1 ipb p1b pJoin stemRec stemA stemB cpSec pStep pStepb
               g rep recs r bestRec bestIp bestD dNow segIdx choosePlus
               procData anchorRec remote
               forceMain isAnchor cpMain cpCur cpE cpEshort
               uTan uPerp corner1 corner2 paramCur distEnds
               pDown pDownRin uDirRemote anchorStemDir
               key cx cy ix iy rec item mergePt isTargetSide
               sX sY sideFact 
               ipAvg pMid paramMid deriv Tlen Tx Ty Lx Ly dotProd dirSign distMid distDown distDownRin maxDist
               pMerge pMergeRin pLeft pRight ipLeft ipRight pMainTop pMainBot ipTop ipBot yTop yBot pTopA pBotA pTopB pBotB pTopDrop pBotDrop scoreA scoreB outsideLeft fromTop sideMode shortIp longIp calcCrv)

  (vl-load-com)

  (setq joinCand 20.0)
  (setq short    10.0)
  (setq shift    10.0)
  (setq approach 10.0)

  (setq nearLim    100.0)
  (setq mainFarLim 200.0)
  (setq mergeOff   50.0)

  (setq crv0 (DZO--ename crv0))

  (if (not (and crv0 (entget crv0)))
    (progn (princ "\nDZ: Gecersiz polyline.") (princ))
    (if (not (and ss (= (type ss) 'PICKSET) (> (sslength ss) 0)))
      (progn (princ "\nDZ: Block secimi yok.") (princ))
      (progn

        (setq ptsMain   (DZO--get-lwpts crv0))
        (setq propsMain (DZO--safe-props crv0))
        (setq mainClosed (cdr (assoc 70 (entget crv0))))
        (if (null mainClosed) (setq mainClosed 0))
        (setq mainClosed (if (/= (logand mainClosed 1) 0) 1 0))
        (setq mainTmp   (DZO--entmakex-lwpoly ptsMain propsMain mainClosed))

        (setq cell    nearLim)
        (setq cells   '())
        (setq parents '())
        (setq data    '())

        (setq i 0)
        (while (< i (sslength ss))
          (setq blk (ssname ss i))
          (if (not (DZO--skip-block-p blk))
            (progn
              (setq ip (DZO--pt2d (cdr (assoc 10 (entget blk)))))

              (setq parents (DZO--uf-init parents blk))
              (setq data (append data (list (list blk ip))))

              (setq key (DZO--cellkey ip cell))
              (setq cx (car key) cy (cadr key))

              (setq ix -1)
              (while (<= ix 1)
                (setq iy -1)
                (while (<= iy 1)
                  (setq rec (assoc (list (+ cx ix) (+ cy iy)) cells))
                  (if rec
                    (foreach item (cdr rec)
                      (setq blk2 (car item))
                      (setq ip2  (cadr item))
                      (if (and blk2 ip2 (<= (distance ip ip2) nearLim))
                        (setq parents (DZO--uf-union parents blk blk2))
                      )
                    )
                  )
                  (setq iy (1+ iy))
                )
                (setq ix (1+ ix))
              )

              (setq cells (DZO--cells-put cells (list cx cy) (list blk ip)))
            )
          )
          (setq i (1+ i))
        )

        (setq groups (DZO--groups-build parents data))

        (setq forcedReps '())
        (setq sideMap    '())
        (setq segMap     '())
        (setq anchorMap  '())
        (setq stemMap    '())
        (setq remoteMap  '())
        (setq mergeMap   '())
        (setq dirMap     '())

        (foreach g groups
          (setq rep  (car g))
          (setq recs (cdr g))

          (setq bestRec nil)
          (setq bestD   1e99)
          (foreach r recs
            (setq ip (cadr r))
            (setq cpMain (dzo-safe-closest-point mainTmp ip))
            (setq dNow (distance (DZO--pt2d ip) (DZO--pt2d cpMain)))
            (if (< dNow bestD)
              (progn (setq bestD dNow) (setq bestRec r))
            )
          )
          (if (null bestRec) (setq bestRec (car recs)))
          (setq bestIp (cadr bestRec))
          (setq anchorMap (cons (cons rep bestRec) anchorMap))

          (setq cpMain (dzo-safe-closest-point mainTmp bestIp))
          (setq stemMap (cons (cons rep (list (DZO--pt2d bestIp) (DZO--pt2d cpMain))) stemMap))
          (setq choosePlus (DZO--choosePlus-main mainTmp bestIp cpMain joinCand))
          (setq sideMap (cons (cons rep choosePlus) sideMap))
          (setq segIdx (DZO--poly-closest-seg-index ptsMain bestIp mainClosed))
          (setq segMap (cons (cons rep segIdx) segMap))

          (if (> (length recs) 1)
            (progn
              (if (> bestD mainFarLim)
                (progn
                  (setq remoteMap (cons (cons rep T) remoteMap))
                  (setq mergePt (DZO--point-toward bestIp cpMain mergeOff))
                  (setq mergeMap (cons (cons rep mergePt) mergeMap))

                  (setq udir (DZO--unit (- (car bestIp) (car cpMain)) (- (cadr bestIp) (cadr cpMain))))
                  (setq dirMap (cons (cons rep (list (car udir) (cadr udir))) dirMap))
                )
                (progn
                  (setq remoteMap (cons (cons rep nil) remoteMap))
                  (setq forcedReps (cons rep forcedReps))
                )
              )
            )
            (setq remoteMap (cons (cons rep nil) remoteMap))
          )
        )

        (setq procData '())
        (foreach g groups
          (setq rep  (car g))
          (setq recs (cdr g))
          (setq remote (cdr (assoc rep remoteMap)))
          (if (and remote (> (length recs) 1))
            (progn
              (setq anchorRec (cdr (assoc rep anchorMap)))
              (setq procData (append procData (list anchorRec)))
              (foreach r recs
                (if (not (equal (car r) (car anchorRec)))
                  (setq procData (append procData (list r)))
                )
              )
            )
            (setq procData (append procData recs))
          )
        )

        (setq crv crv0)

        (foreach rec procData
          (setq blk (car rec))
          (setq ip  (cadr rec))

          (setq rep (DZO--uf-find parents blk))
          (setq choosePlus (cdr (assoc rep sideMap)))
          (if (null choosePlus) (setq choosePlus T))
          (setq remote (cdr (assoc rep remoteMap)))

          (setq anchorRec (cdr (assoc rep anchorMap)))
          (setq isAnchor (and remote anchorRec (equal blk (car anchorRec))))
          (setq forceMain (if (member rep forcedReps) T nil))

          (cond
            (forceMain
              (progn
                (setq segIdx (cdr (assoc rep segMap)))
                (if (null segIdx) (setq segIdx 0))
                (setq cpMain (DZO--poly-closest-on-seg ptsMain segIdx ip mainClosed))
              )
            )
            (remote
              (if isAnchor
                (progn
                  (setq segIdx (cdr (assoc rep segMap)))
                  (if (null segIdx) (setq segIdx 0))
                  (setq cpMain (DZO--poly-closest-on-seg ptsMain segIdx ip mainClosed))
                )
                (progn
                  (setq cpMain (dzo-safe-closest-point mainTmp ip))
                )
              )
            )
            (T (setq cpMain (dzo-safe-closest-point mainTmp ip)))
          )

          (setq cpCur (dzo-safe-closest-point crv cpMain))

          (setq ip     (DZO--pt2d ip))
          (setq cpMain (DZO--pt2d cpMain))
          (setq cpCur  (DZO--pt2d cpCur))

          (setq vvx (- (car ip) (car cpMain)))
          (setq vvy (- (cadr ip) (cadr cpMain)))
          
          (setq orthoForced (and (> (abs vvx) 1e-6) (> (abs vvy) 1e-6)))
(setq shiftBlk (if orthoForced 10.0 shift))

;; ORTHO zorlamasi (diag) durumunda dx/dy eksenini sabitle:
;; - Bloktan ana hatta en kisa eksen (X veya Y) secilir.
;; - Böylece shiftBlk=10.0 gercekten 10 olarak kalir (capraz unit ile bozulmaz).
(if orthoForced
  (progn
    (setq firstX (>= (abs vvx) (abs vvy)))
    (setq dx (if firstX (if (>= vvx 0.0) 1.0 -1.0) 0.0))
    (setq dy (if firstX 0.0 (if (>= vvy 0.0) 1.0 -1.0)))
    (setq len 100.0)
  )
  (progn
    (setq uu (DZO--unit vvx vvy))
    (setq dx (car uu) dy (cadr uu) len (caddr uu))
  )
)

          (if (and remote (not isAnchor))
            (progn
              (setq uDirRemote (cdr (assoc rep dirMap)))
              (setq dx (car uDirRemote))
              (setq dy (cadr uDirRemote))
              (setq len 100.0)
            )
          )

          (if (> len 1e-9)
            (progn
              (setq rx dy)
              (setq ry (- dx))

              ;; =========================================================
              ;; 1. BLOK BACAK YONU VE TARAF KONTROLU (HERKES ICIN)
              ;; =========================================================
              (setq isTargetSide (or (> dy 1e-4) (< dx -1e-4)))
              (setq sideFact (if isTargetSide -1.0 1.0))

              ;; Sol/Ust taraf ise bacaklari ters yone cevir
              (setq ipRin
                (list
                  (+ (car ip) (* rx shiftBlk sideFact))
                  (+ (cadr ip) (* ry shiftBlk sideFact))
                )
              )
              (setq ipRin
                 (list 
                   (- (car ipRin) (* dx approach))
                   (- (cadr ipRin) (* dy approach))
                 )
              )
              
              ;; cpE noktasini da tarafa gore duzelt (Referans icin)
              (setq rx (* rx sideFact))
              (setq ry (* ry sideFact))

              ;; Remote + anchor + sol/ust ise ANA HAT UZERINDEKI CIKIS VERTEX'INI OBUR TARAFA AL
              ;; (blok bacagi/yonu degismez, sadece ana hatta degdigi taraf degisir)
              (if (and remote isAnchor isTargetSide)
                (setq choosePlus (if choosePlus nil T))
              )

              (if (or forceMain remote)
                (setq cpE (DZO--cpE-side-flag crv cpCur joinCand choosePlus))
                (setq cpE (DZO--cpE-side      crv cpCur joinCand rx ry))
              )

              (setq cpEshort (DZO--shorten-toward-cp crv cpCur cpE short))

              (if (> (distance cpCur cpEshort) 1e-4)
                (progn
                  
                  (if (and remote (not isAnchor))
                     ;; =====================================================
                     ;; DURUM A: UZAK BLOKLAR (REMOTE) -> L-SHAPE / MERGE
                     ;; =====================================================
                     ;; * Bu bloklar komsu hattina baglanmali (Merge).
                     ;; * Hesaplamalar 'crv' (islenmis hat) uzerinde yapilmali.
                     (progn
                       ;; pMerge: ip'den mergeOff kadar asagi
                       (setq pMerge
                        (list
                          (+ (car ip) (* (- dx) mergeOff))
                          (+ (cadr ip) (* (- dy) mergeOff))
                        )
                       )
                       ;; pMergeRin: ipRin hizasinda
                       (setq pMergeRin
                        (list
                          (+ (car pMerge) (- (car ipRin) (car ip)))
                          (+ (cadr pMerge) (- (cadr ipRin) (cadr ip)))
                        )
                       )
                       
                       ;; Ana hat uzerindeki noktalar (Mevcut 'crv' uzerinden alinir)
                       (setq cpCur    (dzo-safe-closest-point crv pMerge))
                       (setq cpEshort (dzo-safe-closest-point crv pMergeRin))
                       
                       ;; Baglanti: pMerge noktalarini kullan (L Sekli)
                       ;; ACI ZORLANAN (ORTHO) DURUMDA:
                       ;; Ilk kolu her zaman "ana hat hizasinda" baslatmak icin, cpCur noktasinda
                       ;; egri uzerinde iki yonde orneklenir ve bloða dogru daha iyi hizalanan
                       ;; segmentin ekseni secilir (vertex ustu sapmalari engeller).
                       (if orthoForced
                         (setq lmode (DZO--lmode-along-main-at crv cpCur ip))
                         (progn
                           (setq firstX (DZO--ortho-first-axis ip cpCur))
                           (setq lmode (if firstX 'hfirst 'vfirst))
                         )
                       )

                       (setq corner1 (DZO--calc-L-corner-mode cpCur    ip   lmode))
                       (setq corner2 (DZO--calc-L-corner-mode cpEshort ipRin lmode))

                       (setq crv (DZO--insert-detour crv cpCur cpEshort (list corner1 ip ipRin corner2)))
                     )
                     
                     ;; =====================================================
                     ;; DURUM B: YAKIN BLOKLAR (DIRECT CONNECT)
                     ;; =====================================================
                     ;; * Bu bloklar DIREKT ana hatta baglanmali.
                     ;; * Komsunun bacagina YAPISMAMALI.
                     ;; * Bu yuzden referans olarak 'mainTmp' (Temiz Hat) kullanilmali.
                     (progn
                        (if (and remote isAnchor)
                            ;; Anchor ozel durumu (Pahli Baglanti)
                            (progn
                              (setq distEnds (distance cpCur cpEshort))
                              (setq uTan (list (/ (- (car cpEshort) (car cpCur)) distEnds)
                                               (/ (- (cadr cpEshort) (cadr cpCur)) distEnds)))
                              (setq uPerp (list (- (cadr uTan)) (car uTan)))
                              (setq corner1 (DZO--calc-L-corner cpCur ip uPerp))
                              (setq corner2 (DZO--calc-L-corner cpEshort ipRin uPerp))
                              (setq crv (DZO--insert-detour crv cpCur cpEshort (list corner1 ip ipRin corner2)))
                            )
                            
                            ;; STANDART DIREKT BAGLANTI (VEKTOREL HIZALAMA)
                            (progn
                                ;; *** ONEMLI: Hesaplamalarda 'mainTmp' (Temiz Hat) kullan! ***
                                (setq calcCrv mainTmp) 
                                
                                ;; A. Orta noktayi bul
                                (setq ipAvg (list (/ (+ (car ip) (car ipRin)) 2.0) (/ (+ (cadr ip) (cadr ipRin)) 2.0)))
                                (setq pMid (dzo-safe-closest-point calcCrv ipAvg))
                                
                                ;; B. Hattin yonunu bul (Temiz hat uzerinden)
                                (setq paramMid (vlax-curve-getParamAtPoint (DZO--ename calcCrv) (DZO--pt3d pMid)))
                                (setq deriv (vlax-curve-getFirstDeriv (DZO--ename calcCrv) paramMid))
                                (setq Tlen (distance '(0 0 0) deriv))
                                (if (< Tlen 1e-9)
                                   (progn (setq Tx rx) (setq Ty ry))
                                   (progn (setq Tx (/ (car deriv) Tlen)) (setq Ty (/ (cadr deriv) Tlen)))
                                )

                                ;; C. Hizalama Yonu
                                (setq Lx (- (car ipRin) (car ip)))
                                (setq Ly (- (cadr ipRin) (cadr ip)))
                                (setq dotProd (+ (* Tx Lx) (* Ty Ly)))
                                (setq dirSign (if (>= dotProd 0) 1.0 -1.0))

                                ;; Remote + anchor + target side: reverse direction so the short piece is taken from the other side
                                (if (and remote isAnchor isTargetSide)
                                  (setq dirSign (- dirSign))
                                )
                                
                                ;; D. Sabit 10 birim aralik (Merkezden +/- 5.0)
                                (setq distMid (vlax-curve-getDistAtParam (DZO--ename calcCrv) paramMid))
                                (setq maxDist (DZO--curve-total calcCrv))
                                
                                (setq distPair (DZO--distpair10 distMid dirSign maxDist shift))
                                (setq distDown (car distPair))
                                (setq distDownRin (cadr distPair))
                                
                                ;; Noktalari Temiz Hat uzerinden al (Komsunun bacagina carpmaz)
                                (setq pDown    (DZO--pt2d (vlax-curve-getPointAtDist (DZO--ename calcCrv) distDown)))
                                (setq pDownRin (DZO--pt2d (vlax-curve-getPointAtDist (DZO--ename calcCrv) distDownRin)))

                                ;; Detour ekleme noktalarini guncel 'crv' uzerinde bul
                                ;; pDown temiz hat uzerinde oldugu icin, 'crv' uzerinde de govdeye denk gelir.
                                (setq cpCur    (dzo-safe-closest-point crv pDown))
                                (setq cpEshort (dzo-safe-closest-point crv pDownRin))
                                
                                ;; DIREKT BAGLANTI LISTESI
                                ;; ORTHO modunu ana hattin yonune gore sabitle (iki uc ayni mod kullanir)
                                (if orthoForced
                                (setq lmode (DZO--lmode-along-main-at crv cpCur ip))
                                (progn
                                  (setq firstX (DZO--ortho-first-axis ip cpCur))
                                  (setq lmode (if firstX 'hfirst 'vfirst))
                                )
                              )
                       ;; ORTHO zorlanan ve blok ana hattin ustunde/solunda ise
                       ;; kisa kolun blok tarafinda kalmasi icin mode'u corner->ip mesafesine gore sec
                       (if (and orthoForced isTargetSide)
                         (progn
                           (setq dxA (abs (- (car ip) (car cpCur))))
                           (setq dyA (abs (- (cadr ip) (cadr cpCur))))
                           ;; vfirst => corner->ip yatay (dx), hfirst => corner->ip dikey (dy)
                           (setq lmode (if (< dxA dyA) 'vfirst 'hfirst))
                         )
                       )
(setq corner1 (DZO--calc-L-corner-mode cpCur    ip   lmode))
                                (setq corner2 (DZO--calc-L-corner-mode cpEshort ipRin lmode))
                                (setq crv (DZO--insert-detour crv cpCur cpEshort (list corner1 ip ipRin corner2)))
                            )
                        )
                     )
                  )
                )
              )
            )
          )
        )

        (if mainTmp (entdel mainTmp))
      )
    )
  )
  (if (and crv (entget crv)) crv nil)
)

(defun DZO-DR--RUN (mainEnt pick dist / mainPts tol ss allEnts rootId assignedEnts lay mainCol tubePls scan e pl outline)
  (setq mainPts (g365_get_pts mainEnt))
  (if (or (null mainPts) (< (length mainPts) 2))
    (progn (princ "\nAna hat okunamadi / cok kisa.") nil)
    (progn
      (setq tol (DEG:CFG-TOL-NUM-OR 'DR_TREE_TOL 0.1))
      (if (<= dist 0.0)
        (progn (princ "\nGecersiz mesafe.") nil)
        (progn
          (setq lay (cdr (assoc 8 (entget mainEnt))))
          (setq mainCol (g365_effective_color mainEnt))
          ;; Iskelete dahil olacak nesneler, secilen ana hat ile AYNI layer'da olmalidir.
          (if (and lay (/= lay ""))
            (setq ss (ssget "X" (list (cons 0 "LWPOLYLINE,POLYLINE,LINE") (cons 8 lay))))
            (setq ss (ssget "X" '((0 . "LWPOLYLINE,POLYLINE,LINE"))))
          )
          (if (null ss)
            (progn (princ "\nHic nesne bulunamadi.") nil)
            (progn
              (setq allEnts (g372_ss_to_list ss))
              ;; Iskelete dahil olacak nesneler, secilen ana hat ile AYNI renkte olmalidir.
              (setq allEnts
                (vl-remove nil
                  (mapcar
                    '(lambda (en)
                       (if (= (g365_effective_color en) mainCol) en nil)
                     )
                    allEnts
                  )
                )
              )
              (setq rootId (g372_build_tree mainEnt mainPts allEnts tol))
              (setq assignedEnts (dzo415_get_assigned_original_ents allEnts))
              
              (setq tubePls nil)
              (setq scan assignedEnts)
              (while scan
                (setq e (car scan))
                (setq pl (dzo415_make_tube_poly_from_ent e dist lay))
                (if pl (setq tubePls (cons pl tubePls)))
                (setq scan (cdr scan))
              )
              (setq tubePls (reverse tubePls))
              (setq outline (dzo415_union_tubes_to_outline tubePls lay))

              (if outline
                (progn
                  (setq outline (dzo418_rebuild_outline_seam outline lay pick mainPts dist))
                  (if outline (g365_copy_color mainEnt outline))
                  (dzo415_delete_ents assignedEnts)
                  (dzo418_flush_cmd)
                  outline
                )
                nil
              )
            )
          )
        )
      )
    )
  )
)

(defun DZO-ORIG ()
  (prompt "\nDZ bu sürümden kaldýrýldý.")
  (princ)
)




(defun c:DZ ()
  (prompt "\nDZ bu sürümden kaldýrýldý.")
  (princ)
)



;;; --- Yeni DZ komutu (DRZ.lsp) ---
;;; ===========================================================
;;; DEG_DRZ_V6_FINAL.LSP
;;; 1. mainFarLim = 200.0
;;; 2. YON KONTROLU: Ãœst/Sol -> L-Tip, Alt/SaÄŸ -> DÃ¼z.
;;; 3. L-TIP KOSE DUZELTMESÄ°:
;;;    L'nin kosesindeki vertexler (pDown ve pDownRin), birbirine
;;;    zÄ±t yÃ¶nlere 10 birim kaydÄ±rÄ±larak (Sol/SaÄŸ) bozulma giderildi.
;;; ===========================================================


(defun g365_abs (x) (if (< x 0.0) (- x) x))
(defun g365_clayer () (getvar "CLAYER"))
(defun g365_closep (p q) (<= (distance p q) 1e-6))

;; -----------------------------------------------------------
;; Renk eslestirme (ByLayer/ByBlock dahil)
;; -----------------------------------------------------------
(defun g365_layer_color (lay / rec)
  (setq rec (tblsearch "LAYER" lay))
  (if rec
    (abs (cdr (assoc 62 rec)))
    7
  )
)

(defun g365_effective_color (e / ed c lay)
  (setq ed (entget e))
  (setq lay (cdr (assoc 8 ed)))
  (setq c (cdr (assoc 62 ed)))
  (cond
    ((or (null c) (= c 256) (= c 0)) (g365_layer_color lay))
    (t (abs c))
  )
)

(defun g365_append_pt (lst p)
  (if (or (null lst) (not (g365_closep (car (reverse lst)) p)))
    (append lst (list p))
    lst
  )
)

(defun g365_rev (lst / out)
  (setq out nil)
  (while lst
    (setq out (cons (car lst) out))
    (setq lst (cdr lst))
  )
  out
)

(defun g365_last (lst / x)
  (setq x nil)
  (while lst
    (setq x (car lst))
    (setq lst (cdr lst))
  )
  x
)

(defun g365_clean_pts (pts / out p prevPt)
  (setq out nil prevPt nil)
  (while pts
    (setq p (car pts))
    (if (or (null prevPt) (> (distance p prevPt) 1e-9))
      (progn
        (setq out (append out (list (list (car p) (cadr p) 0.0))))
        (setq prevPt (list (car p) (cadr p) 0.0))
      )
    )
    (setq pts (cdr pts))
  )
  out
)

(defun g365_get_pts_lw (e / ed pts pr)
  (setq ed (entget e) pts nil)
  (while ed
    (setq pr (car ed))
    (if (= (car pr) 10)
      (setq pts (append pts (list (list (car (cdr pr)) (cadr (cdr pr)) 0.0))))
    )
    (setq ed (cdr ed))
  )
  (g365_clean_pts pts)
)

(defun g365_get_pts_pl (e / pts en vd p)
  (setq pts nil)
  (setq en (entnext e))
  (while (and en (/= (cdr (assoc 0 (entget en))) "SEQEND"))
    (setq vd (entget en))
    (if (= (cdr (assoc 0 vd)) "VERTEX")
      (progn
        (setq p (cdr (assoc 10 vd)))
        (setq pts (append pts (list (list (car p) (cadr p) 0.0))))
      )
    )
    (setq en (entnext en))
  )
  (g365_clean_pts pts)
)

(defun g365_get_pts_line (e / ed p0 p1)
  (setq ed (entget e))
  (setq p0 (cdr (assoc 10 ed)))
  (setq p1 (cdr (assoc 11 ed)))
  (if (and p0 p1)
    (list (list (car p0) (cadr p0) 0.0) (list (car p1) (cadr p1) 0.0))
    nil
  )
)

(defun g365_get_pts (e / ed typ)
  (setq ed (entget e))
  (setq typ (cdr (assoc 0 ed)))
  (cond
    ((= typ "LWPOLYLINE") (g365_get_pts_lw e))
    ((= typ "POLYLINE")   (g365_get_pts_pl e))
    ((= typ "LINE")       (g365_get_pts_line e))
    (t nil)
  )
)

(defun g365_ptkey (p / sx sy)
  (setq sx (rtos (car p) 2 6))
  (setq sy (rtos (cadr p) 2 6))
  (strcat sx "," sy)
)

(defun g365_dot2 (ax ay bx by) (+ (* ax bx) (* ay by)))

(defun g365_closest_on_seg (p a b / ax ay bx by px py vx vy wx wy vv uPar cx cy)
  (setq ax (car a) ay (cadr a))
  (setq bx (car b) by (cadr b))
  (setq px (car p) py (cadr p))
  (setq vx (- bx ax))
  (setq vy (- by ay))
  (setq wx (- px ax))
  (setq wy (- py ay))
  (setq vv (+ (* vx vx) (* vy vy)))
  (if (<= vv 1e-12)
    (list a 0.0 (distance p a))
    (progn
      (setq uPar (/ (g365_dot2 wx wy vx vy) vv))
      (if (< uPar 0.0) (setq uPar 0.0))
      (if (> uPar 1.0) (setq uPar 1.0))
      (setq cx (+ ax (* uPar vx)))
      (setq cy (+ ay (* uPar vy)))
      (list (list cx cy 0.0) uPar (distance p (list cx cy 0.0)))
    )
  )
)

(defun g365_closest_on_poly (p pts / n i a b bestDist bestSeg bestU bestPt res curPt curU curDist)
  (setq n (length pts))
  (setq i 0)
  (setq bestDist 1e99)
  (setq bestSeg 0)
  (setq bestU 0.0)
  (setq bestPt (car pts))
  (while (< i (1- n))
    (setq a (nth i pts))
    (setq b (nth (1+ i) pts))
    (setq res (g365_closest_on_seg p a b))
    (setq curPt (nth 0 res))
    (setq curU (nth 1 res))
    (setq curDist (nth 2 res))
    (if (< curDist bestDist)
      (progn
        (setq bestDist curDist)
        (setq bestSeg i)
        (setq bestU curU)
        (setq bestPt curPt)
      )
    )
    (setq i (1+ i))
  )
  (list bestPt bestU bestSeg bestDist)
)

(defun g376_is_closed (pts / a b)
  (and pts (>= (length pts) 3)
       (<= (distance (car pts) (last pts)) 1e-6))
)

(defun g376_nth_safe (pts idx / n)
  (setq n (length pts))
  (if (or (< idx 0) (>= idx n)) nil (nth idx pts))
)

(defun g376_nth_wrap (pts idx / n i)
  (setq n (length pts))
  (if (<= n 0)
    nil
    (progn
      (setq i idx)
      (while (< i 0) (setq i (+ i n)))
      (while (>= i n) (setq i (- i n)))
      (nth i pts)
    )
  )
)

(defun g365_nearest_vidx (pts pick / n i bestI bestD dd)
  (setq n (length pts) i 0 bestI 0 bestD 1e99)
  (while (< i n)
    (setq dd (distance (nth i pts) pick))
    (if (< dd bestD) (setq bestD dd bestI i))
    (setq i (1+ i))
  )
  bestI
)

(defun g365_assoc_add (al key val / it)
  (setq it (assoc key al))
  (if it
    (subst (cons key (append (cdr it) (list val))) it al)
    (cons (cons key (list val)) al)
  )
)

(defun g365_assoc_set (al key val / it)
  (setq it (assoc key al))
  (if it
    (subst (cons key val) it al)
    (cons (cons key val) al)
  )
)

(defun g365_sort_u (lst / out mn scan)
  (setq out nil)
  (while lst
    (setq mn (car lst))
    (setq scan (cdr lst))
    (while scan
      (if (< (car (car scan)) (car mn)) (setq mn (car scan)))
      (setq scan (cdr scan))
    )
    (setq out (append out (list mn)))
    (setq lst (vl-remove mn lst))
  )
  out
)

(defun g365_line_inter (a b c d / x1 y1 x2 y2 x3 y3 x4 y4 den lam ix iy)
  (setq x1 (car a) y1 (cadr a))
  (setq x2 (car b) y2 (cadr b))
  (setq x3 (car c) y3 (cadr c))
  (setq x4 (car d) y4 (cadr d))
  (setq den (- (* (- x1 x2) (- y3 y4)) (* (- y1 y2) (- x3 x4))))
  (if (<= (g365_abs den) 1e-12)
    nil
    (progn
      (setq lam (/ (- (* (- x1 x3) (- y3 y4)) (* (- y1 y3) (- x3 x4))) den))
      (setq ix (+ x1 (* lam (- x2 x1))))
      (setq iy (+ y1 (* lam (- y2 y1))))
      (list ix iy 0.0)
    )
  )
)

(defun g365_seg_param (a b p / vx vy wx wy vv parVal)
  (setq vx (- (car b) (car a)))
  (setq vy (- (cadr b) (cadr a)))
  (setq wx (- (car p) (car a)))
  (setq wy (- (cadr p) (cadr a)))
  (setq vv (+ (* vx vx) (* vy vy)))
  (if (<= vv 1e-12)
    nil
    (/ (+ (* wx vx) (* wy vy)) vv)
  )
)

(defun g365_unit (vx vy / L)
  (setq L (distance (list 0.0 0.0 0.0) (list vx vy 0.0)))
  (if (<= L 1e-9)
    (list 0.0 0.0)
    (list (/ vx L) (/ vy L))
  )
)

(defun g365_left_normal (ux uy) (list (- uy) ux))
(defun g365_dot (ax ay bx by) (+ (* ax bx) (* ay by)))

(defun g384_need_corner (p1 corner p2 dist / v1 v2 u1 u2 l1 l2 dotv)
  (if (or (null p1) (null corner) (null p2) (null dist))
    nil
    (progn
      (setq l1 (distance p1 corner))
      (setq l2 (distance p2 corner))
      (if (and (<= l1 (* 2.0 dist)) (<= l2 (* 2.0 dist)))
        (progn
          (setq v1 (list (- (car p1) (car corner)) (- (cadr p1) (cadr corner))))
          (setq v2 (list (- (car p2) (car corner)) (- (cadr p2) (cadr corner))))
          (setq u1 (g365_unit (car v1) (cadr v1)))
          (setq u2 (g365_unit (car v2) (cadr v2)))
          (setq dotv (g365_abs (g365_dot (car u1) (cadr u1) (car u2) (cadr u2))))
          (< dotv 0.98)
        )
        nil
      )
    )
  )
)

(defun g365_offset_vertex_open (pPrev pCur pNext dist side / vx1 vy1 vx2 vy2 u1 u2 n1 n2
                                     a1 b1 a2 b2 ip
                                     ox oy lim
                                     bx by bL bux buy dotv mLen nx2 ny2 len1 len2)
  (setq vx1 (- (car pCur) (car pPrev)))
  (setq vy1 (- (cadr pCur) (cadr pPrev)))
  (setq vx2 (- (car pNext) (car pCur)))
  (setq vy2 (- (cadr pNext) (cadr pCur)))

  (setq len1 (sqrt (+ (* vx1 vx1) (* vy1 vy1))))
  (setq len2 (sqrt (+ (* vx2 vx2) (* vy2 vy2))))

  (setq u1 (g365_unit vx1 vy1))
  (setq u2 (g365_unit vx2 vy2))

  (setq n1 (g365_left_normal (car u1) (cadr u1)))
  (setq n2 (g365_left_normal (car u2) (cadr u2)))

  (setq n1 (list (* side (car n1)) (* side (cadr n1))))
  (setq n2 (list (* side (car n2)) (* side (cadr n2))))

  (setq lim (* 20.0 dist))

  (setq dotv (g365_dot (car u1) (cadr u1) (car u2) (cadr u2)))
  (if (and (> len1 1e-9) (> len2 1e-9) (> dotv 0.9999))
    (progn
      (setq ox (* (car n1) dist))
      (setq oy (* (cadr n1) dist))
    )
    (progn
      (cond
        ((and (<= len1 1e-9) (> len2 1e-9))
          (setq ox (* (car n2) dist) oy (* (cadr n2) dist))
        )
        ((and (<= len2 1e-9) (> len1 1e-9))
          (setq ox (* (car n1) dist) oy (* (cadr n1) dist))
        )
        (t
          (setq a1 (list (+ (car pPrev) (* (car n1) dist)) (+ (cadr pPrev) (* (cadr n1) dist)) 0.0))
          (setq b1 (list (+ (car pCur)  (* (car n1) dist)) (+ (cadr pCur)  (* (cadr n1) dist)) 0.0))
          (setq a2 (list (+ (car pCur)  (* (car n2) dist)) (+ (cadr pCur)  (* (cadr n2) dist)) 0.0))
          (setq b2 (list (+ (car pNext) (* (car n2) dist)) (+ (cadr pNext) (* (cadr n2) dist)) 0.0))
          (setq ip (g365_line_inter a1 b1 a2 b2))

          (if (and ip (<= (distance ip pCur) lim))
            (progn
              (setq ox (- (car ip) (car pCur)))
              (setq oy (- (cadr ip) (cadr pCur)))
            )
            (progn
              (setq bx (+ (car n1) (car n2)))
              (setq by (+ (cadr n1) (cadr n2)))
              (setq bL (distance (list 0.0 0.0 0.0) (list bx by 0.0)))

              (if (<= bL 1e-9)
                (progn (setq bux (car n2)) (setq buy (cadr n2)))
                (progn (setq bux (/ bx bL)) (setq buy (/ by bL)))
              )

              (setq nx2 (car n2))
              (setq ny2 (cadr n2))
              (setq dotv (g365_dot bux buy nx2 ny2))

              (if (<= dotv 0.001)
                (progn (setq ox (* nx2 dist)) (setq oy (* ny2 dist)))
                (progn
                  (setq mLen (/ dist dotv))
                  (if (> mLen lim) (setq mLen lim))
                  (setq ox (* bux mLen))
                  (setq oy (* buy mLen))
                )
              )
            )
          )
        )
      )
    )
  )

  (list (+ (car pCur) ox) (+ (cadr pCur) oy) 0.0)
)

(defun g365_offset_open_pts (pts dist side / n i p0 p1 pn2 pn1 u nrm out pPrev pCur pNext)
  (setq n (length pts))
  (setq out nil)
  (if (< n 2)
    out
    (progn
      (setq p0 (nth 0 pts))
      (setq p1 (nth 1 pts))
      (setq u (g365_unit (- (car p1) (car p0)) (- (cadr p1) (cadr p0))))
      (setq nrm (g365_left_normal (car u) (cadr u)))
      (setq nrm (list (* side (car nrm)) (* side (cadr nrm))))
      (setq out (append out (list (list (+ (car p0) (* (car nrm) dist)) (+ (cadr p0) (* (cadr nrm) dist)) 0.0))))

      (setq i 1)
      (while (< i (1- n))
        (setq pPrev (nth (1- i) pts))
        (setq pCur  (nth i pts))
        (setq pNext (nth (1+ i) pts))
        (setq out (append out (list (g365_offset_vertex_open pPrev pCur pNext dist side))))
        (setq i (1+ i))
      )

      (setq pn2 (nth (- n 2) pts))
      (setq pn1 (nth (- n 1) pts))
      (setq u (g365_unit (- (car pn1) (car pn2)) (- (cadr pn1) (cadr pn2))))
      (setq nrm (g365_left_normal (car u) (cadr u)))
      (setq nrm (list (* side (car nrm)) (* side (cadr nrm))))
      (setq out (append out (list (list (+ (car pn1) (* (car nrm) dist)) (+ (cadr pn1) (* (cadr nrm) dist)) 0.0))))
      out
    )
  )
)

(defun g365_entmake_open_poly (lay pts / n data e p)
  (setq n (length pts))
  (if (and n (> n 1))
    (progn
      (setq data (list
        (cons 0 "LWPOLYLINE")
        (cons 100 "AcDbEntity")
        (cons 8 lay)
        (cons 100 "AcDbPolyline")
        (cons 90 n)
        (cons 70 0)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g365_ed_remove_codes (ed codes / out pr)
  (setq out nil)
  (while ed
    (setq pr (car ed))
    (if (not (member (car pr) codes))
      (setq out (append out (list pr)))
    )
    (setq ed (cdr ed))
  )
  out
)

(defun g365_ed_ins_after_code (ed code ins / out done pr)
  (setq out nil done nil)
  (while ed
    (setq pr (car ed))
    (setq out (append out (list pr)))
    (if (and (not done) (= (car pr) code))
      (progn
        (setq out (append out ins))
        (setq done T)
      )
    )
    (setq ed (cdr ed))
  )
  (if done out (append out ins))
)

(defun g365_copy_color (srcEnt dstEnt / es oS oD srcCol c420 acad cm)
  (if (and srcEnt dstEnt)
    (progn
      (vl-load-com)
      (setq oS (vlax-ename->vla-object srcEnt))
      (setq oD (vlax-ename->vla-object dstEnt))

      (setq srcCol (vl-catch-all-apply 'vla-get-Color (list oS)))
      (if (not (vl-catch-all-error-p srcCol))
        (vl-catch-all-apply 'vla-put-Color (list oD srcCol))
      )

      (setq es (entget srcEnt))
      (setq c420 (assoc 420 es))
      (if c420
        (progn
          (setq acad (vlax-get-acad-object))
          (setq cm (vla-GetInterfaceObject acad "AutoCAD.AcCmColor"))
          (vl-catch-all-apply 'vla-put-ColorValue (list cm (cdr c420)))
          (vl-catch-all-apply 'vla-put-TrueColor (list oD cm))
        )
      )
    )
  )
  dstEnt
)

(defun g365_force_color_aci (ent aci / ed c62)
  (if ent
    (progn
      (setq ed (entget ent))
      (setq ed (g365_ed_remove_codes ed (list 420 430)))
      (setq c62 (assoc 62 ed))
      (if c62
        (setq ed (subst (cons 62 (fix aci)) c62 ed))
        (setq ed (g365_ed_ins_after_code ed 8 (list (cons 62 (fix aci)))))
      )
      (vl-catch-all-apply 'entmod (list ed))
      (vl-catch-all-apply 'entupd (list ent))
    )
  )
  ent
)

(defun g365_add_mouth_cand (candList signVal boundaryPt bA bB brA0 brA1 sideTag maxLen / ip parB parBr)
  (setq ip (g365_line_inter bA bB brA0 brA1))
  (if ip
    (progn
      (setq parB (g365_seg_param bA bB ip))
      (setq parBr (g365_seg_param brA0 brA1 ip))
      (if (and parB parBr
               (>= parB -1e-6) (<= parB (+ 1.0 1e-6))
               (<= (distance boundaryPt ip) maxLen)
               (<= (distance brA0 ip) maxLen))
        (append candList (list (list signVal ip sideTag)))
        candList
      )
    )
    candList
  )
)

(defun g365_pick_best_by_sign (candList wantNeg / best rec sgn absS)
  (setq best nil)
  (while candList
    (setq rec (car candList))
    (setq sgn (car rec))
    (if (or (and wantNeg (< sgn 0.0)) (and (not wantNeg) (> sgn 0.0)))
      (progn
        (setq absS (g365_abs sgn))
        (if (or (null best) (< absS (g365_abs (car best))))
          (setq best rec)
        )
      )
    )
    (setq candList (cdr candList))
  )
  best
)

(defun g365_pick_best_pos_opposite (candList negSideTag / best rec sgn absS)
  (setq best nil)
  (while candList
    (setq rec (car candList))
    (setq sgn (car rec))
    (if (and (> sgn 0.0) (/= (caddr rec) negSideTag))
      (progn
        (setq absS (g365_abs sgn))
        (if (or (null best) (< absS (g365_abs (car best))))
          (setq best rec)
        )
      )
    )
    (setq candList (cdr candList))
  )
  best
)

(defun g365_bump_open_mouth (boundaryPts idx step brPts dist / n bpt maxLen
                                       inA inB outA outB
                                       brL brR brL0 brL1 brR0 brR1
                                       cand negRec posRec posAlt
                                       enter exit enterTag exitTag
                                       startPoly otherPoly otherRev nOther jj seq farOther)
  (setq n (length boundaryPts))
  (if (or (<= idx 0) (>= idx (1- n)) (null brPts) (< (length brPts) 2))
    nil
    (progn
      (setq bpt (nth idx boundaryPts))
      (setq maxLen (* 8.0 dist))
      (setq brL (g365_offset_open_pts brPts dist  1))
      (setq brR (g365_offset_open_pts brPts dist -1))
      (if (or (null brL) (null brR) (< (length brL) 2) (< (length brR) 2))
        nil
        (progn
          (setq inA  (nth (- idx step) boundaryPts))
          (setq inB  (nth idx boundaryPts))
          (setq outA (nth idx boundaryPts))
          (setq outB (nth (+ idx step) boundaryPts))

          (setq brL0 (nth 0 brL)) (setq brL1 (nth 1 brL))
          (setq brR0 (nth 0 brR)) (setq brR1 (nth 1 brR))

          (setq cand nil)

          (setq cand (g365_add_mouth_cand cand (- (distance bpt inA)) bpt inA inB brL0 brL1  1 maxLen))
          (setq cand (g365_add_mouth_cand cand (- (distance bpt inA)) bpt inA inB brR0 brR1 -1 maxLen))

          (setq cand (g365_add_mouth_cand cand (distance bpt outB) bpt outA outB brL0 brL1  1 maxLen))
          (setq cand (g365_add_mouth_cand cand (distance bpt outB) bpt outA outB brR0 brR1 -1 maxLen))

          (setq negRec (g365_pick_best_by_sign cand 1))
          (setq posRec (g365_pick_best_by_sign cand nil))

          (if (and negRec posRec)
            (progn
              (if (= (caddr negRec) (caddr posRec))
                (progn
                  (setq posAlt (g365_pick_best_pos_opposite cand (caddr negRec)))
                  (if posAlt (setq posRec posAlt))
                )
              )

              (setq enter (cadr negRec))
              (setq exit  (cadr posRec))
              (setq enterTag (caddr negRec))
              (setq exitTag  (caddr posRec))

              (if (= enterTag exitTag)
                nil
                (progn
                  (if (= enterTag 1) (setq startPoly brL) (setq startPoly brR))
                  (if (= exitTag  1) (setq otherPoly brL) (setq otherPoly brR))

                  (setq seq nil)
                  (setq seq (g365_append_pt seq enter))

                  (setq jj 1)
                  (while (< jj (length startPoly))
                    (setq seq (g365_append_pt seq (nth jj startPoly)))
                    (setq jj (1+ jj))
                  )

                  (setq farOther (g365_last otherPoly))
                  (setq seq (g365_append_pt seq farOther))

                  (setq otherRev (g365_rev otherPoly))
                  (setq nOther (length otherPoly))
                  (setq jj 1)
                  (while (< jj (1- nOther))
                    (setq seq (g365_append_pt seq (nth jj otherRev)))
                    (setq jj (1+ jj))
                  )

                  (setq seq (g365_append_pt seq exit))
                  seq
                )
              )
            )
            nil
          )
        )
      )
    )
  )
)

(defun g371_sublist (lst start / i out n)
  (setq out nil)
  (setq n (length lst))
  (setq i start)
  (while (< i n)
    (setq out (append out (list (nth i lst))))
    (setq i (1+ i))
  )
  out
)

(defun g371_sublist_rev (lst idx / i out)
  (setq out nil)
  (setq i idx)
  (while (>= i 0)
    (setq out (append out (list (nth i lst))))
    (setq i (1- i))
  )
  out
)

(defun g371_best_contact (mainPts brPts tol / mN bN mi bi mA mB bA bB best bestD
                                   ip uM uB res pMain pBr d)
  (setq best nil)
  (setq bestD 1e99)
  (setq mN (length mainPts))
  (setq bN (length brPts))
  (if (or (< mN 2) (< bN 2))
    nil
    (progn
      (setq mi 0)
      (while (< mi (1- mN))
        (setq mA (nth mi mainPts))
        (setq mB (nth (1+ mi) mainPts))
        (setq bi 0)
        (while (< bi (1- bN))
          (setq bA (nth bi brPts))
          (setq bB (nth (1+ bi) brPts))

          (setq ip (g365_line_inter mA mB bA bB))
          (if ip
            (progn
              (setq uM (g365_seg_param mA mB ip))
              (setq uB (g365_seg_param bA bB ip))
              (if (and uM uB (>= uM -1e-6) (<= uM (+ 1.0 1e-6)) (>= uB -1e-6) (<= uB (+ 1.0 1e-6)))
                (progn
                  (setq d 0.0)
                  (if (< d bestD)
                    (progn
                      (setq bestD d)
                      (setq best (list d mi uM ip bi uB ip))
                    )
                  )
                )
              )
            )
          )

          (setq res (g365_closest_on_seg bA mA mB))
          (setq pMain (nth 0 res))
          (setq uM (nth 1 res))
          (setq d (nth 2 res))
          (if (< d bestD)
            (progn
              (setq bestD d)
              (setq best (list d mi uM pMain bi 0.0 bA))
            )
          )

          (setq res (g365_closest_on_seg bB mA mB))
          (setq pMain (nth 0 res))
          (setq uM (nth 1 res))
          (setq d (nth 2 res))
          (if (< d bestD)
            (progn
              (setq bestD d)
              (setq best (list d mi uM pMain bi 1.0 bB))
            )
          )

          (setq res (g365_closest_on_seg mA bA bB))
          (setq pBr (nth 0 res))
          (setq uB (nth 1 res))
          (setq d (nth 2 res))
          (if (< d bestD)
            (progn
              (setq bestD d)
              (setq best (list d mi 0.0 mA bi uB pBr))
            )
          )

          (setq res (g365_closest_on_seg mB bA bB))
          (setq pBr (nth 0 res))
          (setq uB (nth 1 res))
          (setq d (nth 2 res))
          (if (< d bestD)
            (progn
              (setq bestD d)
              (setq best (list d mi 1.0 mB bi uB pBr))
            )
          )

          (setq bi (1+ bi))
        )
        (setq mi (1+ mi))
      )

      (if (and best (<= (car best) tol)) best nil)
    )
  )
)

(defun g371_branch_dirs (pts segIdx u touchBr / eps n newPts idxTouch i out)
  (setq eps 1e-6)
  (setq n (length pts))
  (setq out nil)
  (if (or (null pts) (< n 2) (null segIdx) (null u) (null touchBr))
    nil
    (progn
      (if (<= u eps)
        (progn
          (setq newPts pts)
          (setq idxTouch segIdx)
        )
        (if (>= u (- 1.0 eps))
          (progn
            (setq newPts pts)
            (setq idxTouch (1+ segIdx))
          )
          (progn
            (setq newPts nil)
            (setq i 0)
            (while (< i n)
              (setq newPts (append newPts (list (nth i pts))))
              (if (= i segIdx)
                (setq newPts (append newPts (list touchBr)))
              )
              (setq i (1+ i))
            )
            (setq idxTouch (1+ segIdx))
          )
        )
      )

      (if (< idxTouch (1- (length newPts)))
        (setq out (append out (list (g371_sublist newPts idxTouch))))
      )
      (if (> idxTouch 0)
        (setq out (append out (list (g371_sublist_rev newPts idxTouch))))
      )
      out
    )
  )
)

(defun g371_make_branch (touchMain dirPts / out)
  (setq out nil)
  (if (and dirPts (>= (length dirPts) 2))
    (progn
      (if (g365_closep touchMain (car dirPts))
        (setq out (cons touchMain (cdr dirPts)))
        (setq out (cons touchMain dirPts))
      )
    )
  )
  (if (and out (>= (length out) 2)) out nil)
)

(defun g371_branch_side (mainAug iKey brPts left right / touch outPt pPrev pNext tx ty bx by cr)
  (setq touch (nth 0 brPts))
  (setq outPt (nth 1 brPts))
  (setq pPrev (if (> iKey 0) (nth (1- iKey) mainAug) (nth iKey mainAug)))
  (setq pNext (if (< iKey (1- (length mainAug))) (nth (1+ iKey) mainAug) (nth iKey mainAug)))
  (setq tx (- (car pNext) (car pPrev)))
  (setq ty (- (cadr pNext) (cadr pPrev)))
  (setq bx (- (car outPt) (car touch)))
  (setq by (- (cadr outPt) (cadr touch)))
  (setq cr (- (* tx by) (* ty bx)))
  (if (> (g365_abs cr) 1e-9)
    (if (> cr 0.0) 1 -1)
    (if (< (distance outPt (nth iKey left)) (distance outPt (nth iKey right))) 1 -1)
  )
)

(setq g372_nodes nil)
(setq g372_nextId 0)
(setq g372_assigned nil)

(defun g372_reset_tree ()
  (setq g372_nodes nil)
  (setq g372_nextId 0)
  (setq g372_assigned nil)
)

(defun g372_get_node (id) (cdr (assoc id g372_nodes)))

(defun g372_node (id sym / nd)
  (setq nd (g372_get_node id))
  (if nd (cdr (assoc sym nd)) nil)
)

(defun g372_set_node (id sym val / pair nd newnd)
  (setq pair (assoc id g372_nodes))
  (if pair
    (progn
      (setq nd (cdr pair))
      (setq newnd (g365_assoc_set nd sym val))
      (setq g372_nodes (subst (cons id newnd) pair g372_nodes))
    )
  )
  val
)

(defun g372_assigned_p (ent) (if (assoc ent g372_assigned) T nil))

(defun g372_assign (ent val)
  (setq g372_assigned (g365_assoc_set g372_assigned ent val))
  val
)

(defun g372_new_node (ent pts parentId parentKey / id nd)
  (setq id g372_nextId)
  (setq g372_nextId (1+ g372_nextId))
  (setq nd (list
    (cons 'id id)
    (cons 'ent ent)
    (cons 'pts pts)
    (cons 'parent parentId)
    (cons 'pkey parentKey)
    (cons 'touchBySeg nil)
    (cons 'childrenByKey nil)
    (cons 'aug nil)
    (cons 'left nil)
    (cons 'right nil)
    (cons 'keyIndex nil)
    (cons 'branchMap nil)
  ))
  (setq g372_nodes (cons (cons id nd) g372_nodes))
  id
)

(defun g372_ss_to_list (ss / i out)
  (setq out nil i 0)
  (if ss
    (while (< i (sslength ss))
      (setq out (cons (ssname ss i) out))
      (setq i (1+ i))
    )
  )
  out
)

(defun g372_build_tree (rootEnt rootPts allEnts tol / rootId queue pid pPts scan entScan brPts bestRes
                              segIdx uVal touchMain brSegIdx brU touchBr key dirList brPts2
                              firstChild touchBySeg childrenByKey childId)
  (g372_reset_tree)
  (setq rootId (g372_new_node rootEnt rootPts nil nil))
  (g372_assign rootEnt rootId)
  (setq queue (list rootId))

  (while queue
    (setq pid (car queue))
    (setq queue (cdr queue))
    (setq pPts (g372_node pid 'pts))

    (setq scan allEnts)
    (while scan
      (setq entScan (car scan))
      (if (and (/= entScan (g372_node pid 'ent)) (not (g372_assigned_p entScan)))
        (progn
          (setq brPts (g365_get_pts entScan))
          (if (and brPts (>= (length brPts) 2))
            (progn
              (setq bestRes (g371_best_contact pPts brPts tol))
              (if bestRes
                (progn
                  (setq segIdx    (nth 1 bestRes))
                  (setq uVal      (nth 2 bestRes))
                  (setq touchMain (nth 3 bestRes))
                  (setq brSegIdx  (nth 4 bestRes))
                  (setq brU       (nth 5 bestRes))
                  (setq touchBr   (nth 6 bestRes))

                  (setq key (g365_ptkey touchMain))

                  (setq touchBySeg (g372_node pid 'touchBySeg))
                  (setq touchBySeg (g365_assoc_add touchBySeg segIdx (list uVal touchMain key)))
                  (g372_set_node pid 'touchBySeg touchBySeg)

                  (setq dirList (g371_branch_dirs brPts brSegIdx brU touchBr))
                  (setq firstChild nil)
                  (while dirList
                    (setq brPts2 (g371_make_branch touchMain (car dirList)))
                    (if (and brPts2 (>= (length brPts2) 2))
                      (progn
                        (setq childId (g372_new_node entScan brPts2 pid key))
                        (if (null firstChild) (setq firstChild childId))
                        (setq queue (append queue (list childId)))
                        (setq childrenByKey (g372_node pid 'childrenByKey))
                        (setq childrenByKey (g365_assoc_add childrenByKey key childId))
                        (g372_set_node pid 'childrenByKey childrenByKey)
                      )
                    )
                    (setq dirList (cdr dirList))
                  )

                  (if firstChild (g372_assign entScan firstChild))
                )
              )
            )
          )
        )
      )
      (setq scan (cdr scan))
    )
  )

  rootId
)

(defun g372_prepare_node (id dist / pts touchBySeg childrenByKey mainAug segK segTouches sorted left right
                               keyIndexMap scan key childIds iKey childId childPts sidePick branchMap)
  (setq pts (g372_node id 'pts))
  (setq touchBySeg (g372_node id 'touchBySeg))
  (setq childrenByKey (g372_node id 'childrenByKey))

  (if (or (null pts) (< (length pts) 2))
    nil
    (progn
      (setq mainAug nil)
      (setq mainAug (append mainAug (list (nth 0 pts))))
      (setq segK 0)
      (while (< segK (1- (length pts)))
        (setq segTouches (cdr (assoc segK touchBySeg)))
        (if segTouches
          (progn
            (setq sorted (g365_sort_u segTouches))
            (while sorted
              (setq mainAug (g365_append_pt mainAug (cadr (car sorted))))
              (setq sorted (cdr sorted))
            )
          )
        )
        (setq mainAug (g365_append_pt mainAug (nth (1+ segK) pts)))
        (setq segK (1+ segK))
      )

      (setq left  (g365_offset_open_pts mainAug dist  1))
      (setq right (g365_offset_open_pts mainAug dist -1))

      (if (or (null left) (null right) (< (length left) 2) (/= (length left) (length mainAug)))
        (progn
          (g372_set_node id 'aug mainAug)
          (g372_set_node id 'left nil)
          (g372_set_node id 'right nil)
          (g372_set_node id 'keyIndex nil)
          (g372_set_node id 'branchMap nil)
          nil
        )
        (progn
          (setq keyIndexMap nil)
          (setq segK 0)
          (while (< segK (length mainAug))
            (setq keyIndexMap (g365_assoc_set keyIndexMap (g365_ptkey (nth segK mainAug)) segK))
            (setq segK (1+ segK))
          )

          (setq branchMap nil)
          (setq scan childrenByKey)
          (while scan
            (setq key (car (car scan)))
            (setq childIds (cdr (car scan)))
            (setq iKey (cdr (assoc key keyIndexMap)))
            (if iKey
              (progn
                (while childIds
                  (setq childId (car childIds))
                  (setq childPts (g372_node childId 'pts))
                  (if (and childPts (>= (length childPts) 2))
                    (progn
                      (setq sidePick (g371_branch_side mainAug iKey childPts left right))
                      (setq branchMap (g365_assoc_add branchMap key (list sidePick childId)))
                    )
                  )
                  (setq childIds (cdr childIds))
                )
              )
            )
            (setq scan (cdr scan))
          )

          (g372_set_node id 'aug mainAug)
          (g372_set_node id 'left left)
          (g372_set_node id 'right right)
          (g372_set_node id 'keyIndex keyIndexMap)
          (g372_set_node id 'branchMap branchMap)
          T
        )
      )
    )
  )
)

(defun g372_prepare_all (dist / ids p)
  (setq ids nil)
  (setq p g372_nodes)
  (while p
    (setq ids (cons (car (car p)) ids))
    (setq p (cdr p))
  )
  (while ids
    (g372_prepare_node (car ids) dist)
    (setq ids (cdr ids))
  )
  T
)

(defun g372_bump_open_mouth_rec (boundaryPts idx step childId dist / childAug brL brR childBM n bpt maxLen
                                        inA inB outA outB brL0 brL1 brR0 brR1
                                        cand negRec posRec posAlt enter exit enterTag exitTag
                                        startPoly otherPoly seq jj key brList tmp rec bump kk2
                                        nOther idxCur didBump farOther)
  (setq childAug (g372_node childId 'aug))
  (setq brL (g372_node childId 'left))
  (setq brR (g372_node childId 'right))
  (setq childBM (g372_node childId 'branchMap))

  (setq n (length boundaryPts))
  (if (or (<= idx 0) (>= idx (1- n)) (null childAug) (< (length childAug) 2)
          (null brL) (null brR) (< (length brL) 2) (< (length brR) 2))
    nil
    (progn
      (setq bpt (nth idx boundaryPts))
      (setq maxLen (* 8.0 dist))

      (setq inA  (nth (- idx step) boundaryPts))
      (setq inB  (nth idx boundaryPts))
      (setq outA (nth idx boundaryPts))
      (setq outB (nth (+ idx step) boundaryPts))

      (setq brL0 (nth 0 brL)) (setq brL1 (nth 1 brL))
      (setq brR0 (nth 0 brR)) (setq brR1 (nth 1 brR))

      (setq cand nil)
      (setq cand (g365_add_mouth_cand cand (- (distance bpt inA)) bpt inA inB brL0 brL1  1 maxLen))
      (setq cand (g365_add_mouth_cand cand (- (distance bpt inA)) bpt inA inB brR0 brR1 -1 maxLen))
      (setq cand (g365_add_mouth_cand cand (distance bpt outB) bpt outA outB brL0 brL1  1 maxLen))
      (setq cand (g365_add_mouth_cand cand (distance bpt outB) bpt outA outB brR0 brR1 -1 maxLen))

      (setq negRec (g365_pick_best_by_sign cand 1))
      (setq posRec (g365_pick_best_by_sign cand nil))

      (if (and negRec posRec)
        (progn
          (if (= (caddr negRec) (caddr posRec))
            (progn
              (setq posAlt (g365_pick_best_pos_opposite cand (caddr negRec)))
              (if posAlt (setq posRec posAlt))
            )
          )

          (setq enter (cadr negRec))
          (setq exit  (cadr posRec))
          (setq enterTag (caddr negRec))
          (setq exitTag  (caddr posRec))

          (if (= enterTag exitTag)
            nil
            (progn
              (if (= enterTag 1) (setq startPoly brL) (setq startPoly brR))
              (if (= exitTag  1) (setq otherPoly brL) (setq otherPoly brR))

              (setq seq nil)
              (setq seq (g365_append_pt seq enter))

              (setq jj 1)
              (while (< jj (length startPoly))
                (setq key (g365_ptkey (nth jj childAug)))
                (setq brList (cdr (assoc key childBM)))
                (setq didBump nil)

                (if brList
                  (progn
                    (setq tmp brList)
                    (while tmp
                      (setq rec (car tmp))
                      (if (= (car rec) enterTag)
                        (progn
                          (setq bump (g377_bump_force_rec startPoly jj 1 (cadr rec) dist))
                          (if bump
                            (progn
                              (setq kk2 0)
                              (while (< kk2 (length bump))
                                (setq seq (g365_append_pt seq (nth kk2 bump)))
                                (setq kk2 (1+ kk2))
                              )
                              (setq didBump 1)
                            )
                          )
                        )
                      )
                      (setq tmp (cdr tmp))
                    )
                  )
                )

                (if (not didBump)
                  (setq seq (g365_append_pt seq (nth jj startPoly)))
                )
                (setq jj (1+ jj))
              )

              (setq farOther (g365_last otherPoly))
              (setq seq (g365_append_pt seq farOther))

              (setq nOther (length otherPoly))
              (setq idxCur (- nOther 2))
              (while (>= idxCur 1)
                (setq key (g365_ptkey (nth idxCur childAug)))
                (setq brList (cdr (assoc key childBM)))
                (setq didBump nil)

                (if brList
                  (progn
                    (setq tmp brList)
                    (while tmp
                      (setq rec (car tmp))
                      (if (= (car rec) exitTag)
                        (progn
                          (setq bump (g377_bump_force_rec otherPoly idxCur -1 (cadr rec) dist))
                          (if bump
                            (progn
                              (setq kk2 0)
                              (while (< kk2 (length bump))
                                (setq seq (g365_append_pt seq (nth kk2 bump)))
                                (setq kk2 (1+ kk2))
                              )
                              (setq didBump 1)
                            )
                          )
                        )
                      )
                      (setq tmp (cdr tmp))
                    )
                  )
                )

                (if (not didBump)
                  (setq seq (g365_append_pt seq (nth idxCur otherPoly)))
                )

                (setq idxCur (1- idxCur))
              )

              (setq seq (g365_append_pt seq exit))
              seq
            )
          )
        )
        nil
      )
    )
  )
)

(defun g373_mouth_ip (bA bB boundaryPt brA0 brA1 sideTag maxLen / ip parB parBr res u d tolTouch)
  (setq ip (g365_line_inter bA bB brA0 brA1))
  (if ip
    (progn
      (setq parB (g365_seg_param bA bB ip))
      (setq parBr (g365_seg_param brA0 brA1 ip))
      (if (and parB parBr
               (>= parB -1e-6) (<= parB (+ 1.0 1e-6))
               (>= parBr -1e-6) (<= parBr (+ 1.0 1e-6))
               (<= (distance boundaryPt ip) maxLen)
               (<= (distance brA0 ip) maxLen))
        (list parB ip sideTag)
        nil
      )
    )
    (progn
      (setq tolTouch 0.1)
      (setq res (g365_closest_on_seg boundaryPt brA0 brA1))
      (setq u (nth 1 res))
      (setq d (nth 2 res))
      (if (and (<= d tolTouch)
               (or (<= u 1e-3) (>= u (- 1.0 1e-3))))
        (progn
          (setq parB (g365_seg_param bA bB boundaryPt))
          (if (and parB (>= parB -1e-6) (<= parB (+ 1.0 1e-6)))
            (list parB boundaryPt sideTag)
            nil
          )
        )
        nil
      )
    )
  )
)

(defun g372_bump_open_mouth_half_rec (boundaryPts idx step childId dist useIncoming / childAug brL brR childBM n bpt maxLen isClosed bInA bInB bOutA bOutB bA2 bB2 recL1 recR1 recL2 recR2 segL segR d1 d2 snapTol cornerTol cornerTol2
                                            bA bB brL0 brL1 brR0 brR1 recL recR enterRec exitRec
                                            enter exit enterTag exitTag
                                            startPoly otherPoly seq jj key brList tmp rec bump kk2
                                            nOther idxCur didBump farOther)
  (setq childAug (g372_node childId 'aug))
  (setq brL (g372_node childId 'left))
  (setq brR (g372_node childId 'right))
  (setq childBM (g372_node childId 'branchMap))

  (setq n (length boundaryPts))
  (if (or (null boundaryPts) (< n 2) (null childAug) (< (length childAug) 2)
          (null brL) (null brR) (< (length brL) 2) (< (length brR) 2))
    nil
    (progn
      (setq isClosed (g376_is_closed boundaryPts))
      (setq maxLen (* 8.0 dist))

      (if isClosed
        (setq bpt (g376_nth_wrap boundaryPts idx))
        (setq bpt (g376_nth_safe boundaryPts idx))
      )

      (if isClosed
        (progn
          (setq bInA  (g376_nth_wrap boundaryPts (- idx step)))
          (setq bInB  (g376_nth_wrap boundaryPts idx))
          (setq bOutA (g376_nth_wrap boundaryPts idx))
          (setq bOutB (g376_nth_wrap boundaryPts (+ idx step)))
        )
        (progn
          (setq bInA  (g376_nth_safe boundaryPts (- idx step)))
          (setq bInB  (g376_nth_safe boundaryPts idx))
          (setq bOutA (g376_nth_safe boundaryPts idx))
          (setq bOutB (g376_nth_safe boundaryPts (+ idx step)))
        )
      )

      (if useIncoming
        (progn
          (setq bA bInA) (setq bB bInB)
          (setq bA2 bOutA) (setq bB2 bOutB)
        )
        (progn
          (setq bA bOutA) (setq bB bOutB)
          (setq bA2 bInA) (setq bB2 bInB)
        )
      )

      (if (or (null bA) (null bB) (null bpt))
        nil
        (progn
          (setq brL0 (nth 0 brL)) (setq brL1 (nth 1 brL))
          (setq brR0 (nth 0 brR)) (setq brR1 (nth 1 brR))

          (setq snapTol 0.2)
          (if (<= (distance bpt brL0) snapTol)
            (progn
              (setq brL (cons bpt (cdr brL)))
              (setq brL0 bpt)
            )
          )
          (if (<= (distance bpt brR0) snapTol)
            (progn
              (setq brR (cons bpt (cdr brR)))
              (setq brR0 bpt)
            )
          )

          (setq recL1 (g373_mouth_ip bA  bB  bpt brL0 brL1  1 maxLen))
          (setq recR1 (g373_mouth_ip bA  bB  bpt brR0 brR1 -1 maxLen))
          (setq recL2 (if (and bA2 bB2) (g373_mouth_ip bA2 bB2 bpt brL0 brL1  1 maxLen) nil))
          (setq recR2 (if (and bA2 bB2) (g373_mouth_ip bA2 bB2 bpt brR0 brR1 -1 maxLen) nil))

          (setq recL nil) (setq segL 0)
          (if recL1 (progn (setq recL recL1) (setq segL 1)))
          (if recL2
            (if (null recL)
              (progn (setq recL recL2) (setq segL 2))
              (progn
                (setq d1 (distance bpt (cadr recL)))
                (setq d2 (distance bpt (cadr recL2)))
                (if (< d2 d1) (progn (setq recL recL2) (setq segL 2)))
              )
            )
          )

          (setq recR nil) (setq segR 0)
          (if recR1 (progn (setq recR recR1) (setq segR 1)))
          (if recR2
            (if (null recR)
              (progn (setq recR recR2) (setq segR 2))
              (progn
                (setq d1 (distance bpt (cadr recR)))
                (setq d2 (distance bpt (cadr recR2)))
                (if (< d2 d1) (progn (setq recR recR2) (setq segR 2)))
              )
            )
          )

          (setq cornerTol 0.2)
          (if (and recL recR (/= segL segR)
                   (<= (distance bpt (cadr recL)) cornerTol)
                   (<= (distance bpt (cadr recR)) cornerTol))
            (progn (setq recL nil) (setq recR nil))
          )


          (if (and recL recR)
            (progn
              (if (< (car recL) (car recR))
                (progn (setq enterRec recL) (setq exitRec recR))
                (progn (setq enterRec recR) (setq exitRec recL))
              )

              (setq enter (cadr enterRec))
              (setq exit  (cadr exitRec))
              (setq enterTag (caddr enterRec))
              (setq exitTag  (caddr exitRec))

              (if (= enterTag exitTag)
                nil
                (progn
                  (if (= enterTag 1) (setq startPoly brL) (setq startPoly brR))
                  (if (= exitTag  1) (setq otherPoly brL) (setq otherPoly brR))

                  (setq seq nil)
                  (setq seq (g365_append_pt seq enter))

                  (setq jj 1)
                  (while (< jj (length startPoly))
                    (setq key (g365_ptkey (nth jj childAug)))
                    (setq brList (cdr (assoc key childBM)))
                    (setq didBump nil)

                    (if brList
                      (progn
                        (setq tmp brList)
                        (while tmp
                          (setq rec (car tmp))
                          (if (= (car rec) enterTag)
                            (progn
                              (setq bump (g377_bump_force_rec startPoly jj 1 (cadr rec) dist))
                              (if bump
                                (progn
                                  (setq kk2 0)
                                  (while (< kk2 (length bump))
                                    (setq seq (g365_append_pt seq (nth kk2 bump)))
                                    (setq kk2 (1+ kk2))
                                  )
                                  (setq didBump 1)
                                )
                              )
                            )
                          )
                          (setq tmp (cdr tmp))
                        )
                      )
                    )

                    (if (not didBump)
                      (setq seq (g365_append_pt seq (nth jj startPoly)))
                    )
                    (setq jj (1+ jj))
                  )

                  (setq farOther (g365_last otherPoly))
                  (setq seq (g365_append_pt seq farOther))

                  (setq nOther (length otherPoly))
                  (setq idxCur (- nOther 2))
                  (while (>= idxCur 1)
                    (setq key (g365_ptkey (nth idxCur childAug)))
                    (setq brList (cdr (assoc key childBM)))
                    (setq didBump nil)

                    (if brList
                      (progn
                        (setq tmp brList)
                        (while tmp
                          (setq rec (car tmp))
                          (if (= (car rec) exitTag)
                            (progn
                              (setq bump (g377_bump_force_rec otherPoly idxCur -1 (cadr rec) dist))
                              (if bump
                                (progn
                                  (setq kk2 0)
                                  (while (< kk2 (length bump))
                                    (setq seq (g365_append_pt seq (nth kk2 bump)))
                                    (setq kk2 (1+ kk2))
                                  )
                                  (setq didBump 1)
                                )
                              )
                            )
                          )
                          (setq tmp (cdr tmp))
                        )
                      )
                    )

                    (if (not didBump)
                      (setq seq (g365_append_pt seq (nth idxCur otherPoly)))
                    )

                    (setq idxCur (1- idxCur))
                  )

                  (setq seq (g365_append_pt seq exit))
                  seq
                )
              )
            )
            nil
          )
        )
      )
    )
  )
)

(defun g377_get_bpt (boundaryPts idx / isClosed)
  (setq isClosed (g376_is_closed boundaryPts))
  (if isClosed
    (g376_nth_wrap boundaryPts idx)
    (g376_nth_safe boundaryPts idx)
  )
)

(defun g378_pt_towards (from to d / vx vy ln k)
  (setq vx (- (car to) (car from)))
  (setq vy (- (cadr to) (cadr from)))
  (setq ln (sqrt (+ (* vx vx) (* vy vy))))
  (if (<= ln 1e-9)
    from
    (progn
      (setq k (/ d ln))
      (list (+ (car from) (* k vx)) (+ (cadr from) (* k vy)) 0.0)
    )
  )
)

(defun g377_valid_inter (p0 p1 a b bpt maxd / ip tb tp)
  (setq ip (g365_line_inter p0 p1 a b))
  (if ip
    (progn
      (setq tb (g365_seg_param a b ip))
      (setq tp (g365_seg_param p0 p1 ip))
      (if (and tb tp
               (>= tb -0.05) (<= tb 1.05)
               (>= tp -0.05) (<= tp 1.05)
               (<= (distance ip bpt) maxd))
        ip
        nil
      )
    )
    nil
  )
)

(defun g377_proj_on_seg (p a b / res)
  (setq res (g365_closest_on_seg p a b))
  (if res (nth 0 res) nil)
)

(defun g377_pick_attach (poly prevPt bpt nextPt maxd usePrev / p0 p1 ip)
  (setq p0 (nth 0 poly))
  (setq p1 (nth 1 poly))
  (if (and p0 p1)
    (progn
      (if usePrev
        (progn
          (setq ip (if prevPt (g377_valid_inter p0 p1 prevPt bpt bpt maxd) nil))
          (if (null ip) (setq ip (if prevPt (g377_proj_on_seg p0 prevPt bpt) nil)))
        )
        (progn
          (setq ip (if nextPt (g377_valid_inter p0 p1 bpt nextPt bpt maxd) nil))
          (if (null ip) (setq ip (if nextPt (g377_proj_on_seg p0 bpt nextPt) nil)))
        )
      )
      (if (and ip (> (distance ip bpt) maxd)) (setq ip nil))
      ip
    )
    nil
  )
)

(defun g377_bump_force_rec (boundaryPts idx step childId dist / bump)
  (setq bump (g372_bump_open_mouth_rec boundaryPts idx step childId dist))
  (if bump bump (g377_bump_vertex_cap boundaryPts idx step childId dist))
)

(defun g377_bump_force_half (boundaryPts idx step childId dist useIncoming / bump)
  (setq bump (g372_bump_open_mouth_half_rec boundaryPts idx step childId dist useIncoming))
  (if bump bump (g377_bump_vertex_cap boundaryPts idx step childId dist))
)

(defun g385_chamfer_fix (pts dist / n i out p0 p1 p2 p3 u01 u12 u23 l12 dot01_23 dot12_01 dot12_23 ip maxD)
  (setq n (length pts))
  (if (or (null pts) (< n 4))
    pts
    (progn
      (setq out nil)
      (setq out (g365_append_pt out (nth 0 pts)))
      (setq i 1)
      (while (< i n)
        (if (<= i (- n 3))
          (progn
            (setq p0 (nth (1- i) pts))
            (setq p1 (nth i pts))
            (setq p2 (nth (1+ i) pts))
            (setq p3 (nth (+ i 2) pts))

            (setq l12 (distance p1 p2))
            (setq u01 (g365_unit (- (car p1) (car p0)) (- (cadr p1) (cadr p0))))
            (setq u12 (g365_unit (- (car p2) (car p1)) (- (cadr p2) (cadr p1))))
            (setq u23 (g365_unit (- (car p3) (car p2)) (- (cadr p3) (cadr p2))))

            (setq dot01_23 (g365_abs (g365_dot (car u01) (cadr u01) (car u23) (cadr u23))))
            (setq dot12_01 (g365_abs (g365_dot (car u12) (cadr u12) (car u01) (cadr u01))))
            (setq dot12_23 (g365_abs (g365_dot (car u12) (cadr u12) (car u23) (cadr u23))))

            (setq maxD (* 8.0 dist))

            (if (and (> dist 0.0)
                     (<= l12 (* 4.0 dist))
                     (< dot01_23 0.35)
                     (< dot12_01 0.95)
                     (< dot12_23 0.95)
                     (<= (distance p1 p0) maxD)
                     (<= (distance p2 p3) maxD))
              (progn
                (setq ip (g365_line_inter p0 p1 p2 p3))
                (if (and ip (<= (distance ip p1) maxD) (<= (distance ip p2) maxD))
                  (progn
                    (setq out (g365_append_pt out ip))
                    (setq i (+ i 2))
                  )
                  (progn
                    (setq out (g365_append_pt out p1))
                    (setq i (1+ i))
                  )
                )
              )
              (progn
                (setq out (g365_append_pt out p1))
                (setq i (1+ i))
              )
            )
          )
          (progn
            (setq out (g365_append_pt out (nth i pts)))
            (setq i (1+ i))
          )
        )
      )
      out
    )
  )
)

(defun g385_simplify_colinear (pts dist / n i out pPrev pCur pNext u1 u2 dotv res d tol)
  (setq n (length pts))
  (if (or (null pts) (< n 3))
    pts
    (progn
      (setq tol (max 0.05 (* 0.02 dist)))
      (setq out nil)
      (setq out (g365_append_pt out (nth 0 pts)))
      (setq i 1)
      (while (< i (1- n))
        (setq pPrev (g365_last out))
        (setq pCur (nth i pts))
        (setq pNext (nth (1+ i) pts))

        (setq u1 (g365_unit (- (car pCur) (car pPrev)) (- (cadr pCur) (cadr pPrev))))
        (setq u2 (g365_unit (- (car pNext) (car pCur)) (- (cadr pNext) (cadr pCur))))
        (setq dotv (g365_abs (g365_dot (car u1) (cadr u1) (car u2) (cadr u2))))

        (setq res (g365_closest_on_seg pCur pPrev pNext))
        (setq d (if res (nth 2 res) 1e99))

        (if (and (> dotv 0.9995) (<= d tol))
          out
          (setq out (g365_append_pt out pCur))
        )

        (setq i (1+ i))
      )
      (setq out (g365_append_pt out (nth (1- n) pts)))
      out
    )
  )
)

(defun g385_postprocess_path (pts dist / p1 p2)
  (setq p1 (g385_chamfer_fix pts dist))
  (setq p2 (g385_simplify_colinear p1 dist))
  p2
)

(defun g418_drop_last (pts / out)
  (if (and pts (> (length pts) 0))
    (reverse (cdr (reverse pts)))
    pts
  )
)

(defun g419_entmake_open_poly (lay pts / n data e p)
  (setq n (length pts))
  (if (and n (> n 1))
    (progn
      (setq data (list
        (cons 0 "LWPOLYLINE")
        (cons 100 "AcDbEntity")
        (cons 8 lay)
        (cons 100 "AcDbPolyline")
        (cons 90 n)
        (cons 70 0)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g419_main_tangent (pts idx / n i0 i1 p0 p1 v)
  (setq n (length pts))
  (if (< n 2)
    (list 0.0 0.0)
    (progn
      (setq i0 (max 0 (1- idx)))
      (setq i1 (min (1- n) (1+ idx)))
      (setq p0 (nth i0 pts))
      (setq p1 (nth i1 pts))
      (setq v (list (- (car p1) (car p0)) (- (cadr p1) (cadr p0))))
      (g365_unit (car v) (cadr v))
    )
  )
)

(defun g419_best_cap_start_index (outPts pMain uMain dist / n i a b mid v u dotv len d score best bestI)
  (setq n (length outPts))
  (setq i 0 best 1e99 bestI 0)
  (while (< i n)
    (setq a (nth i outPts))
    (setq b (nth (rem (1+ i) n) outPts))
    (setq mid (list (/ (+ (car a) (car b)) 2.0) (/ (+ (cadr a) (cadr b)) 2.0) 0.0))
    (setq v (list (- (car b) (car a)) (- (cadr b) (cadr a))))
    (setq len (sqrt (+ (* (car v) (car v)) (* (cadr v) (cadr v)))))
    (setq u (if (> len 1e-9) (list (/ (car v) len) (/ (cadr v) len)) (list 0.0 0.0)))
    (setq dotv (g365_abs (g365_dot (car u) (cadr u) (car uMain) (cadr uMain))))
    (setq d (distance mid pMain))
    (setq score (+ d (* dotv (* 10.0 dist)) (g365_abs (- len (* 2.0 dist)))))
    (if (< score best)
      (progn (setq best score) (setq bestI i))
    )
    (setq i (1+ i))
  )
  (rem (1+ bestI) n)
)

(defun g418_rebuild_outline_seam (outline lay pick mainPts dist / outPts nearV iMain pMain uMain k pts2 newEnt)
  (if (and outline (entget outline))
    (progn
      (setq outPts (g365_get_pts outline))
      (if (and outPts (>= (length outPts) 3) (g376_is_closed outPts))
        (setq outPts (g418_drop_last outPts))
      )
      (if (and outPts (>= (length outPts) 3) pick mainPts dist)
        (progn
          (setq nearV (g417_nearest_vertex pick mainPts))
          (setq iMain (car nearV))
          (setq pMain (cadr nearV))
          (setq uMain (g419_main_tangent mainPts iMain))
          (setq k (g419_best_cap_start_index outPts pMain uMain dist))
          (setq pts2 (g417_rotate outPts k))
          (setq newEnt (g419_entmake_open_poly lay pts2))
          (if newEnt
            (progn
              (entdel outline)
              newEnt
            )
            outline
          )
        )
        outline
      )
    )
    outline
  )
)

(defun g387_dist_pt_seg (p a b / res)
  (setq res (g365_closest_on_seg p a b))
  (if res (nth 2 res) 1e99)
)

(defun g387_on_seg (a b p / u)
  (setq u (g365_seg_param a b p))
  (and u (>= u -0.001) (<= u 1.001))
)

(defun g387_attach_inter (poly a b bpt maxd / p0 p1 ip)
  (setq p0 (nth 0 poly) p1 (nth 1 poly))
  (setq ip (if (and p0 p1 a b) (g377_valid_inter p0 p1 a b bpt maxd) nil))
  ip
)

(defun g388_pen (pt dist)
  (if pt 0.0 dist)
)

(defun g388_best_snap (p a b c d tol / r1 r2 d1 d2)
  (setq r1 (if (and a b) (g365_closest_on_seg p a b) nil))
  (setq r2 (if (and c d) (g365_closest_on_seg p c d) nil))
  (setq d1 (if r1 (nth 2 r1) 1e99))
  (setq d2 (if r2 (nth 2 r2) 1e99))
  (cond
    ((and r1 (<= d1 tol) (<= d1 d2)) (nth 0 r1))
    ((and r2 (<= d2 tol)) (nth 0 r2))
    (t p)
  )
)

(defun g372_colorize_assigned (aci) nil)

(defun g405_safe_entdel (e)
  (if (and e (entget e))
    (vl-catch-all-apply 'entdel (list e))
  )
)

(defun g372_delete_assigned (keepEnt / scan pair ent delCnt skipCnt)
  (setq delCnt 0)
  (setq skipCnt 0)
  (setq scan g372_assigned)
  (while scan
    (setq pair (car scan))
    (setq ent (car pair))
    (if (and ent (/= ent keepEnt) (entget ent))
      (progn
        (if (vl-catch-all-error-p (vl-catch-all-apply 'entdel (list ent)))
          (setq skipCnt (1+ skipCnt))
          (setq delCnt (1+ delCnt))
        )
      )
    )
    (setq scan (cdr scan))
  )
  T
)

(defun g405_on_seg (a b p / u)
  (setq u (g365_seg_param a b p))
  (and u (>= u -0.001) (<= u 1.001))
)

(defun g405_closest_pt (p a b / r)
  (setq r (g365_closest_on_seg p a b))
  (if r (car r) p)
)

(defun g405_dist_pt_seg (p a b / r)
  (setq r (g365_closest_on_seg p a b))
  (if r (nth 2 r) 1e99)
)

(defun g405_clamp_leg (p a b bpt maxLen / cp)
  (setq cp (g405_closest_pt p a b))
  (if (> (distance cp bpt) maxLen)
    (g378_pt_towards bpt cp maxLen)
    cp
  )
)

(defun g405_attach_score (aS aE prevPt bpt nextPt dist / pen)
  (setq pen 0.0)
  (if (and prevPt (not (g405_on_seg prevPt bpt aS)))
    (setq pen (+ pen (* 50.0 dist)))
  )
  (if (and nextPt (not (g405_on_seg bpt nextPt aE)))
    (setq pen (+ pen (* 50.0 dist)))
  )
  (+ pen (distance aS bpt) (distance aE bpt))
)

(defun g406_pt_ok (p)
  (and (listp p)
       (numberp (car p))
       (numberp (cadr p)))
)

(defun g406_to3 (p)
  (if (g406_pt_ok p)
    (list (car p) (cadr p)
          (if (and (caddr p) (numberp (caddr p))) (caddr p) 0.0))
    nil
  )
)

(defun g406_mid (p q / p3 q3)
  (setq p3 (g406_to3 p))
  (setq q3 (g406_to3 q))
  (if (and p3 q3)
    (list (/ (+ (car p3) (car q3)) 2.0)
          (/ (+ (cadr p3) (cadr q3)) 2.0)
          0.0)
    nil
  )
)

(defun g406_get_v (pts i / isClosed)
  (setq isClosed (g376_is_closed pts))
  (if isClosed (g376_nth_wrap pts i) (g376_nth_safe pts i))
)

(defun g406_best_corner_idx (boundaryPts idx step seed / cand bestI bestD i p s3 d)
  (setq s3 (g406_to3 seed))
  (if (null s3)
    idx
    (progn
      (setq cand (list idx
                       (- idx step) (+ idx step)
                       (- idx (* 2 step)) (+ idx (* 2 step))))
      (setq bestI idx)
      (setq bestD 1e99)
      (foreach i cand
        (setq p (g406_get_v boundaryPts i))
        (if (g406_pt_ok p)
          (progn
            (setq d (distance s3 (g406_to3 p)))
            (if (< d bestD) (setq bestD d bestI i))
          )
        )
      )
      bestI
    )
  )
)

(defun g407_ptdist (p q / p3 q3)
  (setq p3 (g406_to3 p))
  (setq q3 (g406_to3 q))
  (if (and p3 q3) (distance p3 q3) 1e99)
)

(defun g408_min2 (a b) (if (< a b) a b))
(defun g408_min3 (a b c) (g408_min2 (g408_min2 a b) c))

(defun g408_swap2 (a b / t) (setq t a) (setq a b) (setq b t) (list a b))

(defun g408_fix_side_order (side aug0 / s0 se)
  (if (and side aug0 (> (length side) 1))
    (progn
      (setq s0 (car side))
      (setq se (g365_last side))
      (if (< (distance (g406_to3 se) (g406_to3 aug0))
             (distance (g406_to3 s0) (g406_to3 aug0)))
        (g365_rev side)
        side
      )
    )
    side
  )
)

(defun g409_p2 (p)
  (and (listp p) (numberp (car p)) (numberp (cadr p)))
)

(defun g409_to3 (p)
  (if (g409_p2 p)
    (list (car p) (cadr p) (if (numberp (caddr p)) (caddr p) 0.0))
    nil
  )
)

(defun g409_dist (a b / aa bb)
  (setq aa (g409_to3 a))
  (setq bb (g409_to3 b))
  (if (and aa bb) (distance aa bb) 1e99)
)

(defun g409_find_p1 (pts p0 / i p1)
  (setq i 1 p1 nil)
  (while (and (< i (length pts)) (null p1))
    (if (> (g409_dist (nth i pts) p0) 1e-6)
      (setq p1 (nth i pts))
    )
    (setq i (1+ i))
  )
  (if p1 p1 (nth 1 pts))
)

(defun g410_ptp (p)
  (and p (listp p) (numberp (car p)) (numberp (cadr p)))
)

(defun g410_find_p1_safe (pts p0 / p1)
  (setq p1 (g409_find_p1 pts p0))
  (if (g410_ptp p1)
    p1
    (if (and pts (> (length pts) 1) (g410_ptp (nth 1 pts)))
      (nth 1 pts)
      p0
    )
  )
)

(defun g411_min (a b) (if (< a b) a b))

(defun g411_orient_triplet_to_bpt (aug brL brR bpt / a0 aN)
  (setq a0 (car aug))
  (setq aN (g365_last aug))
  (if (and a0 aN bpt (> (distance a0 bpt) (distance aN bpt)))
    (list (g365_rev aug) (g365_rev brL) (g365_rev brR))
    (list aug brL brR)
  )
)

(defun g412_wrap_index (i n)
  (if (and n (> n 0))
    (rem (+ i (* n 1000)) n)
    i
  )
)

(defun g412_seek_leg_point (pts idx dir bpt minD isClosed / n j k cand)
  (setq n (length pts))
  (setq j 1)
  (setq cand nil)
  (while (and (null cand) (< j (min 12 n)))
    (setq k (+ idx (* dir j)))
    (if isClosed
      (setq k (g412_wrap_index k n))
      (if (or (< k 0) (>= k n)) (setq k nil))
    )
    (if k
      (progn
        (setq cand (nth k pts))
        (if (or (null cand) (<= (distance cand bpt) minD))
          (setq cand nil)
        )
      )
    )
    (setq j (1+ j))
  )
  (if cand cand (if isClosed (g376_nth_wrap pts (+ idx dir)) (g376_nth_safe pts (+ idx dir))))
)

(defun g413_inter_line (a b c d / x1 y1 x2 y2 x3 y3 x4 y4 den t1 t2 x y)
  (if (and a b c d)
    (progn
      (setq x1 (car a)  y1 (cadr a))
      (setq x2 (car b)  y2 (cadr b))
      (setq x3 (car c)  y3 (cadr c))
      (setq x4 (car d)  y4 (cadr d))
      (setq den (- (* (- x1 x2) (- y3 y4)) (* (- y1 y2) (- x3 x4))))
      (if (< (abs den) 1e-12)
        nil
        (progn
          (setq t1 (- (* x1 y2) (* y1 x2)))
          (setq t2 (- (* x3 y4) (* y3 x4)))
          (setq x (/ (- (* t1 (- x3 x4)) (* (- x1 x2) t2)) den))
          (setq y (/ (- (* t1 (- y3 y4)) (* (- y1 y2) t2)) den))
          (list x y)
        )
      )
    )
    nil
  )
)

(defun g413_attach_on_bound (a b c d dist / ip cp1 cp2 tol)
  (setq tol (* 0.6 dist))
  (setq ip (g413_inter_line a b c d))
  (if ip
    (progn
      (setq cp1 (g365_closest_on_seg ip a b))
      (setq cp2 (g365_closest_on_seg ip c d))
      (if (and cp1 cp2 (<= (nth 2 cp1) tol) (<= (nth 2 cp2) tol))
        ip
        nil
      )
    )
    nil
  )
)

(defun g377_bump_vertex_cap (boundaryPts idx step childId dist /
                                   childAug brL brR childBM bpt isClosed prevPt nextPt
                                   lenPrev lenNext minLen capD minD trip
                                   enter exit
                                   brL0 brR0 side1 side2 tag1 tag2
                                   attIn attOut
                                   n jj idxCur key brList tmp rec bump didBump kk2 farOther seq)

  (setq childAug (g372_node childId 'aug))
  (setq brL      (g372_node childId 'left))
  (setq brR      (g372_node childId 'right))
  (setq childBM  (g372_node childId 'branchMap))

  (setq isClosed (g376_is_closed boundaryPts))
  (setq bpt (g377_get_bpt boundaryPts idx))

  (if (or (null bpt) (null childAug) (< (length childAug) 2)
          (null brL) (null brR) (< (length brL) 2) (< (length brR) 2))
    nil
    (progn
      (setq minD (max (* 0.15 dist) 0.001))
      (setq prevPt (g412_seek_leg_point boundaryPts idx -1 bpt minD isClosed))
      (setq nextPt (g412_seek_leg_point boundaryPts idx  1 bpt minD isClosed))

      (setq trip (g411_orient_triplet_to_bpt childAug brL brR bpt))
      (setq childAug (nth 0 trip))
      (setq brL      (nth 1 trip))
      (setq brR      (nth 2 trip))

      (setq lenPrev (if prevPt (distance bpt prevPt) 0.0))
      (setq lenNext (if nextPt (distance bpt nextPt) 0.0))
      (cond
        ((and prevPt nextPt) (setq minLen (min lenPrev lenNext)))
        (prevPt             (setq minLen lenPrev))
        (nextPt             (setq minLen lenNext))
        (t                  (setq minLen 0.0))
      )

      (setq capD (min (* 0.7 dist) (* 0.45 minLen)))
      (if (< capD (* 0.05 dist)) (setq capD (* 0.05 dist)))

      (setq enter (if prevPt (g378_pt_towards bpt prevPt capD) bpt))
      (setq exit  (if nextPt (g378_pt_towards bpt nextPt capD) bpt))

      (setq brL0 (car brL))
      (setq brR0 (car brR))

      (if (and brL0 brR0 prevPt (< (distance brL0 prevPt) (distance brR0 prevPt)))
        (progn
          (setq side1 brL  tag1  1)
          (setq side2 brR  tag2 -1)
        )
        (progn
          (setq side1 brR  tag1 -1)
          (setq side2 brL  tag2  1)
        )
      )

      (setq attIn  (if prevPt (g413_attach_on_bound (nth 0 side1) (nth 1 side1) prevPt bpt dist) bpt))
      (setq attOut (if nextPt (g413_attach_on_bound (nth 0 side2) (nth 1 side2) bpt nextPt dist) bpt))
      (if (null attIn)  (setq attIn bpt))
      (if (null attOut) (setq attOut bpt))

      (setq side1 (cons attIn  (cdr side1)))
      (setq side2 (cons attOut (cdr side2)))

      (setq n (length childAug))
      (if (or (< n 2) (/= (length side1) n) (/= (length side2) n))
        nil
        (progn
          (setq seq nil)

          (setq seq (g365_append_pt seq enter))
          (if prevPt
            (progn
              (if (and (not (g387_on_seg prevPt bpt attIn)) (not (g365_closep attIn bpt)))
                (setq seq (g365_append_pt seq bpt))
              )
              (setq seq (g365_append_pt seq attIn))
            )
            (setq seq (g365_append_pt seq attIn))
          )

          (setq jj 1)
          (while (< jj n)
            (setq key (g365_ptkey (nth jj childAug)))
            (setq brList (if childBM (cdr (assoc key childBM)) nil))
            (setq didBump nil)

            (if (and brList (> jj 0) (< jj (1- n)))
              (progn
                (setq tmp brList)
                (while tmp
                  (setq rec (car tmp))
                  (if (= (car rec) tag1)
                    (progn
                      (setq bump (g377_bump_force_rec side1 jj 1 (cadr rec) dist))
                      (if bump
                        (progn
                          (setq kk2 0)
                          (while (< kk2 (length bump))
                            (setq seq (g365_append_pt seq (nth kk2 bump)))
                            (setq kk2 (1+ kk2))
                          )
                          (setq didBump 1)
                        )
                      )
                    )
                  )
                  (setq tmp (cdr tmp))
                )
              )
            )

            (if (not didBump)
              (setq seq (g365_append_pt seq (nth jj side1)))
            )
            (setq jj (1+ jj))
          )

          (setq farOther (nth (1- n) side2))
          (setq seq (g365_append_pt seq farOther))

          (setq idxCur (- n 2))
          (while (>= idxCur 0)
            (setq key (g365_ptkey (nth idxCur childAug)))
            (setq brList (if childBM (cdr (assoc key childBM)) nil))
            (setq didBump nil)

            (if (and brList (> idxCur 0) (< idxCur (1- n)))
              (progn
                (setq tmp brList)
                (while tmp
                  (setq rec (car tmp))
                  (if (= (car rec) tag2)
                    (progn
                      (setq bump (g377_bump_force_rec side2 idxCur -1 (cadr rec) dist))
                      (if bump
                        (progn
                          (setq kk2 0)
                          (while (< kk2 (length bump))
                            (setq seq (g365_append_pt seq (nth kk2 bump)))
                            (setq kk2 (1+ kk2))
                          )
                          (setq didBump 1)
                        )
                      )
                    )
                  )
                  (setq tmp (cdr tmp))
                )
              )
            )

            (if (not didBump)
              (setq seq (g365_append_pt seq (nth idxCur side2)))
            )
            (setq idxCur (1- idxCur))
          )

          (if nextPt
            (progn
              (if (and (not (g387_on_seg bpt nextPt attOut)) (not (g365_closep attOut bpt)))
                (setq seq (g365_append_pt seq bpt))
              )
              (setq seq (g365_append_pt seq exit))
            )
            (setq seq (g365_append_pt seq exit))
          )

          seq
        )
      )
    )
  )
)

(defun g415_entmake_closed_poly (lay pts / n data e p)
  (setq n (length pts))
  (if (and n (> n 2))
    (progn
      (setq data (list
        (cons 0 "LWPOLYLINE")
        (cons 100 "AcDbEntity")
        (cons 8 lay)
        (cons 100 "AcDbPolyline")
        (cons 90 n)
        (cons 70 1)
        (cons 38 0.0)
        (cons 43 0.0)
      ))
      (while pts
        (setq p (car pts))
        (setq data (append data (list (cons 10 (list (car p) (cadr p))))))
        (setq pts (cdr pts))
      )
      (setq e (entmakex data))
      e
    )
    nil
  )
)

(defun g418_flush_cmd (/ i)
  (setq i 0)
  (while (and (> (getvar "CMDACTIVE") 0) (< i 80))
    (vl-cmdf "")
    (setq i (1+ i))
  )
  (setq i 0)
  (while (and (> (getvar "CMDACTIVE") 0) (< i 10))
    (vl-cmdf "\003") 
    (setq i (1+ i))
  )
  (setq i 0)
  (while (and (> (getvar "CMDACTIVE") 0) (< i 10))
    (vl-cmdf "_.CANCEL")
    (setq i (1+ i))
  )
  T
)

(defun g415_ss_from_list (lst / ss)
  (setq ss (ssadd))
  (while lst
    (if (and (car lst) (entget (car lst)))
      (ssadd (car lst) ss)
    )
    (setq lst (cdr lst))
  )
  ss
)

(defun g415_collect_new_ents (afterEnt / e out)
  (setq out nil)
  (setq e (if afterEnt (entnext afterEnt) (entnext nil)))
  (while e
    (setq out (cons e out))
    (setq e (entnext e))
  )
  (reverse out)
)

(defun g415_poly_closed_p (e / ed flg)
  (setq ed (entget e))
  (setq flg (cdr (assoc 70 ed)))
  (and flg (= 1 (logand 1 flg)))
)

(defun g415_poly_area (e / o a)
  (vl-load-com)
  (setq o (vlax-ename->vla-object e))
  (setq a (vl-catch-all-apply 'vla-get-Area (list o)))
  (if (vl-catch-all-error-p a) 0.0 a)
)

(defun g415_pick_largest_closed_poly (cand / best bestA e a)
  (setq best nil bestA 0.0)
  (while cand
    (setq e (car cand))
    (if (and (entget e) (= (cdr (assoc 0 (entget e))) "LWPOLYLINE") (g415_poly_closed_p e))
      (progn
        (setq a (g415_poly_area e))
        (if (> a bestA)
          (progn (setq best e) (setq bestA a))
        )
      )
    )
    (setq cand (cdr cand))
  )
  best
)

(defun g415_delete_ents (lst)
  (while lst
    (if (and (car lst) (entget (car lst)))
      (entdel (car lst))
    )
    (setq lst (cdr lst))
  )
  T
)

(defun g415_get_assigned_original_ents (allEnts / out scan e)
  (setq out nil)
  (setq scan allEnts)
  (while scan
    (setq e (car scan))
    (if (and e (g372_assigned_p e))
      (setq out (cons e out))
    )
    (setq scan (cdr scan))
  )
  (reverse out)
)

(defun g415_make_tube_poly_from_ent (ent dist lay / pts left right path)
  (setq pts (g365_get_pts ent))
  (if (and pts (>= (length pts) 2))
    (progn
      (setq left  (g365_offset_open_pts pts dist  1))
      (setq right (g365_offset_open_pts pts dist -1))
      (if (and left right (= (length left) (length pts)) (= (length right) (length pts)))
        (progn
          (setq path (append left (reverse right)))
          (g415_entmake_closed_poly lay path)
        )
        nil
      )
    )
    nil
  )
)

(defun g415_union_tubes_to_outline (tubePls lay / oldCm oldPe oldOsm oldCl beforeR regEnts ssReg beforeU uniEnts regU beforeX curves ssC beforeP newEnts cand best)
  (setq best nil)
  (if (null tubePls)
    nil
    (progn
      (setq oldCm (getvar "CMDECHO"))
      (setq oldPe (getvar "PEDITACCEPT"))
      (setq oldOsm (getvar "OSMODE"))
      (setq oldCl (getvar "CLAYER"))
      (setvar "CMDECHO" 0)
      (setvar "PEDITACCEPT" 1)
      (setvar "OSMODE" 0)

      (setq beforeR (entlast))
      (vl-cmdf "_.REGION" (g415_ss_from_list tubePls) "")
      (setq regEnts (g415_collect_new_ents beforeR))

      (if regEnts
        (progn
          (setq ssReg (g415_ss_from_list regEnts))
          (setq beforeU (entlast))
          (vl-cmdf "_.UNION" ssReg "")
          (setq uniEnts (g415_collect_new_ents beforeU))
          (if uniEnts
            (setq regU (car (last uniEnts)))
            (setq regU (entlast))
          )

          (if (and regU (entget regU))
            (progn
              (setq beforeX (entlast))
              (vl-cmdf "_.EXPLODE" regU)
              (setq curves (g415_collect_new_ents beforeX))

              (if curves
                (progn
                  (setq ssC (g415_ss_from_list curves))
                  (setq beforeP (entlast))
                  (vl-cmdf "_.PEDIT" "M" ssC "" "J" "" 0.0 "" "C" "X" "" "")
                  (g418_flush_cmd)
                  (setq newEnts (g415_collect_new_ents beforeP))
                  (setq cand (append curves newEnts))
                  (setq best (g415_pick_largest_closed_poly cand))

                  (g415_delete_ents (vl-remove best cand))
                )
              )
            )
          )
        )
      )

      (g418_flush_cmd)
      (setvar "CMDECHO" oldCm)
      (setvar "PEDITACCEPT" oldPe)
      (setvar "OSMODE" oldOsm)
      (setvar "CLAYER" oldCl)

      best
    )
  )
)

(defun g417_take (lst n / out i)
  (setq out nil i 0)
  (while (and lst (< i n))
    (setq out (cons (car lst) out))
    (setq lst (cdr lst))
    (setq i (1+ i))
  )
  (reverse out)
)

(defun g417_nthcdr (n lst / i)
  (setq i 0)
  (while (and lst (< i n))
    (setq lst (cdr lst))
    (setq i (1+ i))
  )
  lst
)

(defun g417_rotate (lst k / a b)
  (if (or (null lst) (<= k 0))
    lst
    (progn
      (setq a (g417_nthcdr k lst))
      (setq b (g417_take lst k))
      (append a b)
    )
  )
)

(defun g417_set_nth (lst idx val / i out)
  (setq i 0 out nil)
  (while lst
    (setq out (cons (if (= i idx) val (car lst)) out))
    (setq lst (cdr lst))
    (setq i (1+ i))
  )
  (reverse out)
)

(defun g417_nearest_vertex (p pts / i bestI bestD d)
  (setq i 0 bestI 0 bestD 1e99)
  (while (< i (length pts))
    (setq d (distance p (nth i pts)))
    (if (< d bestD)
      (progn
        (setq bestD d)
        (setq bestI i)
      )
    )
    (setq i (1+ i))
  )
  (list bestI (nth bestI pts) bestD)
)

(defun g417_farthest_index (p pts / i bestI bestD d)
  (setq i 0 bestI 0 bestD -1.0)
  (while (< i (length pts))
    (setq d (distance p (nth i pts)))
    (if (> d bestD)
      (progn
        (setq bestD d)
        (setq bestI i)
      )
    )
    (setq i (1+ i))
  )
  bestI
)

(defun g417_lwpoly_parse (ed / pts bul sw ew curIdx pr code val)
  (setq pts nil bul nil sw nil ew nil curIdx -1)
  (while ed
    (setq pr (car ed))
    (setq code (car pr))
    (setq val (cdr pr))
    (cond
      ((= code 10)
        (setq pts (append pts (list (list (car val) (cadr val) 0.0))))
        (setq bul (append bul (list 0.0)))
        (setq sw  (append sw  (list nil)))
        (setq ew  (append ew  (list nil)))
        (setq curIdx (1- (length pts)))
      )
      ((and (>= curIdx 0) (= code 42))
        (setq bul (g417_set_nth bul curIdx val))
      )
      ((and (>= curIdx 0) (= code 40))
        (setq sw (g417_set_nth sw curIdx val))
      )
      ((and (>= curIdx 0) (= code 41))
        (setq ew (g417_set_nth ew curIdx val))
      )
    )
    (setq ed (cdr ed))
  )
  (list pts bul sw ew)
)

(defun g417_lwpoly_rebuild (pre pts bul sw ew / n i x y out)
  (setq n (length pts))
  (setq out nil)
  (while pre
    (if (= (car (car pre)) 90)
      (setq out (cons (cons 90 n) out))
      (setq out (cons (car pre) out))
    )
    (setq pre (cdr pre))
  )
  (setq out (reverse out))

  (setq i 0)
  (while (< i n)
    (setq x (car (nth i pts)))
    (setq y (cadr (nth i pts)))
    (setq out (append out (list (cons 10 (list x y)))))
    (if (nth i sw) (setq out (append out (list (cons 40 (nth i sw))))))
    (if (nth i ew) (setq out (append out (list (cons 41 (nth i ew))))))
    (if (and (nth i bul) (/= (nth i bul) 0.0))
      (setq out (append out (list (cons 42 (nth i bul)))))
    )
    (setq i (1+ i))
  )
  out
)

(defun g417_lwpoly_rotate_start (e k / ed pre rest parsed pts bul sw ew n pts2 bul2 sw2 ew2 newEd)
  (setq ed (entget e))
  (if (/= (cdr (assoc 0 ed)) "LWPOLYLINE")
    nil
    (progn
      (setq pre nil rest ed)
      (while (and rest (/= (car (car rest)) 10))
        (setq pre (append pre (list (car rest))))
        (setq rest (cdr rest))
      )
      (setq parsed (g417_lwpoly_parse ed))
      (setq pts (nth 0 parsed))
      (setq bul (nth 1 parsed))
      (setq sw  (nth 2 parsed))
      (setq ew  (nth 3 parsed))
      (setq n (length pts))
      (if (< n 3)
        nil
        (progn
          (setq k (rem k n))
          (if (< k 0) (setq k (+ k n)))
          (setq pts2 (g417_rotate pts k))
          (setq bul2 (g417_rotate bul k))
          (setq sw2  (g417_rotate sw k))
          (setq ew2  (g417_rotate ew k))
          (setq newEd (g417_lwpoly_rebuild pre pts2 bul2 sw2 ew2))
          (entmod newEd)
          (entupd e)
          T
        )
      )
    )
  )
)

(defun g417_move_outline_seam (outline pick mainPts / nearV outPts k)
  (if (and outline pick mainPts)
    (progn
      (if (= (cdr (assoc 0 (entget outline))) "LWPOLYLINE")
        (progn
          (setq nearV (g417_nearest_vertex pick mainPts))
          (setq outPts (g365_get_pts outline))
          (if (and outPts (>= (length outPts) 3))
            (progn
              (setq k (g417_farthest_index (cadr nearV) outPts))
              (g417_lwpoly_rotate_start outline k)
            )
          )
        )
      )
    )
  )
  T
)

(vl-load-com)

(defun DEGZ--ename (x)
  (cond
    ((= (type x) 'ENAME) x)
    ((= (type x) 'VLA-OBJECT) (vlax-vla-object->ename x))
    (t nil)
  )
)

(defun DEGZ--pt2d (p)
  (cond
    ((and (listp p) (>= (length p) 2)) (list (car p) (cadr p)))
    (t p)
  )
)
(defun DEGZ--pt-ok-p (p)
  (and (listp p) (numberp (car p)) (numberp (cadr p)))
)

(defun DEGZ--pt2d-safe (p fallback / q)
  (cond
    ((DEGZ--pt-ok-p p) (DEGZ--pt2d p))
    ((and (listp p) (DEGZ--pt-ok-p (car p))) (DEGZ--pt2d (car p)))
    ((DEGZ--pt-ok-p fallback) (DEGZ--pt2d fallback))
    (T nil)
  )
)

(defun DEGZ--safe-distance (a b / pa pb)
  (setq pa (DEGZ--pt2d-safe a nil))
  (setq pb (DEGZ--pt2d-safe b nil))
  (if (and pa pb)
    (distance pa pb)
    0.0
  )
)

(defun DEGZ--redundant-mouth3-p (a b c / pa pb pc abx aby bcx bcy cross dot lenAB lenBC tol)
  (setq pa (DEGZ--pt2d-safe a nil))
  (setq pb (DEGZ--pt2d-safe b nil))
  (setq pc (DEGZ--pt2d-safe c nil))
  (if (and pa pb pc)
    (progn
      (setq abx (- (car pb) (car pa)))
      (setq aby (- (cadr pb) (cadr pa)))
      (setq bcx (- (car pc) (car pb)))
      (setq bcy (- (cadr pc) (cadr pb)))
      (setq cross (- (* abx bcy) (* aby bcx)))
      (setq dot (+ (* abx bcx) (* aby bcy)))
      (setq lenAB (sqrt (+ (* abx abx) (* aby aby))))
      (setq lenBC (sqrt (+ (* bcx bcx) (* bcy bcy))))
      (setq tol (* 1e-7 (max 1.0 (* lenAB lenBC))))
      (and (> lenAB 1e-9)
           (> lenBC 1e-9)
           (<= (abs cross) tol)
           (> (abs dot) 1e-8))
    )
    nil
  )
)

(defun DEGZ--mouth-redundant-p (a b c / pa pb pc abx aby bcx bcy cross dot lenAB lenBC tol)
  ;; Sadece ana hat agzinda kullanilir. Hesaptan kalan cok kucuk aci farklarini
  ;; ayni dogrultu sayar; gercek dirsek ve cikinti koselerine dokunmaz.
  (setq pa (DEGZ--pt2d-safe a nil))
  (setq pb (DEGZ--pt2d-safe b nil))
  (setq pc (DEGZ--pt2d-safe c nil))
  (if (and pa pb pc)
    (progn
      (setq abx (- (car pb) (car pa)))
      (setq aby (- (cadr pb) (cadr pa)))
      (setq bcx (- (car pc) (car pb)))
      (setq bcy (- (cadr pc) (cadr pb)))
      (setq cross (- (* abx bcy) (* aby bcx)))
      (setq dot (+ (* abx bcx) (* aby bcy)))
      (setq lenAB (sqrt (+ (* abx abx) (* aby aby))))
      (setq lenBC (sqrt (+ (* bcx bcx) (* bcy bcy))))
      (setq tol (* 1e-5 (max 1.0 (* lenAB lenBC))))
      (and (> lenAB 1e-9)
           (> lenBC 1e-9)
           (<= (abs cross) tol)
           (> (abs dot) 1e-8))
    )
    nil
  )
)
(defun DEGZ--trim-route-mouth-backtracks (pts / rev clean p)
  ;; Once ayni konumdaki ardisik rota noktalarini tek noktaya indir.
  ;; Sifir uzunluklu parca agizdaki dogrusal kontrolu engellemesin.
  (setq clean '())
  (foreach p pts
    (setq p (DEGZ--pt2d p))
    (if (or (null clean) (> (DEGZ--safe-distance p (car clean)) 1e-6))
      (setq clean (cons p clean))
    )
  )
  (setq pts (reverse clean))

  ;; Sadece agizlara komsu tasan vertexleri sil; dirsek icini koru.
  (while (and (>= (length pts) 3)
              (DEGZ--mouth-redundant-p (car pts) (cadr pts) (caddr pts)))
    (setq pts (cons (car pts) (cddr pts)))
  )
  (setq rev (reverse pts))
  (while (and (>= (length rev) 3)
              (DEGZ--mouth-redundant-p (car rev) (cadr rev) (caddr rev)))
    (setq rev (cons (car rev) (cddr rev)))
  )
  (reverse rev)
)
(defun DEGZ--drop-last (lst)
  (if (cdr lst) (reverse (cdr (reverse lst))) nil)
)

(defun DEGZ--pt3d (p)
  (setq p (DEGZ--pt2d p))
  (list (car p) (cadr p) 0.0)
)

(defun deg-safe-closest-point (crv pt / e r p2)
  (setq e (DEGZ--ename crv))
  (setq p2 (DEGZ--pt2d-safe pt nil))
  (if (or (not e) (not p2))
    p2
    (progn
      (setq r (vl-catch-all-apply 'vlax-curve-getClosestPointTo (list e (list (car p2) (cadr p2) 0.0))))
      (if (vl-catch-all-error-p r)
        p2
        (DEGZ--pt2d-safe r p2)
      )
    )
  )
)

(defun deg-safe-dist-at-point (crv pt / e cp r)
  (setq e  (DEGZ--ename crv))
  (if (not e)
    0.0
    (progn
      (setq cp (deg-safe-closest-point e pt))
      (if (not cp)
        0.0
        (progn
          (setq r  (vl-catch-all-apply 'vlax-curve-getDistAtPoint (list e (list (car cp) (cadr cp) 0.0))))
          (if (vl-catch-all-error-p r)
            0.0
            r
          )
        )
      )
    )
  )
)

(defun DEGZ--safe-props (e / ed pr)
  (setq e  (DEGZ--ename e))
  (setq ed (entget e))
  (setq pr (vl-remove nil (list (assoc 8 ed) (assoc 62 ed) (assoc 6 ed) (assoc 48 ed) (assoc 370 ed))))
  pr
)

(defun DEGZ--get-lwpts (e / ed pts x)
  (setq e  (DEGZ--ename e))
  (setq ed (entget e) pts '())
  (foreach x ed
    (if (= (car x) 10)
      (cond
        ((listp (cdr x)) (setq pts (append pts (list (DEGZ--pt2d (cdr x))))))
        ((and (listp x) (>= (length x) 3))
         (setq pts (append pts (list (list (cadr x) (caddr x))))))
      )
    )
  )
  pts
)

(defun DEGZ--entmakex-lwpoly (pts props closed70 / lst e)
  (if (null closed70) (setq closed70 0))
  (setq lst
    (append
      (list (cons 0 "LWPOLYLINE") (cons 100 "AcDbEntity"))
      props
      (list (cons 100 "AcDbPolyline") (cons 90 (length pts)) (cons 70 closed70))
      (apply 'append (mapcar '(lambda (p) (list (cons 10 (DEGZ--pt2d p)))) pts))
    )
  )
  (entmake lst)
  (setq e (entlast))
  e
)

(defun DEGZ--ensure-last (lst pt)
  (if (or (null lst) (> (distance (DEGZ--pt2d (last lst)) (DEGZ--pt2d pt)) 1e-6))
    (append lst (list (DEGZ--pt2d pt)))
    lst
  )
)

(defun DEGZ--unit (vx vy / l)
  (setq l (sqrt (+ (* vx vx) (* vy vy))))
  (if (> l 1e-12)
    (list (/ vx l) (/ vy l) l)
    (list 0.0 0.0 0.0)
  )
)


(defun DEGZ--perp-axis-from-curve (crv pt / obj par der dx dy)
  ;; ORTHO: curve tangent -> choose dominant axis, return perpendicular unit (rx ry)
  (setq obj (if (vlax-objectp crv) crv (vlax-ename->vla-object crv)))
  (setq par (vl-catch-all-apply 'vlax-curve-getParamAtPoint (list obj pt)))
  (if (vl-catch-all-error-p par)
    (progn
      (list 1.0 0.0)
    )
    (progn
      (setq der (vl-catch-all-apply 'vlax-curve-getFirstDeriv (list obj par)))
      (if (vl-catch-all-error-p der)
        (list 1.0 0.0)
        (progn
          (setq dx (car der) dy (cadr der))
          (if (>= (abs dx) (abs dy))
            (list 0.0 1.0)  ;; curve ~ horizontal -> perp is vertical
            (list 1.0 0.0)  ;; curve ~ vertical   -> perp is horizontal
          )
        )
      )
    )
  )
)

(defun DEGZ--curve-total (crv)
  (setq crv (DEGZ--ename crv))
  (if (not crv)
    0.0
    (vlax-curve-getDistAtParam crv (vlax-curve-getEndParam crv))
  )
)

(defun DEGZ--clamp (v a b)
  (cond ((< v a) a) ((> v b) b) (t v))
)

(defun DEGZ--distpair10 (distMid dirSign maxDist half / d1 d2)
  ;; distMid etrafÄ±nda Â±half (toplam 2*half) olacak ÅŸekilde iki mesafe Ã¼retir.
  ;; UÃ§larda (0 / maxDist) 10 birimi korumak iÃ§in iÃ§eri kaydÄ±rÄ±r.
  (setq full (* 2.0 half))
  (setq d1 (- distMid (* half dirSign)))
  (setq d2 (+ distMid (* half dirSign)))

  ;; Ã¶nce kaba clamp
  (setq d1 (DEGZ--clamp d1 0.0 maxDist))
  (setq d2 (DEGZ--clamp d2 0.0 maxDist))

  ;; eÄŸer 10 birim bozulduysa, uca gÃ¶re dÃ¼zelt
  (if (< (abs (- d2 d1)) (- full 1e-3))
    (cond
      ;; baÅŸlangÄ±ca Ã§ok yakÄ±n
      ((< distMid half)
        (if (>= dirSign 0.0)
          (progn (setq d1 0.0) (setq d2 (DEGZ--clamp full 0.0 maxDist)))
          (progn (setq d2 0.0) (setq d1 (DEGZ--clamp full 0.0 maxDist)))
        )
      )
      ;; sona Ã§ok yakÄ±n
      ((< (- maxDist distMid) half)
        (if (>= dirSign 0.0)
          (progn (setq d2 maxDist) (setq d1 (DEGZ--clamp (- maxDist full) 0.0 maxDist)))
          (progn (setq d1 maxDist) (setq d2 (DEGZ--clamp (- maxDist full) 0.0 maxDist)))
        )
      )
    )
  )

  (list d1 d2)
)

(defun DEGZ--closest-on-seg (a b p / ax ay bx by px py abx aby apx apy den tt cx cy dx dy)
  (setq a (DEGZ--pt2d a) b (DEGZ--pt2d b) p (DEGZ--pt2d p))
  (setq ax (car a) ay (cadr a))
  (setq bx (car b) by (cadr b))
  (setq px (car p) py (cadr p))
  (setq abx (- bx ax) aby (- by ay))
  (setq apx (- px ax) apy (- py ay))
  (setq den (+ (* abx abx) (* aby aby)))
  (if (< den 1e-12)
    (list a (+ (* apx apx) (* apy apy)))
    (progn
      (setq tt (/ (+ (* apx abx) (* apy aby)) den))
      (setq tt (DEGZ--clamp tt 0.0 1.0))
      (setq cx (+ ax (* tt abx)))
      (setq cy (+ ay (* tt aby)))
      (setq dx (- px cx))
      (setq dy (- py cy))
      (list (list cx cy) (+ (* dx dx) (* dy dy)))
    )
  )
)

(defun DEGZ--poly-closest-seg-index (pts p closed70 / n lim i a b res d2 bestI bestD)
  (setq pts (mapcar 'DEGZ--pt2d pts))
  (setq p (DEGZ--pt2d p))
  (setq n (length pts))
  (if (< n 2)
    0
    (progn
      (setq lim (if (/= (logand closed70 1) 0) n (1- n)))
      (setq i 0 bestI 0 bestD 1e99)
      (while (< i lim)
        (setq a (nth i pts))
        (setq b (nth (if (= i (1- n)) 0 (1+ i)) pts))
        (setq res (DEGZ--closest-on-seg a b p))
        (setq d2 (cadr res))
        (if (< d2 bestD)
          (progn (setq bestD d2) (setq bestI i))
        )
        (setq i (1+ i))
      )
      bestI
    )
  )
)

(defun DEGZ--poly-closest-on-seg (pts segIdx p closed70 / n a b res)
  (setq pts (mapcar 'DEGZ--pt2d pts))
  (setq p (DEGZ--pt2d p))
  (setq n (length pts))
  (if (< n 2)
    p
    (progn
      (setq a (nth segIdx pts))
      (setq b (nth (if (= segIdx (1- n)) 0 (1+ segIdx)) pts))
      (setq res (DEGZ--closest-on-seg a b p))
      (car res)
    )
  )
)

(defun DEGZ--cpE-side (crv cp join rx ry / e d tot pPlus pMin v1x v1y v2x v2y s1 s2 rPlus rMin)
  (setq e (DEGZ--ename crv))
  (setq cp (DEGZ--pt2d-safe cp nil))
  (if (or (not e) (not cp))
    cp
    (progn
      (setq d   (deg-safe-dist-at-point e cp))
      (setq tot (DEGZ--curve-total e))
      (setq rPlus (vl-catch-all-apply 'vlax-curve-getPointAtDist (list e (min tot (+ d join)))))
      (setq rMin  (vl-catch-all-apply 'vlax-curve-getPointAtDist (list e (max 0.0 (- d join)))))
      (setq pPlus (if (vl-catch-all-error-p rPlus) cp (DEGZ--pt2d-safe rPlus cp)))
      (setq pMin  (if (vl-catch-all-error-p rMin)  cp (DEGZ--pt2d-safe rMin  cp)))
      (if (and pPlus pMin)
        (progn
          (setq v1x (- (car pPlus) (car cp)))
          (setq v1y (- (cadr pPlus) (cadr cp)))
          (setq v2x (- (car pMin) (car cp)))
          (setq v2y (- (cadr pMin) (cadr cp)))
          (setq s1 (+ (* v1x rx) (* v1y ry)))
          (setq s2 (+ (* v2x rx) (* v2y ry)))
          (if (>= s1 s2) pPlus pMin)
        )
        cp
      )
    )
  )
)

(defun DEGZ--cpE-side-flag (crv cp join choosePlus / e d tot pPlus pMin rPlus rMin)
  (setq e (DEGZ--ename crv))
  (setq cp (DEGZ--pt2d-safe cp nil))
  (if (or (not e) (not cp))
    cp
    (progn
      (setq d   (deg-safe-dist-at-point e cp))
      (setq tot (DEGZ--curve-total e))
      (setq rPlus (vl-catch-all-apply 'vlax-curve-getPointAtDist (list e (min tot (+ d join)))))
      (setq rMin  (vl-catch-all-apply 'vlax-curve-getPointAtDist (list e (max 0.0 (- d join)))))
      (setq pPlus (if (vl-catch-all-error-p rPlus) cp (DEGZ--pt2d-safe rPlus cp)))
      (setq pMin  (if (vl-catch-all-error-p rMin)  cp (DEGZ--pt2d-safe rMin  cp)))
      (if choosePlus pPlus pMin)
    )
  )
)

(defun DEGZ--shorten-toward-cp (crv cp cpE short / e dcp dE tot dNew res)
  (setq e (DEGZ--ename crv))
  (setq cp  (DEGZ--pt2d-safe cp nil))
  (setq cpE (DEGZ--pt2d-safe cpE cp))
  (if (or (not e) (not cp) (not cpE))
    cpE
    (progn
      (setq dcp (deg-safe-dist-at-point e cp))
      (setq dE  (deg-safe-dist-at-point e cpE))
      (setq tot (DEGZ--curve-total e))
      (if (>= dE dcp)
        (setq dNew (max dcp (- dE short)))
        (setq dNew (min dcp (+ dE short)))
      )
      (setq res (vl-catch-all-apply 'vlax-curve-getPointAtDist (list e (DEGZ--clamp dNew 0.0 tot))))
      (if (vl-catch-all-error-p res)
        cpE
        (DEGZ--pt2d-safe res cpE)
      )
    )
  )
)

(defun DEGZ--right-angle3-p (a b c / pa pb pc ux uy vx vy lenU lenV dot tol)
  (setq pa (DEGZ--pt2d-safe a nil))
  (setq pb (DEGZ--pt2d-safe b nil))
  (setq pc (DEGZ--pt2d-safe c nil))
  (if (and pa pb pc)
    (progn
      (setq ux (- (car pa) (car pb)))
      (setq uy (- (cadr pa) (cadr pb)))
      (setq vx (- (car pc) (car pb)))
      (setq vy (- (cadr pc) (cadr pb)))
      (setq lenU (sqrt (+ (* ux ux) (* uy uy))))
      (setq lenV (sqrt (+ (* vx vx) (* vy vy))))
      (setq dot (+ (* ux vx) (* uy vy)))
      (setq tol (* 1e-6 (max 1.0 (* lenU lenV))))
      (and (> lenU 1e-8)
           (> lenV 1e-8)
           (<= (abs dot) tol))
    )
    nil
  )
)

(defun DEGZ--snap-close-double-turns (pts limit / src out clean snapped a b c d newB newC leftDist rightDist chooseLeft p tol)
  ;; A-B-C-D icinde B ve C yakin iki 90 derece koseyse, kisa B-C
  ;; donusunu A veya D dis komsusundan daha yakin olanin hizasina tasi.
  (setq src (mapcar 'DEGZ--pt2d pts))
  (setq out '())
  (setq tol (* 1e-6 (max 1.0 limit)))
  (while src
    (setq snapped nil)
    (if (>= (length src) 4)
      (progn
        (setq a (car src))
        (setq b (cadr src))
        (setq c (caddr src))
        (setq d (cadddr src))
        (if (and (<= (DEGZ--safe-distance b c) (+ limit tol))
                 (DEGZ--right-angle3-p a b c)
                 (DEGZ--right-angle3-p b c d))
          (progn
            ;; Her 90 derece kosenin dis komsusuna olan mesafesine bak.
            ;; A-B daha kisaysa A hizzasi, C-D daha kisaysa D hizzasi kazanir.
            (setq leftDist  (DEGZ--safe-distance a b))
            (setq rightDist (DEGZ--safe-distance c d))
            (setq chooseLeft
              (cond
                ((< leftDist (- rightDist tol)) T)
                ((< rightDist (- leftDist tol)) nil)
                ;; Esitlikte vertex sirasi degisse de ayni fiziksel nokta secilsin.
                ((< (car a) (car d)) T)
                ((> (car a) (car d)) nil)
                ((<= (cadr a) (cadr d)) T)
                (T nil)
              )
            )
            (if chooseLeft
              (progn
                ;; B, A ile cakisacagi icin sifir boylu parcayi ekleme.
                (setq newC
                  (list (+ (car a) (- (car c) (car b)))
                        (+ (cadr a) (- (cadr c) (cadr b)))))
                (setq out (append out (list a newC)))
              )
              (progn
                ;; C, D ile cakisacak; kisa parcayi D tarafina tasi.
                (setq newB
                  (list (- (car d) (- (car c) (car b)))
                        (- (cadr d) (- (cadr c) (cadr b)))))
                (setq out (append out (list a newB)))
              )
            )
            (setq src (cdddr src))
            (setq snapped T)
          )
        )
      )
    )
    (if (not snapped)
      (progn
        (setq out (append out (list (car src))))
        (setq src (cdr src))
      )
    )
  )

  ;; Tasima sonrasinda ayni konuma gelen ardisik noktalari tek noktaya indir.
  (setq clean '())
  (foreach p out
    (if (or (null clean)
            (> (DEGZ--safe-distance p (car clean)) 1e-7))
      (setq clean (cons p clean))
    )
  )
  (reverse clean)
)
(defun DEGZ--snap-close-double-turn-entity (crv limit / e pts origPts newPts props flags closed newEnt changed pass maxPass)
  ;; DZ bittikten sonra, uygun yakin cift dirsek kalmayana kadar final noktalarini tara.
  (setq e (DEGZ--ename crv))
  (if (or (not e) (not (numberp limit)) (<= limit 0.0))
    e
    (progn
      (setq pts (DEGZ--get-lwpts e))
      (setq origPts pts)
      (setq newPts pts)
      (setq changed T)
      (setq pass 0)
      ;; Her duzeltme nokta sayisini azalttigi icin baslangic nokta sayisi kesin sinirdir.
      (setq maxPass (max 1 (length pts)))
      (while (and changed (< pass maxPass))
        (setq pts newPts)
        (setq newPts (DEGZ--snap-close-double-turns pts limit))
        (setq changed (not (equal pts newPts 1e-8)))
        (setq pass (1+ pass))
      )
      (if (or (< (length newPts) 2) (equal origPts newPts 1e-8))
        e
        (progn
          (setq props (DEGZ--safe-props e))
          (setq flags (cdr (assoc 70 (entget e))))
          (if (not (numberp flags)) (setq flags 0))
          (setq closed (if (/= (logand flags 1) 0) 1 0))
          (entdel e)
          (setq newEnt (DEGZ--entmakex-lwpoly newPts props closed))
          (if newEnt
            newEnt
            (progn
              (entdel e)
              e
            )
          )
        )
      )
    )
  )
)
(defun DEGZ--actual-mouth (e a b route / firstPt lastPt span dx dy tol pa pb)
  ;; Only relocate mouths along the same straight baseline, never across a bend.
  (if (and route (cdr route) (> (setq span (distance a b)) 1e-9))
    (progn
      (setq firstPt (DEGZ--pt2d (car route)) lastPt (DEGZ--pt2d (last route))
            dx (/ (- (car b) (car a)) span)
            dy (/ (- (cadr b) (cadr a)) span) tol 1e-6)
      (if (and (> (distance firstPt lastPt) tol)
               (< (abs (- (* (- (car firstPt) (car a)) dy)
                          (* (- (cadr firstPt) (cadr a)) dx))) tol)
               (< (abs (- (* (- (car lastPt) (car a)) dy)
                          (* (- (cadr lastPt) (cadr a)) dx))) tol))
        (progn
          (setq pa (vl-catch-all-apply 'vlax-curve-getParamAtPoint
                     (list e (DEGZ--pt3d firstPt)))
                pb (vl-catch-all-apply 'vlax-curve-getParamAtPoint
                     (list e (DEGZ--pt3d lastPt))))
          (if (and (numberp pa) (numberp pb)
                   (equal (abs (- (vlax-curve-getDistAtParam e pa)
                                  (vlax-curve-getDistAtParam e pb)))
                          (distance firstPt lastPt) tol))
            (list firstPt lastPt pa pb)))))))

(defun DEGZ--insert-detour (crv attachA attachB midPts / e pts props pA pB tmp sIdx eIdx head tail k newPts firstPt lastPt keepScore revScore midNorm p routePts omitStart actualMouth)
  (setq e     (DEGZ--ename crv))
  (setq pts   (DEGZ--get-lwpts e))
  (setq props (DEGZ--safe-props e))

  (setq attachA (deg-safe-closest-point e attachA))
  (setq attachB (deg-safe-closest-point e attachB))

  (setq pA (vl-catch-all-apply 'vlax-curve-getParamAtPoint (list e (DEGZ--pt3d attachA))))
  (setq pB (vl-catch-all-apply 'vlax-curve-getParamAtPoint (list e (DEGZ--pt3d attachB))))
  (if (or (vl-catch-all-error-p pA) (vl-catch-all-error-p pB))
    crv
    (progn
      ;; midPts tek nokta ya da karisik liste gelebilir; sadece gercek noktalari kullan.
      (setq midNorm '())
      (cond
        ((null midPts)
          (setq midPts nil)
        )
        ((not (listp midPts))
          (setq midPts nil)
        )
        ((and (numberp (car midPts)) (numberp (cadr midPts)))
          (setq midPts (list (DEGZ--pt2d midPts)))
        )
        (T
          (foreach p midPts
            (if (and (listp p) (numberp (car p)) (numberp (cadr p)))
              (setq midNorm (append midNorm (list (DEGZ--pt2d p))))
            )
          )
          (setq midPts midNorm)
        )
      )

      (setq actualMouth (DEGZ--actual-mouth e attachA attachB midPts))
      (if actualMouth
        (setq attachA (car actualMouth) attachB (cadr actualMouth)
              pA (caddr actualMouth) pB (cadddr actualMouth)))
      ;; Polyline cizim yonu ters olsa bile agiz eslesmesi yakinliga gore kalsin.
      (if (and midPts (cdr midPts)
               (listp attachA) (numberp (car attachA)) (numberp (cadr attachA))
               (listp attachB) (numberp (car attachB)) (numberp (cadr attachB)))
        (progn
          (setq firstPt (DEGZ--pt2d (car midPts)))
          (setq lastPt  (DEGZ--pt2d (last midPts)))
          (setq keepScore (+ (DEGZ--safe-distance (DEGZ--pt2d attachA) firstPt) (DEGZ--safe-distance (DEGZ--pt2d attachB) lastPt)))
          (setq revScore  (+ (DEGZ--safe-distance (DEGZ--pt2d attachA) lastPt)  (DEGZ--safe-distance (DEGZ--pt2d attachB) firstPt)))
          (if (< revScore keepScore)
            (setq midPts (reverse midPts))
          )
        )
      )

      ;; Once yakinlik eslesmesi belirlendi. Simdi sadece polyline yeniden kurma
      ;; sirasi icin parametreleri sirala; eslesmis yolun tamamini birlikte cevir.
      (if (> pA pB)
        (progn
          (setq tmp attachA attachA attachB attachB tmp)
          (setq tmp pA pA pB pB tmp)
          (if midPts (setq midPts (reverse midPts)))
        )
      )

      (setq sIdx (fix pA))
      (setq eIdx (fix pB))

      (setq head '() k 0)
      (while (<= k sIdx)
        (setq head (append head (list (nth k pts))))
        (setq k (1+ k))
      )
      (setq head (DEGZ--ensure-last head attachA))

      (setq tail '() k (1+ eIdx))
      (while (< k (length pts))
        (setq tail (append tail (list (nth k pts))))
        (setq k (1+ k))
      )

      (setq routePts
        (append (list attachA) (mapcar 'DEGZ--pt2d midPts) (list attachB))
      )
      (setq routePts (DEGZ--trim-route-mouth-backtracks routePts))
      (DEGZ--dbg-route "FINAL" routePts)

      ;; Baslangic agzi: onceki ana hat noktasi - attachA - ilk rota noktasi.
      (setq omitStart nil)
      (if (and (>= (length head) 2)
               (>= (length routePts) 2)
               (DEGZ--mouth-redundant-p
                 (nth (- (length head) 2) head)
                 (car routePts)
                 (cadr routePts)))
        (progn
          (setq head (DEGZ--drop-last head))
          (setq routePts (cdr routePts))
          (setq omitStart T)
        )
      )

      ;; Bitis agzi: son rota noktasi - attachB - sonraki ana hat noktasi.
      (if (and tail
               (>= (length routePts) 2)
               (DEGZ--mouth-redundant-p
                 (nth (- (length routePts) 2) routePts)
                 (last routePts)
                 (car tail)))
        (setq routePts (DEGZ--drop-last routePts))
      )

      (if omitStart
        (setq newPts (append head routePts tail))
        (if routePts
          (setq newPts (append head (cdr routePts) tail))
          (setq newPts (append head tail))
        )
      )


      (entdel e)
      (DEGZ--entmakex-lwpoly newPts props 0)
    )
  )
)

(defun DEGZ--block-effective-name (en / vla nm ed)
  (setq en (DEGZ--ename en))
  (if (not en)
    nil
    (progn
      (setq ed (entget en))
      (setq nm (cdr (assoc 2 ed)))
      (if (and nm (= (substr nm 1 1) "*"))
        (progn
          (setq vla (vlax-ename->vla-object en))
          (if (vlax-property-available-p vla 'EffectiveName)
            (setq nm (vla-get-EffectiveName vla))
          )
        )
      )
      nm
    )
  )
)

(defun DEGZ--skip-block-p (blk / nm nmU)
  (setq nm  (DEGZ--block-effective-name blk))
  (setq nmU (strcase (if nm nm "")))
  (if (or (vl-string-search "FLASOR" nmU)
          (vl-string-search "FLAR"   nmU))
    T
    nil
  )
)

(defun DEGZ--block-wcs-center (blk / ip obj mn mx r mnL mxL)
  ;; Blok rotasyonundan bagimsiz taraf karari icin WCS bbox merkezini kullan.
  ;; Bbox okunamazsa eski INSERT/base noktasina duser.
  (setq ip (if (and blk (entget blk))
             (DEGZ--pt2d (cdr (assoc 10 (entget blk))))
             '(0.0 0.0)
           )
  )
  (setq obj (if (and blk (entget blk))
              (vl-catch-all-apply 'vlax-ename->vla-object (list blk))
              nil
            )
  )
  (if (or (null obj) (vl-catch-all-error-p obj))
    ip
    (progn
      (setq r (vl-catch-all-apply 'vla-getBoundingBox (list obj 'mn 'mx)))
      (if (or (vl-catch-all-error-p r) (null mn) (null mx))
        ip
        (progn
          (setq mnL (degw-_v2l mn))
          (setq mxL (degw-_v2l mx))
          (if (and (listp mnL) (listp mxL))
            (list (/ (+ (car mnL) (car mxL)) 2.0)
                  (/ (+ (cadr mnL) (cadr mxL)) 2.0))
            ip
          )
        )
      )
    )
  )
)
(defun DEGZ--floor (x)
  (if (>= x 0.0) (fix x) (1- (fix x)))
)

(defun DEGZ--cellkey (p cell / cx cy)
  (setq p (DEGZ--pt2d p))
  (setq cx (DEGZ--floor (/ (car p) cell)))
  (setq cy (DEGZ--floor (/ (cadr p) cell)))
  (list cx cy)
)

(defun DEGZ--cells-put (cells key val / rec)
  (if (setq rec (assoc key cells))
    (subst (cons key (cons val (cdr rec))) rec cells)
    (cons (list key val) cells)
  )
)

(defun DEGZ--uf-init (parents x)
  (if (assoc x parents) parents (cons (cons x x) parents))
)

(defun DEGZ--uf-find (parents x / p)
  (setq p (cdr (assoc x parents)))
  (if (null p) x
    (progn
      (while (and p (not (equal p x)))
        (setq x p)
        (setq p (cdr (assoc x parents)))
      )
      x
    )
  )
)

(defun DEGZ--uf-union (parents a b / ra rb rec)
  (setq ra (DEGZ--uf-find parents a))
  (setq rb (DEGZ--uf-find parents b))
  (if (not (equal ra rb))
    (progn
      (setq rec (assoc rb parents))
      (if rec
        (setq parents (subst (cons rb ra) rec parents))
        (setq parents (cons (cons rb ra) parents))
      )
    )
  )
  parents
)

(defun DEGZ--groups-build (parents data / groups blk rep r rec)
  (setq groups '())
  (foreach rec data
    (setq blk (car rec))
    (setq rep (DEGZ--uf-find parents blk))
    (if (setq r (assoc rep groups))
      (setq groups (subst (cons rep (cons rec (cdr r))) r groups))
      (setq groups (cons (list rep rec) groups))
    )
  )
  groups
)

(defun DEGZ--choosePlus-main (mainCrv ip cp join / vvx vvy uu dx dy rx ry rperp cpE d tot pPlus)
  (setq ip (DEGZ--pt2d ip))
  (setq cp (DEGZ--pt2d cp))

  (setq vvx (- (car ip) (car cp)))
  (setq vvy (- (cadr ip) (cadr cp)))
  (setq uu (DEGZ--unit vvx vvy))
  (setq dx (car uu) dy (cadr uu))

  (setq rperp (DEGZ--perp-axis-from-curve-safe mainCrv cp))
              (setq rx (car rperp))
              (setq ry (cadr rperp))

  (setq cpE (DEGZ--cpE-side mainCrv cp join rx ry))

  (setq d   (deg-safe-dist-at-point mainCrv cp))
  (setq tot (DEGZ--curve-total mainCrv))
  (setq pPlus (DEGZ--pt2d (vlax-curve-getPointAtDist (DEGZ--ename mainCrv) (min tot (+ d join)))))

  (if (<= (distance cpE pPlus) 1e-6) T nil)
)

(defun DEGZ--point-toward (a b dist / a2 b2 vx vy uu)
  (setq a2 (DEGZ--pt2d a))
  (setq b2 (DEGZ--pt2d b))
  (setq vx (- (car b2) (car a2)))
  (setq vy (- (cadr b2) (cadr a2)))
  (setq uu (DEGZ--unit vx vy))
  (if (> (caddr uu) 1e-12)
    (list (+ (car a2) (* (car uu) dist)) (+ (cadr a2) (* (cadr uu) dist)))
    a2
  )
)

(defun DEGZ--calc-L-corner (S B uPerp / S2 B2 c1 c2 d1 d2)
  ;; ORTHO KÃ–ÅE: BaÄŸlantÄ±lar sadece 0/90/180/270 olacak ÅŸekilde,
  ;; S -> corner -> B iki eksenli (yatay/dikey) kÄ±rÄ±lÄ±m Ã¼retir.
  (setq S2 (DEGZ--pt2d S))
  (setq B2 (DEGZ--pt2d B))

  ;; Ä°ki olasÄ± L kÃ¶ÅŸe
  (setq c1 (list (car S2) (cadr B2))) ; Ã¶nce dikey, sonra yatay
  (setq c2 (list (car B2) (cadr S2))) ; Ã¶nce yatay, sonra dikey

  ;; S'den daha kÄ±sa ilk bacaÄŸÄ± seÃ§
  (setq d1 (distance S2 c1))
  (setq d2 (distance S2 c2))
  (if (<= d1 d2) c1 c2)
)


(defun DEGZ--ortho-first-axis (ip cp)

(defun DEGZ--perp-axis-from-curve (crv pt / prm deriv tx ty)
  ;; ORTHO iÃ§in ana hattÄ±n tangent yÃ¶nÃ¼ne gÃ¶re (x/y) eksen-perp dÃ¶ndÃ¼rÃ¼r.
  ;; dönü?: (rx ry) birim vektÃ¶r (mutlak eksen), iÅŸaret sideFact ile verilir.
  (setq prm (vlax-curve-getParamAtPoint (DEGZ--ename crv) (DEGZ--pt3d pt)))
  (setq deriv (vlax-curve-getFirstDeriv (DEGZ--ename crv) prm))
  (setq tx (car deriv) ty (cadr deriv))
  (if (> (abs tx) (abs ty))
    (list 0.0 1.0)   ;; tangent yatay => perp dikey
    (list 1.0 0.0)   ;; tangent dikey => perp yatay
  )
)

  ;; T => once X (hfirst), NIL => once Y (vfirst)
  (< (abs (- (car (DEGZ--pt2d ip)) (car (DEGZ--pt2d cp))))
     (abs (- (cadr (DEGZ--pt2d ip)) (cadr (DEGZ--pt2d cp)))))
)

(defun DEGZ--direct-offset-end (base tip mouthA mouthB gap / span tx ty projection nx ny toward lateral setback)
  ;; The final legs are normal to the mouth, not necessarily to the block approach.
  ;; Both the rail gap and the setback toward the main line equal the offset.
  (setq span (distance mouthA mouthB))
  (if (or (<= span 1e-9) (<= gap 0.0))
    tip
    (progn
      (setq tx (/ (- (car mouthB) (car mouthA)) span)
            ty (/ (- (cadr mouthB) (cadr mouthA)) span)
            projection (+ (* (- (car tip) (car base)) tx)
                          (* (- (cadr tip) (cadr base)) ty))
            nx (- ty) ny tx
            toward (+ (* (- (car mouthA) (car base)) nx)
                      (* (- (cadr mouthA) (cadr base)) ny))
            lateral (if (< projection 0.0) (- gap) gap)
            setback (if (< toward 0.0) (- gap) gap))
      (list (+ (car base) (* lateral tx) (* setback nx))
            (+ (cadr base) (* lateral ty) (* setback ny))))))

(defun DEGZ--calc-L-corner (S B uPerp / S2 B2 up ux uy utx uty vx vy projT)
  ;; Vektorel kose:
  ;; S -> corner ana hat dogrultusunda,
  ;; corner -> B ise uPerp dogrultusunda gider.
  (setq S2 (DEGZ--pt2d S))
  (setq B2 (DEGZ--pt2d B))
  (setq up (DEGZ--pt2d uPerp))
  (setq ux (car up))
  (setq uy (cadr up))

  (if (< (+ (* ux ux) (* uy uy)) 1e-12)
    S2
    (progn
      (setq utx (- uy))
      (setq uty ux)
      (setq vx (- (car B2) (car S2)))
      (setq vy (- (cadr B2) (cadr S2)))
      (setq projT (+ (* vx utx) (* vy uty)))
      (list (+ (car S2) (* utx projT))
            (+ (cadr S2) (* uty projT)))
    )
  )
)
(if (not (boundp '*DEG-DDDZ-CIKINTI-DEBUG*))
  (setq *DEG-DDDZ-CIKINTI-DEBUG* nil)
)

(defun DEGZ--dbg-pt (p)
  (if (and (listp p) (numberp (car p)) (numberp (cadr p)))
    (strcat "(" (rtos (car p) 2 2) "," (rtos (cadr p) 2 2) ")")
    "nil"
  )
)

(setq *DEG-DDDZ-CIKINTI-DEBUG* nil)

(defun DEGZ--dbg-route (tag pts / out p)
  (if (and (boundp '*DEG-DDDZ-CIKINTI-DEBUG*) *DEG-DDDZ-CIKINTI-DEBUG*)
    (progn
      (setq out (strcat "\nDDZ ROUTE " tag ":"))
      (foreach p pts
        (setq out (strcat out " " (DEGZ--dbg-pt p)))
      )
      (princ out)
    )
  )
  pts
)

(defun c:DDZDEBUG ()
  (setq *DEG-DDDZ-CIKINTI-DEBUG*
    (not (and (boundp '*DEG-DDDZ-CIKINTI-DEBUG*) *DEG-DDDZ-CIKINTI-DEBUG*)))
  (princ
    (strcat "\nDD/DZ rota debug: "
      (if *DEG-DDDZ-CIKINTI-DEBUG* "ACIK" "KAPALI")))
  (princ)
)
(defun DEGZ--dbg-cikinti (tag blockSide remote isAnchor forceMain ip cp / branch)
  (if (and (boundp '*DEG-DDDZ-CIKINTI-DEBUG*) *DEG-DDDZ-CIKINTI-DEBUG*)
    (progn
      (setq branch (if (and remote (not isAnchor)) "REMOTE" "DIRECT"))
      (princ
        (strcat
          "\n" tag " debug: side=" (vl-princ-to-string blockSide)
          " branch=" branch
          " remote=" (vl-princ-to-string remote)
          " anchor=" (vl-princ-to-string isAnchor)
          " forceMain=" (vl-princ-to-string forceMain)
          " ip=" (DEGZ--dbg-pt ip)
          " cp=" (DEGZ--dbg-pt cp)
        )
      )
    )
  )
)
(defun DEGZ--side-from-vector (vx vy)
  (cond
    ((>= (abs vx) (abs vy)) (if (< vx 0.0) 'LEFT 'RIGHT))
    ((< vy 0.0) 'BOTTOM)
    (T 'TOP)
  )
)

(defun DEGZ--pair-main-block-no-cross (blockSide pA pB iA iB / pa pb ia ib keepScore crossScore)
  ;; Dirsekli cizimde de polyline yonunu kullanma.
  ;; Iki olasi eslesmeden toplam baglanti mesafesi kisa olani sec.
  (setq pa (DEGZ--pt2d-safe pA nil))
  (setq pb (DEGZ--pt2d-safe pB nil))
  (setq ia (DEGZ--pt2d-safe iA nil))
  (setq ib (DEGZ--pt2d-safe iB nil))
  (if (and pa pb ia ib)
    (progn
      (setq keepScore
        (+ (DEGZ--safe-distance pa ia)
           (DEGZ--safe-distance pb ib))
      )
      (setq crossScore
        (+ (DEGZ--safe-distance pa ib)
           (DEGZ--safe-distance pb ia))
      )
      (if (< crossScore keepScore)
        (list pa pb ib ia)
        (list pa pb ia ib)
      )
    )
    (list pA pB iA iB)
  )
)
(defun DEGZ--side-from-connect-to-block (cp ip / c p dx dy)
  ;; Ana hatta baglanilacak noktadan block base/baglanti noktasina bak.
  ;; block sagdaysa LEFT, soldaysa RIGHT, ustteyse BOTTOM, alttaysa TOP.
  (setq c (DEGZ--pt2d cp))
  (setq p (DEGZ--pt2d ip))
  (setq dx (- (car p) (car c)))
  (setq dy (- (cadr p) (cadr c)))
  (cond
    ((>= (abs dx) (abs dy)) (if (>= dx 0.0) 'LEFT 'RIGHT))
    ((>= dy 0.0) 'BOTTOM)
    (T 'TOP)
  )
)
(defun DEGZ--side-from-group-alignment (cp ipAvg recs / side c p minX maxX minY maxY r rp spreadX spreadY)
  ;; Koseye yakin bir blok grubu cp->ip vektoruyle capraz gorunebilir.
  ;; Acikca yatay/dikey dizilmis gruplarda gelis yonunu grup ekseninin
  ;; dikinden bul; boylece ayna cizimlerde RIGHT/BOTTOM karari degismez.
  (setq side (DEGZ--side-from-connect-to-block cp ipAvg))
  (if (and recs (> (length recs) 1))
    (progn
      (foreach r recs
        (setq rp (DEGZ--pt2d-safe (cadr r) nil))
        (if rp
          (progn
            (if (or (null minX) (< (car rp) minX)) (setq minX (car rp)))
            (if (or (null maxX) (> (car rp) maxX)) (setq maxX (car rp)))
            (if (or (null minY) (< (cadr rp) minY)) (setq minY (cadr rp)))
            (if (or (null maxY) (> (cadr rp) maxY)) (setq maxY (cadr rp)))
          )
        )
      )
      (if (and minX maxX minY maxY)
        (progn
          (setq spreadX (- maxX minX)
                spreadY (- maxY minY)
                c (DEGZ--pt2d cp)
                p (DEGZ--pt2d ipAvg))
          (cond
            ((> spreadX (* 1.5 (max spreadY 1e-6)))
              (setq side (if (>= (cadr p) (cadr c)) 'BOTTOM 'TOP)))
            ((> spreadY (* 1.5 (max spreadX 1e-6)))
              (setq side (if (>= (car p) (car c)) 'LEFT 'RIGHT)))
          )
        )
      )
    )
  )
  side
)
(defun DEGZ--group-approach-unit (cp ipAvg recs / c p minX maxX minY maxY r rp spreadX spreadY)
  ;; Acikca yatay dizilen gruba dikey, dikey dizilen gruba yatay yaklas.
  ;; Koseye olan capraz en-yakin vektorunun blok bacagini yamultmasini engeller.
  (if (and recs (> (length recs) 1))
    (progn
      (foreach r recs
        (setq rp (DEGZ--pt2d-safe (cadr r) nil))
        (if rp
          (progn
            (if (or (null minX) (< (car rp) minX)) (setq minX (car rp)))
            (if (or (null maxX) (> (car rp) maxX)) (setq maxX (car rp)))
            (if (or (null minY) (< (cadr rp) minY)) (setq minY (cadr rp)))
            (if (or (null maxY) (> (cadr rp) maxY)) (setq maxY (cadr rp)))
          )
        )
      )
      (if (and minX maxX minY maxY)
        (progn
          (setq spreadX (- maxX minX)
                spreadY (- maxY minY)
                c (DEGZ--pt2d cp)
                p (DEGZ--pt2d ipAvg))
          (cond
            ((> spreadX (* 1.5 (max spreadY 1e-6)))
              (list 0.0 (if (>= (cadr p) (cadr c)) 1.0 -1.0)))
            ((> spreadY (* 1.5 (max spreadX 1e-6)))
              (list (if (>= (car p) (car c)) 1.0 -1.0) 0.0))
            (T nil)
          )
        )
      )
    )
  )
)
(defun DEGZ--normal-group-no-cross-side (cp ipAvg recs fallback / c p minX maxX minY maxY r rp spreadX spreadY eps)
  ;; Yalniz normal baglantida kullanilir. Yakin bloklarin dizilim eksenine
  ;; paralel yaklasmak bir bloktan digerinin icinden gecirir. Bu nedenle
  ;; yatay gruba ust/alt, dikey gruba sol/sag ortak taraftan yaklas.
  (setq c (DEGZ--pt2d-safe cp nil)
        p (DEGZ--pt2d-safe ipAvg nil)
        eps 1e-6)
  (if (and c p recs (> (length recs) 1))
    (progn
      (foreach r recs
        (setq rp (DEGZ--pt2d-safe (cadr r) nil))
        (if rp
          (progn
            (if (or (null minX) (< (car rp) minX)) (setq minX (car rp)))
            (if (or (null maxX) (> (car rp) maxX)) (setq maxX (car rp)))
            (if (or (null minY) (< (cadr rp) minY)) (setq minY (cadr rp)))
            (if (or (null maxY) (> (cadr rp) maxY)) (setq maxY (cadr rp))))))
      (if (and minX maxX minY maxY)
        (progn
          (setq spreadX (- maxX minX)
                spreadY (- maxY minY))
          (if (>= spreadX spreadY)
            (cond
              ((< (cadr c) (- (cadr p) eps)) 'BOTTOM)
              ((> (cadr c) (+ (cadr p) eps)) 'TOP)
              (T 'BOTTOM))
            (cond
              ((< (car c) (- (car p) eps)) 'LEFT)
              ((> (car c) (+ (car p) eps)) 'RIGHT)
              (T 'LEFT))))
        fallback))
    fallback)
)
(defun DEGZ--approach-unit-for-side (side)
  (cond
    ((eq side 'BOTTOM) '(0.0 1.0))
    ((eq side 'TOP)    '(0.0 -1.0))
    ((eq side 'LEFT)   '(1.0 0.0))
    ((eq side 'RIGHT)  '(-1.0 0.0))
    (T nil))
)
(defun DEGZ--corner-mouth-pair-by-approach (crv cp groupDir span / e center d tot dMin dPlus rMin rPlus pMin pPlus valMin valPlus candidate candidateD v1 v2 l1 l2 dotAbs)
  ;; Kosenin iki komsu segmentinden grup yaklasimina dik olani sec.
  ;; Boylece agiz yatay ve dikey kollar arasinda bolunmez.
  (setq e (DEGZ--ename crv))
  (if e
    (setq center (DEGZ--pt2d-safe (deg-safe-closest-point e cp) nil)))
  (if (and e center groupDir (> span 1e-6))
    (progn
      (setq d (deg-safe-dist-at-point e center)
            tot (DEGZ--curve-total e)
            dMin (max 0.0 (- d span))
            dPlus (min tot (+ d span))
            rMin (vl-catch-all-apply 'vlax-curve-getPointAtDist (list e dMin))
            rPlus (vl-catch-all-apply 'vlax-curve-getPointAtDist (list e dPlus))
            pMin (if (vl-catch-all-error-p rMin) nil (DEGZ--pt2d-safe rMin nil))
            pPlus (if (vl-catch-all-error-p rPlus) nil (DEGZ--pt2d-safe rPlus nil)))
      (if (> (abs (cadr groupDir)) (abs (car groupDir)))
        (setq valMin (if pMin (abs (- (car pMin) (car center))) -1.0)
              valPlus (if pPlus (abs (- (car pPlus) (car center))) -1.0))
        (setq valMin (if pMin (abs (- (cadr pMin) (cadr center))) -1.0)
              valPlus (if pPlus (abs (- (cadr pPlus) (cadr center))) -1.0)))
      (if (and pMin pPlus)
        (progn
          (setq v1 (list (- (car pMin) (car center)) (- (cadr pMin) (cadr center)))
                v2 (list (- (car pPlus) (car center)) (- (cadr pPlus) (cadr center)))
                l1 (distance '(0.0 0.0) v1)
                l2 (distance '(0.0 0.0) v2))
          (if (and (> l1 (* span 0.5)) (> l2 (* span 0.5)))
            (setq dotAbs
              (abs (/ (+ (* (car v1) (car v2)) (* (cadr v1) (cadr v2))) (* l1 l2)))))))
      (if (and dotAbs (< dotAbs 0.25))
        ;; Gercek L kosesi: agzin iki ucu iki komsu kola gelsin.
        (list pMin pPlus)
        (progn
          (if (or (>= valMin 0.0) (>= valPlus 0.0))
            (if (>= valMin valPlus)
              (setq candidate pMin candidateD dMin)
              (setq candidate pPlus candidateD dPlus)))
          (if candidate
            (if (< candidateD d)
              (list candidate center)
              (list center candidate)))))
    )
  )
)
(defun DEGZ--corner-at-block-axis (mouthPt blockPt groupDir)
  ;; Agiz L'nin iki kolundaysa donusu blok tarafinda tut.
  (if (> (abs (cadr groupDir)) (abs (car groupDir)))
    (list (car blockPt) (cadr mouthPt))
    (list (car mouthPt) (cadr blockPt)))
)
(defun DEGZ--block-side-from-connect (blk ip / c p dx dy)
  ;; ip block'un baglanti/base noktasi kabul edilir.
  ;; Bu noktadan block govdesi hangi taraftaysa gelis tarafi onun tersidir:
  ;; govde sagda => LEFT, govde solda => RIGHT, govde ustte => BOTTOM, govde altta => TOP.
  (setq p (DEGZ--pt2d ip))
  (setq c (DEGZ--block-wcs-center blk))
  (setq dx (- (car c) (car p)))
  (setq dy (- (cadr c) (cadr p)))
  (cond
    ((>= (abs dx) (abs dy)) (if (>= dx 0.0) 'LEFT 'RIGHT))
    ((>= dy 0.0) 'BOTTOM)
    (T 'TOP)
  )
)
(defun DEGZ--incoming-block-side (crv cp ip / e cp2 ip2 prm deriv tlen tx ty vx vy)
  ;; Cikinti yonu: once ana hattin o noktada yatay mi dikey mi olduguna bak.
  ;; Ana hat yataysa karar sadece X'e gore verilir:
  ;;   blok baglanti noktasinin sagindaysa LEFT (soldan gelis -> cikinti altta)
  ;;   blok baglanti noktasinin solundaysa RIGHT (sagdan gelis -> cikinti ustte)
  ;; Ana hat dikeyse karar sadece Y'ye gore verilir:
  ;;   blok ustteyse BOTTOM, blok alttaysa TOP.
  (setq e (DEGZ--ename crv))
  (setq cp2 (DEGZ--pt2d cp))
  (setq ip2 (DEGZ--pt2d ip))
  (setq vx (- (car ip2) (car cp2)))
  (setq vy (- (cadr ip2) (cadr cp2)))
  (if e
    (progn
      (setq prm (vl-catch-all-apply 'vlax-curve-getParamAtPoint (list e (DEGZ--pt3d cp2))))
      (if (not (vl-catch-all-error-p prm))
        (progn
          (setq deriv (vlax-curve-getFirstDeriv e prm))
          (setq tlen (distance '(0 0 0) deriv))
          (if (> tlen 1e-9)
            (progn
              (setq tx (/ (car deriv) tlen))
              (setq ty (/ (cadr deriv) tlen))
              (if (>= (abs tx) (abs ty))
                (setq vy 0.0)
                (setq vx 0.0)
              )
            )
          )
        )
      )
    )
  )
  (cond
    ((>= (abs vx) (abs vy)) (if (>= vx 0.0) 'LEFT 'RIGHT))
    ((>= vy 0.0) 'BOTTOM)
    (T 'TOP)
  )
)
(defun DEGZ--oblique-vector-p (vx vy / ax ay)
  ;; Birim yonun iki bileseni de anlamliysa hat WCS eksenlerine paralel degildir.
  (setq ax (abs vx)
        ay (abs vy))
  (and (> ax 1e-4) (> ay 1e-4))
)
(defun DEGZ--local-bend-point (basePt targetPt nx ny tx ty blockSide / b q alen dotT)
  ;; Ofseti koruyan yerel dirsek: tabandan ana hatta paralel, block ucundan
  ;; baglanti koluna paralel gecen iki dogrunun kesisim noktasini verir.
  (setq b (DEGZ--pt2d basePt)
        q (DEGZ--pt2d targetPt)
        alen (sqrt (+ (* tx tx) (* ty ty))))
  (if (or (null b) (null q) (<= alen 1e-12))
    b
    (progn
      (setq tx (/ tx alen)
            ty (/ ty alen)
            dotT (+ (* (- (car q) (car b)) tx)
                    (* (- (cadr q) (cadr b)) ty)))
      (list (+ (car b) (* dotT tx))
            (+ (cadr b) (* dotT ty)))
    )
  )
)
(defun DEGZ--pair-by-local-offset (pA pB iA iB tx ty / pa pb ia ib baseOrder targetOrder)
  ;; 90 derece dirsekte ic/dis ofset sirasini yerel teget ekseninde korur.
  (setq pa (DEGZ--pt2d-safe pA nil)
        pb (DEGZ--pt2d-safe pB nil)
        ia (DEGZ--pt2d-safe iA nil)
        ib (DEGZ--pt2d-safe iB nil))
  (if (and pa pb ia ib)
    (progn
      (setq baseOrder
        (+ (* (- (car pb) (car pa)) tx)
           (* (- (cadr pb) (cadr pa)) ty)))
      (setq targetOrder
        (+ (* (- (car ib) (car ia)) tx)
           (* (- (cadr ib) (cadr ia)) ty)))
      (cond
        ((< (* baseOrder targetOrder) -1e-10)
          (list pa pb ib ia)
        )
        ((> (* baseOrder targetOrder) 1e-10)
          (list pa pb ia ib)
        )
        (T
          ;; Izdusum kararsizsa mevcut yakinlik eslestirmesine geri don.
          (DEGZ--pair-main-block-no-cross nil pa pb ia ib)
        )
      )
    )
    (list pA pB iA iB)
  )
)
(defun DEGZ--APPLY (crv0 ss / crv i blk ip blk2 ip2
               ptsMain propsMain mainTmp mainClosed guideSrc
               joinCand short shift approach
               vvx vvy uu dx dy len rx ry ipRin
               nearLim mainFarLim mergeOff
               cell cells
               parents data
               groups
               forcedReps sideMap segMap groupDirMap groupDir
               anchorMap stemMap  remoteMap mergeMap
               dirMap dirRec udir mdx mdy p1 ipb p1b pJoin stemRec stemA stemB cpSec pStep pStepb
               g rep recs r bestRec bestIp bestD dNow segIdx choosePlus
               procData anchorRec remote
               forceMain isAnchor cpMain cpCur cpE cpEshort
               uTan uPerp corner1 corner2 paramCur distEnds
               pDown pDownRin uDirRemote anchorStemDir
               key cx cy ix iy rec item mergePt isTargetSide
               sX sY sideFact 
               ipAvg pMid paramMid deriv Tlen Tx Ty Lx Ly dotProd dirSign distMid distDown distDownRin maxDist
               pMerge pMergeRin pLeft pRight ipLeft ipRight pMainTop pMainBot ipTop ipBot yTop yBot pTopA pBotA pTopB pBotB pTopDrop pBotDrop scoreA scoreB outsideLeft fromTop sideMode shortIp longIp calcCrv sideBase sideDx sideDy blockSide blockSideMap oblique alignedPair rowGuideActive preRec preSide preTarget)

  (vl-load-com)

  (setq joinCand (DEG:CFG-DDDZ-NUM-OR 'DZ_AGIZ_ARAMA 20.0))
  (if (<= joinCand 0.0)
    (setq joinCand (* 20.0 (DEG:PLAN-UNIT-SCALE))))
  (setq short (DEG:CFG-DDDZ-NUM-OR 'DZ_OFFSET 10.0))
  (if (<= short 0.0)
    (setq short (* 10.0 (DEG:PLAN-UNIT-SCALE))))
  (setq shift short)
  (setq approach short)

  (setq nearLim (DEG:CFG-DDDZ-NUM-OR 'DZ_BLOK_YAKINLIK 100.0))
  (if (<= nearLim 0.0)
    (setq nearLim (* 100.0 (DEG:PLAN-UNIT-SCALE))))
  (setq mainFarLim (DEG:CFG-DDDZ-NUM-OR 'DZ_DIRSEK_DIST 200.0))
  (if (<= mainFarLim 0.0)
    (setq mainFarLim (* 200.0 (DEG:PLAN-UNIT-SCALE))))
  (setq mergeOff (DEG:CFG-DDDZ-NUM-OR 'DZ_DIRSEK_KACIS 50.0))
  (if (<= mergeOff 0.0)
    (setq mergeOff (* 50.0 (DEG:PLAN-UNIT-SCALE))))

  (setq crv0 (DEGZ--ename crv0))

  (if (not (and crv0 (entget crv0)))
    (progn (princ "\nDZ: Gecersiz polyline.") (princ))
    (if (not (and ss (= (type ss) 'PICKSET) (> (sslength ss) 0)))
      (progn (princ "\nDZ: Block secimi yok.") (princ))
      (progn

        ;; Ortak omurgadaki bir sirayi islerken en yakin parcayi tum agdan
        ;; arama. O siraya ait cocuk dal merkezini hesap kilavuzu olarak kullan.
        (setq guideSrc
          (if (and (boundp '*DEGZ_ROW_GUIDE*)
                   *DEGZ_ROW_GUIDE*
                   (entget (DEGZ--ename *DEGZ_ROW_GUIDE*)))
            (DEGZ--ename *DEGZ_ROW_GUIDE*)
            crv0))
        (setq rowGuideActive (not (eq guideSrc crv0)))
        (setq ptsMain   (DEGZ--get-lwpts guideSrc))
        (setq propsMain (DEGZ--safe-props guideSrc))
        (setq mainClosed (cdr (assoc 70 (entget guideSrc))))
        (if (null mainClosed) (setq mainClosed 0))
        (setq mainClosed (if (/= (logand mainClosed 1) 0) 1 0))
        (setq mainTmp   (DEGZ--entmakex-lwpoly ptsMain propsMain mainClosed))

        (setq cell    nearLim)
        (setq cells   '())
        (setq parents '())
        (setq data    '())

        (setq i 0)
        (while (< i (sslength ss))
          (setq blk (ssname ss i))
          (if (not (DEGZ--skip-block-p blk))
            (progn
              (setq ip (DEGZ--pt2d (cdr (assoc 10 (entget blk)))))

              (setq parents (DEGZ--uf-init parents blk))
              (setq data (append data (list (list blk ip))))

              (setq key (DEGZ--cellkey ip cell))
              (setq cx (car key) cy (cadr key))

              (setq ix -1)
              (while (<= ix 1)
                (setq iy -1)
                (while (<= iy 1)
                  (setq rec (assoc (list (+ cx ix) (+ cy iy)) cells))
                  (if rec
                    (foreach item (cdr rec)
                      (setq blk2 (car item))
                      (setq ip2  (cadr item))
                      (if (and blk2 ip2 (<= (distance ip ip2) nearLim))
                        (setq parents (DEGZ--uf-union parents blk blk2))
                      )
                    )
                  )
                  (setq iy (1+ iy))
                )
                (setq ix (1+ ix))
              )

              (setq cells (DEGZ--cells-put cells (list cx cy) (list blk ip)))
            )
          )
          (setq i (1+ i))
        )

        (setq groups (DEGZ--groups-build parents data))

        (setq forcedReps '())
        (setq sideMap    '())
        (setq segMap     '())
        (setq anchorMap  '())
        (setq stemMap    '())
        (setq remoteMap  '())
        (setq mergeMap   '())
        (setq dirMap     '())
        (setq blockSideMap '())
        (setq groupDirMap '())

        (foreach g groups
          (setq rep  (car g))
          (setq recs (cdr g))

          (setq bestRec nil)
          (setq bestD   1e99)
          (foreach r recs
            (setq ip (cadr r))
            (setq cpMain (deg-safe-closest-point mainTmp ip))
            (setq dNow (distance (DEGZ--pt2d ip) (DEGZ--pt2d cpMain)))
            (if (< dNow bestD)
              (progn (setq bestD dNow) (setq bestRec r))
            )
          )
          (if (null bestRec) (setq bestRec (car recs)))
          (setq bestIp (cadr bestRec))
          (setq anchorMap (cons (cons rep bestRec) anchorMap))

          (setq cpMain (deg-safe-closest-point mainTmp bestIp))
          (setq stemMap (cons (cons rep (list (DEGZ--pt2d bestIp) (DEGZ--pt2d cpMain))) stemMap))
          (setq choosePlus (DEGZ--choosePlus-main mainTmp bestIp cpMain joinCand))
          (setq sideMap (cons (cons rep choosePlus) sideMap))
          (setq segIdx (DEGZ--poly-closest-seg-index ptsMain bestIp mainClosed))
          (setq segMap (cons (cons rep segIdx) segMap))

          ;; Cikinti yonu grupta tek karar olsun: tum bloklarin merkezini ana hatta gore oku.
          (setq sX 0.0)
          (setq sY 0.0)
          (setq scoreB 0)
          (foreach r recs
            (setq ip (DEGZ--pt2d (cadr r)))
            (setq sX (+ sX (car ip)))
            (setq sY (+ sY (cadr ip)))
            (setq scoreB (1+ scoreB))
          )
          (if (> scoreB 0)
            (setq ipAvg (list (/ sX scoreB) (/ sY scoreB)))
            (setq ipAvg bestIp)
          )
          (setq cpMain (deg-safe-closest-point mainTmp ipAvg))
          (setq blockSide (DEGZ--side-from-group-alignment cpMain ipAvg recs))
          (setq blockSideMap (cons (cons rep blockSide) blockSideMap))
          (setq groupDirMap
            (cons (cons rep (DEGZ--group-approach-unit cpMain ipAvg recs)) groupDirMap))

          ;; Anchor secimi ana hat acisi degisse de ayni blokta kalsin.
          ;; Egik hatta yerel teget sirasi; yatay/dikey hatta mevcut kural kullanilir.
          (if (> (length recs) 1)
            (progn
              (setq scoreA nil)
              (foreach r recs
                (setq ip (DEGZ--pt2d (cadr r)))
                (setq uTan (DEGZ--canonical-tangent-at mainTmp cpMain))
                (setq scoreB
                  (if (and (> (abs (car uTan)) 1e-4)
                           (> (abs (cadr uTan)) 1e-4))
                    ;; Egik hatta X/Y esigi kullanma; bloklari yerel ana-hat ekseninde sirala.
                    (- (+ (* (car ip) (car uTan))
                          (* (cadr ip) (cadr uTan))))
                    ;; Yatay/dikey mevcut davranisi koru.
                    (cond
                      ((eq blockSide 'LEFT) (- (cadr ip)))
                      ((eq blockSide 'RIGHT) (cadr ip))
                      ((or (eq blockSide 'TOP) (eq blockSide 'BOTTOM)) (- (car ip)))
                      (T 0.0)
                    )
                  )
                )
                (if (or (null scoreA) (< scoreB scoreA))
                  (progn
                    (setq scoreA scoreB)
                    (setq bestRec r)
                  )
                )
              )
              (setq bestIp (cadr bestRec))
              (setq anchorMap (cons (cons rep bestRec) anchorMap))
              (setq cpMain (deg-safe-closest-point mainTmp bestIp))
              (setq stemMap (cons (cons rep (list (DEGZ--pt2d bestIp) (DEGZ--pt2d cpMain))) stemMap))
              (setq choosePlus (DEGZ--choosePlus-main mainTmp bestIp cpMain joinCand))
              (setq sideMap (cons (cons rep choosePlus) sideMap))
              (setq segIdx (DEGZ--poly-closest-seg-index ptsMain bestIp mainClosed))
              (setq segMap (cons (cons rep segIdx) segMap))
            )
          )

          (if (> (length recs) 1)
            (progn
               ;; Bu satir icin cocuk dal onceden olusturulduysa 40 cm uzaklik
               ;; onu dirsekli/remote gruba cevirmesin. Yakin bloklar kendi
               ;; cocuk dalina normal ve tek ortak taraftan baglanir.
               (if (and (> bestD mainFarLim) (not rowGuideActive))
                (progn
                  (setq remoteMap (cons (cons rep T) remoteMap))
                  (setq mergePt (DEGZ--point-toward bestIp cpMain mergeOff))
                  (setq mergeMap (cons (cons rep mergePt) mergeMap))

                  (setq udir (DEGZ--unit (- (car bestIp) (car cpMain)) (- (cadr bestIp) (cadr cpMain))))
                  (setq dirMap (cons (cons rep (list (car udir) (cadr udir))) dirMap))
                )
                (progn
                  (setq remoteMap (cons (cons rep nil) remoteMap))
                  (setq forcedReps (cons rep forcedReps))
                  ;; Normal cizimde yakin grup tek taraftan baglansin. Yon,
                  ;; grubun dizilim eksenine dik secilerek blok ustunden gecis onlenir.
                  (setq cpMain (deg-safe-closest-point mainTmp ipAvg)
                        blockSide
                          (DEGZ--normal-group-no-cross-side
                            cpMain ipAvg recs blockSide))
                  (setq blockSideMap (cons (cons rep blockSide) blockSideMap)
                        groupDirMap
                          (cons
                            (cons rep (DEGZ--approach-unit-for-side blockSide))
                            groupDirMap))
                )
              )
            )
            (setq remoteMap (cons (cons rep nil) remoteMap))
          )
        )

        (setq procData '())
        (foreach g groups
          (setq rep  (car g))
          (setq recs (cdr g))
          (setq remote (cdr (assoc rep remoteMap)))
          (if (and remote (> (length recs) 1))
            (progn
              (setq anchorRec (cdr (assoc rep anchorMap)))
              (setq procData (append procData (list anchorRec)))
              (foreach r recs
                (if (not (equal (car r) (car anchorRec)))
                  (setq procData (append procData (list r)))
                )
              )
            )
            (setq procData (append procData recs))
          )
        )

        (setq crv crv0)

        (foreach rec procData
          (setq blk (car rec))
          (setq ip  (cadr rec))

          (setq rep (DEGZ--uf-find parents blk))
          (setq choosePlus (cdr (assoc rep sideMap)))
          (if (null choosePlus) (setq choosePlus T))
          (setq remote (cdr (assoc rep remoteMap)))
          (setq preRec
            (if (and (boundp '*DEGZ_PRE_COMMON_TARGET_MAP*)
                     *DEGZ_PRE_COMMON_TARGET_MAP*)
              (assoc blk *DEGZ_PRE_COMMON_TARGET_MAP*)
              nil)
                preSide (if preRec (cadr preRec) nil)
                preTarget (if preRec (caddr preRec) nil))

          (setq anchorRec (cdr (assoc rep anchorMap)))
          (setq isAnchor (and remote anchorRec (equal blk (car anchorRec))))
          (setq forceMain (if (member rep forcedReps) T nil))

          (cond
            (forceMain
              (progn
                (setq segIdx (cdr (assoc rep segMap)))
                (if (null segIdx) (setq segIdx 0))
                (setq cpMain (DEGZ--poly-closest-on-seg ptsMain segIdx ip mainClosed))
              )
            )
            (remote
              (if isAnchor
                (progn
                  (setq segIdx (cdr (assoc rep segMap)))
                  (if (null segIdx) (setq segIdx 0))
                  (setq cpMain (DEGZ--poly-closest-on-seg ptsMain segIdx ip mainClosed))
                )
                (progn
                  (setq cpMain (deg-safe-closest-point mainTmp ip))
                )
              )
            )
            (T (setq cpMain (deg-safe-closest-point mainTmp ip)))
          )
          (if (and preTarget (not remote))
            (setq cpMain preTarget))

          (setq cpCur (deg-safe-closest-point crv cpMain))

          (setq ip     (DEGZ--pt2d ip))
          (setq cpMain (DEGZ--pt2d cpMain))
          (setq cpCur  (DEGZ--pt2d cpCur))

          (setq vvx (- (car ip) (car cpMain)))
          (setq vvy (- (cadr ip) (cadr cpMain)))

          ;; Cikinti tarafi block'un baglanti/base noktasindan gorunen govdesine bakarak belirlenir.
          ;; Ana hat noktasi veya block rotasyonu bu karari bozmasin.
          (setq blockSide (cdr (assoc rep blockSideMap)))
          (if (null blockSide)
            (setq blockSide (DEGZ--side-from-connect-to-block cpMain ip))
          )
          (if (and preSide (not remote))
            (setq blockSide preSide))
          
          (DEGZ--dbg-cikinti "DZ" blockSide remote isAnchor forceMain ip cpMain)
          (setq orthoForced nil)
(setq shiftBlk shift)
          (setq uu (DEGZ--unit vvx vvy))
          (setq dx (car uu) dy (cadr uu) len (caddr uu))

          (if (and remote (not isAnchor))
            (progn
              (setq uDirRemote (cdr (assoc rep dirMap)))
              (setq dx (car uDirRemote))
              (setq dy (cadr uDirRemote))
              (setq len 100.0)
            )
          )
          (setq groupDir (cdr (assoc rep groupDirMap)))
          (if (and preSide (not remote))
            (setq groupDir (DEGZ--approach-unit-for-side preSide)))
          (if groupDir
            (setq dx (car groupDir)
                  dy (cadr groupDir)
                  len 100.0)
          )

          (if (> len 1e-9)
            (progn
              (setq rx dy)
              (setq ry (- dx))

              ;; =========================================================
              ;; 1. BLOK BACAK YONU VE TARAF KONTROLU (HERKES ICIN)
              ;; =========================================================
              (setq oblique (DEGZ--oblique-vector-p dx dy))
              (if oblique
                (progn
                  ;; Egik hatta taraf karari aciya ve RIGHT/TOP etiketine bagli degildir.
                  (setq sideFact
                    (DEGZ--local-side-factor mainTmp cpMain dx dy rx ry)
                  )
                  (setq isTargetSide (< sideFact 0.0))
                )
                (progn
                  (setq isTargetSide
                    (or (eq blockSide 'BOTTOM) (eq blockSide 'RIGHT))
                  )
                  (setq sideFact (if isTargetSide -1.0 1.0))
                )
              )

              ;; Plan tarafina gore gerekirse bacaklari ters yone cevir
              (setq ipRin
                (list
                  (+ (car ip) (* rx shiftBlk sideFact))
                  (+ (cadr ip) (* ry shiftBlk sideFact))
                )
              )
              (setq ipRin
                 (list 
                   (- (car ipRin) (* dx approach))
                   (- (cadr ipRin) (* dy approach))
                 )
              )
              ;; Sabit cikinti yonu icin ipRin WCS'te uretilir.
              ;; LEFT: altta, RIGHT: ustte, TOP/BOTTOM: solda.
              (if (not oblique)              (setq ipRin
                (cond
                  ((eq blockSide 'LEFT)
                    (list (- (car ip) approach) (- (cadr ip) shiftBlk))
                  )
                  ((eq blockSide 'RIGHT)
                    (list (+ (car ip) approach) (- (cadr ip) shiftBlk))
                  )
                  ((eq blockSide 'TOP)
                    (list (- (car ip) shiftBlk) (+ (cadr ip) approach))
                  )
                  ((eq blockSide 'BOTTOM)
                    (list (- (car ip) shiftBlk) (- (cadr ip) approach))
                  )
                  (T ipRin)
                )
              )              
              )
              ;; cpE noktasini da tarafa gore duzelt (Referans icin)
              (setq rx (* rx sideFact))
              (setq ry (* ry sideFact))

              ;; Remote + anchor + sol/ust ise ANA HAT UZERINDEKI CIKIS VERTEX'INI OBUR TARAFA AL
              ;; (blok bacagi/yonu degismez, sadece ana hatta degdigi taraf degisir)
              (if (and remote isAnchor isTargetSide)
                (setq choosePlus (if choosePlus nil T))
              )

              (if (or forceMain remote)
                (setq cpE (DEGZ--cpE-side-flag crv cpCur joinCand choosePlus))
                (setq cpE (DEGZ--cpE-side      crv cpCur joinCand rx ry))
              )
              (setq cpCur (DEGZ--pt2d-safe cpCur cpMain))
              (setq cpE   (DEGZ--pt2d-safe cpE cpCur))
              (if (and cpCur cpE)
                (setq cpEshort (DEGZ--shorten-toward-cp crv cpCur cpE (min short (* (distance cpCur cpE) 0.45))))
                (setq cpEshort cpCur)
              )
              (setq cpEshort (DEGZ--pt2d-safe cpEshort cpCur))

              ;; Capraz kose grubunda agzi yaklasima dik komsu segmentte ac.
              ;; Remote anchor agzi, hat acisindan bagimsiz olarak ayardaki
              ;; tam ofsetle kurulsun. Aksi halde yatay/dikey kollarda onceki
              ;; kisaltma hesabi agzi 10/20 gibi ara bir mesafede birakiyordu.
              (if (and groupDir remote isAnchor)
                (progn
                  (setq alignedPair
                    (DEGZ--corner-mouth-pair-by-approach crv cpMain groupDir short))
                  (if alignedPair
                    (setq cpCur (car alignedPair)
                          cpEshort (cadr alignedPair)))
                )
              )

              (if (and cpCur cpEshort (> (distance cpCur cpEshort) 1e-4))
                (progn
                  
                  (if (and remote (not isAnchor))
                     ;; =====================================================
                     ;; DURUM A: UZAK BLOKLAR (REMOTE) -> L-SHAPE / MERGE
                     ;; =====================================================
                     ;; * Bu bloklar komsu hattina baglanmali (Merge).
                     ;; * Hesaplamalar 'crv' (islenmis hat) uzerinde yapilmali.
                     (progn
                       ;; pMerge: ip'den mergeOff kadar asagi
                       (setq pMerge
                        (list
                          (+ (car ip) (* (- dx) mergeOff))
                          (+ (cadr ip) (* (- dy) mergeOff))
                        )
                       )
                       ;; pMergeRin: ipRin hizasinda
                       (setq pMergeRin
                        (list
                          (+ (car pMerge) (- (car ipRin) (car ip)))
                          (+ (cadr pMerge) (- (cadr ipRin) (cadr ip)))
                        )
                       )
                       
                       ;; Dis L eslesmesi:
                       ;; Ana hatta devam eden cift hatta soldaki kol ust yataya,
                       ;; sagdaki kol alt yataya baglanir. Boylece capraz eslesme olmaz.
                       (if (or (< (car pMerge) (car pMergeRin))
                               (and (equal (car pMerge) (car pMergeRin) 1e-9)
                                    (> (cadr pMerge) (cadr pMergeRin))))
                         (progn
                           (setq pLeft pMerge)
                           (setq ipLeft ip)
                           (setq pRight pMergeRin)
                           (setq ipRight ipRin)
                         )
                         (progn
                           (setq pLeft pMergeRin)
                           (setq ipLeft ipRin)
                           (setq pRight pMerge)
                           (setq ipRight ip)
                         )
                       )

                       (if (>= (cadr pLeft) (cadr pRight))
                         (progn (setq yTop (cadr pLeft)) (setq yBot (cadr pRight)))
                         (progn (setq yTop (cadr pRight)) (setq yBot (cadr pLeft)))
                       )

                       ;; Cikinti tarafindaki kisa ucu dis tarafa al.
                       ;; Ustten/alttan gelise gore capraz ureten eslesmeyi secme.
                       (setq outsideLeft
                         (>= (+ (* (car ipLeft) rx) (* (cadr ipLeft) ry))
                             (+ (* (car ipRight) rx) (* (cadr ipRight) ry)))
                       )
                       ;; Ustten gelen durumda cikinti aynalanir; kisa ucu dis tarafa almak icin eslesmeyi tersle.
                       (setq fromTop (eq blockSide 'TOP))
                       (if fromTop
                         (setq outsideLeft (if outsideLeft nil T))
                       )
                       ;; Asagidan geliste ust-alt eslesmesi ayri aynalanir.
                       (if (eq blockSide 'BOTTOM)
                         (setq outsideLeft (if outsideLeft nil T))
                       )
                       (setq pTopA (list (car pLeft) yTop))
                       (setq pBotA (list (car pRight) yBot))
                       (setq pTopB (list (car pRight) yTop))
                       (setq pBotB (list (car pLeft) yBot))
                       (if outsideLeft
                         (progn
                           (setq ipTop ipLeft)
                           (setq ipBot ipRight)
                           (setq pMainTop pTopA)
                           (setq pMainBot pBotA)
                         )
                         (progn
                           (setq ipTop ipRight)
                           (setq ipBot ipLeft)
                           (setq pMainTop pTopB)
                           (setq pMainBot pBotB)
                         )
                       )
                        ;; Ana hat agzinda capraz eslesme olmasin:
                        ;; ust/alt (veya sol/sag) ana hat ucu ayni siradaki blok ucuna baglansin.
                        (setq dirRec (DEGZ--pair-main-block-no-cross blockSide pMerge pMergeRin ip ipRin))
                        (setq pMainTop (car dirRec))
                        (setq pMainBot (cadr dirRec))
                        (setq ipTop (caddr dirRec))
                        (setq ipBot (cadddr dirRec))
                       ;; Ana hat uzerindeki noktalar (Mevcut 'crv' uzerinden alinir)
                       (setq cpCur    (deg-safe-closest-point crv pMainTop))
                       (setq cpEshort (deg-safe-closest-point crv pMainBot))
                       
                       ;; Alt kol ana hatta baglanir; ust kol dis L'yi tamamlar.
                       (setq pJoin
                         (inters
                           (list (car pMainBot) (cadr pMainBot) 0.0)
                           (list (+ (car pMainBot) rx) (+ (cadr pMainBot) ry) 0.0)
                           (list (car cpEshort) (cadr cpEshort) 0.0)
                           (list (+ (car cpEshort) dx) (+ (cadr cpEshort) dy) 0.0)
                           nil
                         )
                       )
                       (if pJoin
                         (setq pJoin (DEGZ--pt2d pJoin))
                         (setq pJoin (list (car cpEshort) (cadr pMainBot)))
                       )
                       ;; Blok cikislarina direkt capraz gitme.
                       ;; Ana hat noktasi ile blok cikisi hem X hem Y farkliyse araya kirim koy.
                       (setq sideMode
                         (or
                           (eq blockSide 'LEFT)
                           (eq blockSide 'RIGHT)
                           (and (> (abs (- (car pMainTop) (car ipTop))) 1e-6)
                                (> (abs (- (cadr pMainTop) (cadr ipTop))) 1e-6))
                           (and (> (abs (- (car pMainBot) (car ipBot))) 1e-6)
                                (> (abs (- (cadr pMainBot) (cadr ipBot))) 1e-6))
                         )
                       )
                       (if sideMode
                         (progn
                           ;; Sabit cikinti yonu:
                           ;; LEFT/RIGHT -> cikinti altta.
                           ;; TOP/BOTTOM -> cikinti solda.
                           (setq shortIp nil)
                           (setq longIp nil)
                           (if oblique
                             (if (or (eq blockSide 'LEFT) (eq blockSide 'RIGHT))
                               (progn
                                 ;; Bu dallarda pMainTop-longIp ve pJoin-shortIp ayni ofset kolunda kalir.
                                 (setq longIp ipTop)
                                 (setq shortIp ipBot)
                               )
                               (progn
                                 ;; Bu dallarda pMainTop-shortIp ve pJoin-longIp ayni ofset kolunda kalir.
                                 (setq shortIp ipTop)
                                 (setq longIp ipBot)
                               )
                             )
                             (cond
                               ((or (eq blockSide 'LEFT) (eq blockSide 'RIGHT))
                                 ;; Yatay gelislerde alt nokta short, ust nokta long olur.
                                 ;; Yatay dallar zit cizer: RIGHT short-first, LEFT long-first.
                                 (if (<= (cadr ipTop) (cadr ipBot))
                                   (progn (setq shortIp ipTop) (setq longIp ipBot))
                                   (progn (setq shortIp ipBot) (setq longIp ipTop))
                                 )
                               )
                               ((or (eq blockSide 'TOP) (eq blockSide 'BOTTOM))
                                 ;; Dikey gelislerde sol nokta short, sag nokta long olur.
                                 (if (<= (car ipTop) (car ipBot))
                                   (progn (setq shortIp ipTop) (setq longIp ipBot))
                                   (progn (setq shortIp ipBot) (setq longIp ipTop))
                                 )
                               )
                             )
                           )
                           (if oblique
                             (progn
                               ;; Egik dirsekte hat kimligini koru: pMerge-ip, pMergeRin-ipRin.
                               ;; Uclar ayrica siralanmaz; boylece aciya bagli Z/capraz dirsek olusmaz.
                               (setq pTopDrop
                                 (DEGZ--local-bend-point pMainTop ipTop dx dy rx ry blockSide)
                               )
                               (setq pBotDrop
                                 (DEGZ--local-bend-point pJoin ipBot dx dy rx ry blockSide)
                               )
                               (setq crv
                                 (DEGZ--insert-detour
                                   crv
                                   cpCur
                                   cpEshort
                                   (list pMainTop pTopDrop ipTop ipBot pBotDrop pJoin)
                                 )
                               )
                             )
                             (cond
                               ((eq blockSide 'TOP)
                                       ;; Ustten geliste mevcut dogru eslesme korunur.
                                       (if (not shortIp)
                                         (if (<= (distance pMainTop ipTop) (distance pMainTop ipBot))
                                           (progn (setq shortIp ipTop) (setq longIp ipBot))
                                           (progn (setq shortIp ipBot) (setq longIp ipTop))
                                         )
                                       )
                                       (setq pTopDrop
                                          (if oblique
                                            (DEGZ--local-bend-point pMainTop shortIp dx dy rx ry blockSide)
                                            (list (car pMainTop) (cadr shortIp))
                                          )
                                        )
                                       (setq pBotDrop
                                          (if oblique
                                            (DEGZ--local-bend-point pJoin longIp dx dy rx ry blockSide)
                                            (list (car pJoin) (cadr longIp))
                                          )
                                        )
                                       (setq crv
                                         (DEGZ--insert-detour
                                           crv
                                           cpCur
                                           cpEshort
                                           (list pMainTop pTopDrop shortIp longIp pBotDrop pJoin)
                                         )
                                       )                             )
                               ((eq blockSide 'BOTTOM)
                                 ;; Asagidan geliste cikinti kisa/uzun eslesmesi secim asamasinda aynalanir.
                                 (if (not shortIp)
                                   (if (<= (distance pMainTop ipTop) (distance pMainTop ipBot))
                                     (progn (setq shortIp ipTop) (setq longIp ipBot))
                                     (progn (setq shortIp ipBot) (setq longIp ipTop))
                                   )
                                 )
                                 (setq pTopDrop
                                          (if oblique
                                            (DEGZ--local-bend-point pMainTop shortIp dx dy rx ry blockSide)
                                            (list (car pMainTop) (cadr shortIp))
                                          )
                                        )
                                 (setq pBotDrop
                                          (if oblique
                                            (DEGZ--local-bend-point pJoin longIp dx dy rx ry blockSide)
                                            (list (car pJoin) (cadr longIp))
                                          )
                                        )
                                 (setq crv
                                   (DEGZ--insert-detour
                                     crv
                                     cpCur
                                     cpEshort
                                     (list pMainTop pTopDrop shortIp longIp pBotDrop pJoin)
                                   )
                                 )
                               )
                               ((eq blockSide 'RIGHT)
                                       ;; Sagdan geliste de UP/BOTTOM ile ayni agiz sirasi kullanilir.
                                       (if (not shortIp)
                                         (if (<= (distance pMainBot ipTop) (distance pMainBot ipBot))
                                           (progn (setq shortIp ipTop) (setq longIp ipBot))
                                           (progn (setq shortIp ipBot) (setq longIp ipTop))
                                         )
                                       )
                                       (setq pTopDrop
                                          (if oblique
                                            (DEGZ--local-bend-point pMainTop shortIp dx dy rx ry blockSide)
                                            (list (car pMainTop) (cadr shortIp))
                                          )
                                        )
                                       (setq pBotDrop
                                          (if oblique
                                            (DEGZ--local-bend-point pJoin longIp dx dy rx ry blockSide)
                                            (list (car pJoin) (cadr longIp))
                                          )
                                        )
                                       (setq crv
                                         (DEGZ--insert-detour
                                           crv
                                           cpCur
                                           cpEshort
                                           (list pMainTop pTopDrop shortIp longIp pBotDrop pJoin)
                                         )
                                       )                             )
                               ((eq blockSide 'LEFT)
                                       ;; LEFT, RIGHT'in aynasi olarak uzun ucu ust agza baglar.
                                       (if (not shortIp)
                                         (if (<= (distance pMainTop ipTop) (distance pMainTop ipBot))
                                           (progn (setq shortIp ipTop) (setq longIp ipBot))
                                           (progn (setq shortIp ipBot) (setq longIp ipTop))
                                         )
                                       )
                                       (setq pTopDrop
                                          (if oblique
                                            (DEGZ--local-bend-point pMainTop longIp dx dy rx ry blockSide)
                                            (list (car pMainTop) (cadr longIp))
                                          )
                                        )
                                       (setq pBotDrop
                                          (if oblique
                                            (DEGZ--local-bend-point pJoin shortIp dx dy rx ry blockSide)
                                            (list (car pJoin) (cadr shortIp))
                                          )
                                        )
                                       (setq crv
                                         (DEGZ--insert-detour
                                           crv
                                           cpCur
                                           cpEshort
                                           (list pMainTop pTopDrop longIp shortIp pBotDrop pJoin)
                                         )
                                       )                             )
                               (T
                                       ;; Belirsiz yonde varsayilan dogru eslesme.
                                       (if (not shortIp)
                                         (if (<= (distance pMainTop ipTop) (distance pMainTop ipBot))
                                           (progn (setq shortIp ipTop) (setq longIp ipBot))
                                           (progn (setq shortIp ipBot) (setq longIp ipTop))
                                         )
                                       )
                                       (setq pTopDrop
                                          (if oblique
                                            (DEGZ--local-bend-point pMainTop shortIp dx dy rx ry blockSide)
                                            (list (car pMainTop) (cadr shortIp))
                                          )
                                        )
                                       (setq pBotDrop
                                          (if oblique
                                            (DEGZ--local-bend-point pJoin longIp dx dy rx ry blockSide)
                                            (list (car pJoin) (cadr longIp))
                                          )
                                        )
                                       (setq crv
                                         (DEGZ--insert-detour
                                           crv
                                           cpCur
                                           cpEshort
                                           (list pMainTop pTopDrop shortIp longIp pBotDrop pJoin)
                                         )
                                       )                             )
                             )
                           )
                         )
                         (setq crv
                           (DEGZ--insert-detour
                             crv
                             cpCur
                             cpEshort
                             (list pMainTop ipTop ipBot pMainBot pJoin)
                           )
                         )
                       )
                     )
                     
                     ;; =====================================================
                     ;; DURUM B: YAKIN BLOKLAR (DIRECT CONNECT)
                     ;; =====================================================
                     ;; * Bu bloklar DIREKT ana hatta baglanmali.
                     ;; * Komsunun bacagina YAPISMAMALI.
                     ;; * Bu yuzden referans olarak 'mainTmp' (Temiz Hat) kullanilmali.
                     (progn
                        (if (and remote isAnchor)
                            ;; Anchor ozel durumu (Pahli Baglanti)
                            (progn
                              (setq dirRec
                                 (if oblique
                                   (DEGZ--pair-by-local-offset cpCur cpEshort ip ipRin rx ry)
                                   (DEGZ--direct-detour-order blockSide cpCur cpEshort ip ipRin)
                                 )
                               )
                              (if dirRec
                                (progn
                                  (setq cpCur    (car dirRec))
                                  (setq cpEshort (cadr dirRec))
                                  (setq ipTop    (caddr dirRec))
                                  (setq ipBot    (cadddr dirRec))
                                  (setq distEnds (distance cpCur cpEshort))
                                  (if (> distEnds 1e-9)
                                    (progn
                                      (setq uTan (list (/ (- (car cpEshort) (car cpCur)) distEnds)
                                                       (/ (- (cadr cpEshort) (cadr cpCur)) distEnds)))
                                      (setq uPerp (list (- (cadr uTan)) (car uTan)))
                                      (if alignedPair
                                        (progn
                                          (setq corner1 (DEGZ--corner-at-block-axis cpCur ipTop groupDir)
                                                corner2 (DEGZ--corner-at-block-axis cpEshort ipBot groupDir))
                                          (setq crv (DEGZ--insert-detour crv cpCur cpEshort
                                            (list corner1 ipTop ipBot corner2))))
                                        (progn
                                          (setq corner1 (DEGZ--calc-L-corner cpCur ipTop uPerp)
                                                corner2 (DEGZ--calc-L-corner cpEshort ipBot uPerp))
                                          (setq crv (DEGZ--insert-detour crv cpCur cpEshort
                                            (list corner1 ipTop ipBot corner2)))))
                                    )
                                  )
                                )
                              )
                            )
                            
                            ;; STANDART DIREKT BAGLANTI (VEKTOREL HIZALAMA)
                            (progn
                                ;; *** ONEMLI: Hesaplamalarda 'mainTmp' (Temiz Hat) kullan! ***
                                (setq calcCrv mainTmp) 
                                
                                ;; A. Orta noktayi bul
                                (setq ipAvg (list (/ (+ (car ip) (car ipRin)) 2.0) (/ (+ (cadr ip) (cadr ipRin)) 2.0)))
                                ;; Yakin bloklar icin ortak hedef son yakin-hat
                                ;; hesabindan once korunur.
                                (setq pMid
                                  (if (and preTarget (not remote))
                                    (deg-safe-closest-point calcCrv preTarget)
                                    (deg-safe-closest-point calcCrv ipAvg)))
                                
                                ;; B. Hattin yonunu bul (Temiz hat uzerinden)
                                (setq paramMid (vlax-curve-getParamAtPoint (DEGZ--ename calcCrv) (DEGZ--pt3d pMid)))
                                (setq deriv (vlax-curve-getFirstDeriv (DEGZ--ename calcCrv) paramMid))
                                (setq Tlen (distance '(0 0 0) deriv))
                                (if (< Tlen 1e-9)
                                   (progn (setq Tx rx) (setq Ty ry))
                                   (progn (setq Tx (/ (car deriv) Tlen)) (setq Ty (/ (cadr deriv) Tlen)))
                                )

                                ;; C. Hizalama Yonu
                                (setq Lx (- (car ipRin) (car ip)))
                                (setq Ly (- (cadr ipRin) (cadr ip)))
                                (setq dotProd (+ (* Tx Lx) (* Ty Ly)))
                                (setq dirSign (if (>= dotProd 0) 1.0 -1.0))

                                ;; Remote + anchor + target side: reverse direction so the short piece is taken from the other side
                                (if (and remote isAnchor isTargetSide)
                                  (setq dirSign (- dirSign))
                                )
                                
                                ;; D. DZ_OFFSET iki ray arasindaki toplam mesafedir.
                                ;; Agiz noktalari merkezden +/- DZ_OFFSET/2 uretilir.
                                (setq distMid (vlax-curve-getDistAtParam (DEGZ--ename calcCrv) paramMid))
                                (setq maxDist (DEGZ--curve-total calcCrv))
                                
                                (setq distPair (DEGZ--distpair10 distMid dirSign maxDist (* 0.5 shift)))
                                (setq distDown (car distPair))
                                (setq distDownRin (cadr distPair))
                                
                                ;; Noktalari Temiz Hat uzerinden al (Komsunun bacagina carpmaz)
                                (setq pDown    (DEGZ--pt2d (vlax-curve-getPointAtDist (DEGZ--ename calcCrv) distDown)))
                                (setq pDownRin (DEGZ--pt2d (vlax-curve-getPointAtDist (DEGZ--ename calcCrv) distDownRin)))

                                ;; Detour ekleme noktalarini guncel 'crv' uzerinde bul
                                ;; pDown temiz hat uzerinde oldugu icin, 'crv' uzerinde de govdeye denk gelir.
                                (setq cpCur    (deg-safe-closest-point crv pDown))
                                (setq cpEshort (deg-safe-closest-point crv pDownRin))
                                
                                (setq ipRin (DEGZ--direct-offset-end ip ipRin cpCur cpEshort short))
                                ;; DIREKT BAGLANTI LISTESI
                                (setq dirRec
                                 (DEGZ--pair-by-local-offset cpCur cpEshort ip ipRin
                                   (- (car cpEshort) (car cpCur))
                                   (- (cadr cpEshort) (cadr cpCur)))
                               )
                                (if dirRec
                                  (progn
                                    (setq cpCur    (car dirRec))
                                    (setq cpEshort (cadr dirRec))
                                    (setq ipTop    (caddr dirRec))
                                    (setq ipBot    (cadddr dirRec))
                                    (setq distEnds (distance cpCur cpEshort))
                                    (if (> distEnds 1e-9)
                                      (progn
                                        (setq uTan (list (/ (- (car cpEshort) (car cpCur)) distEnds)
                                                         (/ (- (cadr cpEshort) (cadr cpCur)) distEnds)))
                                        (setq uPerp (list (- (cadr uTan)) (car uTan)))
                                        (setq corner1 (DEGZ--calc-L-corner cpCur ipTop uPerp))
                                        (setq corner2 (DEGZ--calc-L-corner cpEshort ipBot uPerp))
                                        (setq crv (DEGZ--insert-detour crv cpCur cpEshort (list corner1 ipTop ipBot corner2)))
                                      )
                                      (setq crv (DEGZ--insert-detour crv cpCur cpEshort (list ipTop ipBot)))
                                    )
                                  )
                                )
                            )
                        )
                     )
                  )
                )
              )
            )
          )
        )

        (if mainTmp (entdel mainTmp))
      )
    )
  )
  ;; DZ_ORIG final cizimi tek seferlik kontrol edebilsin diye son entity'yi dondur.
  (if (and crv (entget crv)) crv nil)
)

(defun DEGDR--RUN (mainEnt pick dist / mainPts tol ss allEnts rootId assignedEnts lay mainCol tubePls scan e pl outline)
  (setq mainPts (g365_get_pts mainEnt))
  (if (or (null mainPts) (< (length mainPts) 2))
    (progn (princ "\nAna hat okunamadi / cok kisa.") nil)
    (progn
      (setq tol (DEG:CFG-TOL-NUM-OR 'DR_TREE_TOL 0.1))
      (if (<= dist 0.0)
        (progn (princ "\nGecersiz mesafe.") nil)
        (progn
          (setq lay (cdr (assoc 8 (entget mainEnt))))
          (setq mainCol (g365_effective_color mainEnt))
          ;; Iskelete dahil olacak nesneler, secilen ana hat ile AYNI layer'da olmalidir.
          (if (and lay (/= lay ""))
            (setq ss (ssget "X" (list (cons 0 "LWPOLYLINE,POLYLINE,LINE") (cons 8 lay))))
            (setq ss (ssget "X" '((0 . "LWPOLYLINE,POLYLINE,LINE"))))
          )
          (if (null ss)
            (progn (princ "\nHic nesne bulunamadi.") nil)
            (progn
              (setq allEnts (g372_ss_to_list ss))
              ;; Iskelete dahil olacak nesneler, secilen ana hat ile AYNI renkte olmalidir.
              (setq allEnts
                (vl-remove nil
                  (mapcar
                    '(lambda (en)
                       (if (= (g365_effective_color en) mainCol) en nil)
                     )
                    allEnts
                  )
                )
              )
              (setq rootId (g372_build_tree mainEnt mainPts allEnts tol))
              (setq assignedEnts (g415_get_assigned_original_ents allEnts))
              
              (setq tubePls nil)
              (setq scan assignedEnts)
              (while scan
                (setq e (car scan))
                (setq pl (g415_make_tube_poly_from_ent e dist lay))
                (if pl (setq tubePls (cons pl tubePls)))
                (setq scan (cdr scan))
              )
              (setq tubePls (reverse tubePls))
              (setq outline (g415_union_tubes_to_outline tubePls lay))

              (if outline
                (progn
                  (setq outline (g418_rebuild_outline_seam outline lay pick mainPts dist))
                  (if outline (g365_copy_color mainEnt outline))
                  (g415_delete_ents assignedEnts)
                  (g418_flush_cmd)
                  outline
                )
                nil
              )
            )
          )
        )
      )
    )
  )
)

(defun DEGDC--collect-connected (mainEnt / mainPts tol ss allEnts lay mainCol found)
  (setq mainPts (g365_get_pts mainEnt))
  (if (or (null mainPts) (< (length mainPts) 2))
    nil
    (progn
      (setq tol (DEG:CFG-TOL-NUM-OR 'DR_TREE_TOL 0.1))
      (setq lay     (cdr (assoc 8 (entget mainEnt))))
      (setq mainCol (g365_effective_color mainEnt))
      (if (and lay (/= lay ""))
        (setq ss (ssget "X" (list (cons 0 "LWPOLYLINE,POLYLINE,LINE") (cons 8 lay))))
        (setq ss (ssget "X" '((0 . "LWPOLYLINE,POLYLINE,LINE"))))
      )
      (if ss
        (progn
          (setq allEnts (g372_ss_to_list ss))
          (setq allEnts
            (vl-remove nil
              (mapcar
                '(lambda (en)
                   (if (= (g365_effective_color en) mainCol) en nil)
                 )
                allEnts
              )
            )
          )
          (g372_build_tree mainEnt mainPts allEnts tol)
          (setq found (g415_get_assigned_original_ents allEnts))
          (g372_reset_tree)
          found
        )
        nil
      )
    )
  )
)

(defun DEGDC--closest-on-ents (pt ents / basePt bestPt bestEnt bestD en cp d)
  (setq basePt (deg-pt3 pt))
  (setq bestPt nil bestEnt nil bestD nil)
  (while ents
    (setq en (car ents))
    (if (and basePt en (entget en))
      (progn
        (setq cp (deg-safe-closest-point en basePt))
        (if cp
          (progn
            (setq d (distance basePt cp))
            (if (or (null bestD) (< d bestD))
              (setq bestPt cp
                    bestEnt en
                    bestD d)
            )
          )
        )
      )
    )
    (setq ents (cdr ents))
  )
  (if bestPt
    (list bestPt bestEnt bestD)
    nil
  )
)

(defun DEGDC--block-rotation (blkEnt / ang)
  (setq ang (cdr (assoc 50 (entget blkEnt))))
  (if (numberp ang) ang 0.0)
)

(defun DEGDC--offset-point (pt ang dist / p)
  (setq p (deg-pt3 pt))
  (if p
    (list
      (+ (car p) (* dist (cos ang)))
      (+ (cadr p) (* dist (sin ang)))
      (caddr p)
    )
    nil
  )
)

(defun DEGDC--block-ortho-tail-pts (fromPt joinPt joinEnt downAng / d h uTan vx vy offH pickPt prefT rawT dir rad stubLen p1 pEnd)
  (setq d (list (cos downAng) (sin downAng) 0.0))
  (setq h (list (- (sin downAng)) (cos downAng) 0.0))
  (setq uTan (DEGDC--curve-unit-tangent joinEnt joinPt))
  (if (null uTan)
    (setq uTan h)
  )
  (setq vx (- (car joinPt) (car fromPt)))
  (setq vy (- (cadr joinPt) (cadr fromPt)))
  (setq offH (+ (* vx (car h)) (* vy (cadr h))))
  (setq pickPt (deg-pt3 *DEGDC_PICKPT*))
  (setq rawT (+ (* vx (car uTan)) (* vy (cadr uTan))))
  (if pickPt
    (setq prefT (+ (* (- (car pickPt) (car joinPt)) (car uTan)) (* (- (cadr pickPt) (cadr joinPt)) (cadr uTan))))
    (setq prefT rawT)
  )
  (cond
    ((> prefT 1e-6) (setq dir 1.0))
    ((< prefT -1e-6) (setq dir -1.0))
    ((> rawT 1e-6) (setq dir 1.0))
    ((< rawT -1e-6) (setq dir -1.0))
    (T (setq dir 1.0))
  )
  (setq rad (DEG:CFG-NUM-OR 'DC_FILLET_R 10.0))
  (if (<= rad 0.0) (setq rad 10.0))
  (setq stubLen (max rad 1.0))
  (setq p1
    (list
      (+ (car fromPt) (* offH (car h)))
      (+ (cadr fromPt) (* offH (cadr h)))
      (if (caddr fromPt) (caddr fromPt) 0.0)
    )
  )
  (setq pEnd
    (list
      (+ (car joinPt) (* dir stubLen (car uTan)))
      (+ (cadr joinPt) (* dir stubLen (cadr uTan)))
      (if (caddr joinPt) (caddr joinPt) 0.0)
    )
  )
  (g365_clean_pts (list p1 (deg-pt3 joinPt) pEnd))
)
(defun DEGDC--horizontal-sign (pDown ents baseAng sideLen / refRec refPt dx dy axisDot rightPt leftPt rightRec leftRec)
  (if (or (null sideLen) (<= sideLen 0.0))
    (setq sideLen 700.0)
  )
  (setq refRec (DEGDC--closest-on-ents pDown ents))
  (if (null refRec)
    1.0
    (progn
      (setq refPt (car refRec))
      (setq dx (- (car refPt) (car pDown)))
      (setq dy (- (cadr refPt) (cadr pDown)))
      (setq axisDot (+ (* dx (cos baseAng)) (* dy (sin baseAng))))
      (cond
        ((> axisDot 1e-9) 1.0)
        ((< axisDot -1e-9) -1.0)
        (T
          (setq rightPt  (DEGDC--offset-point pDown baseAng sideLen))
          (setq leftPt   (DEGDC--offset-point pDown (+ baseAng pi) sideLen))
          (setq rightRec (DEGDC--closest-on-ents rightPt ents))
          (setq leftRec  (DEGDC--closest-on-ents leftPt ents))
          (cond
            ((and rightRec leftRec)
              (if (<= (caddr rightRec) (caddr leftRec)) 1.0 -1.0)
            )
            (rightRec 1.0)
            (leftRec -1.0)
            (T 1.0)
          )
        )
      )
    )
  )
)

(defun DEGDC--dot2 (a b)
  (+ (* (car a) (car b)) (* (cadr a) (cadr b)))
)

(defun DEGDC--pt+scale (pt vec s)
  (list
    (+ (car pt) (* (car vec) s))
    (+ (cadr pt) (* (cadr vec) s))
    (if (caddr pt) (caddr pt) 0.0)
  )
)

(defun DEGDC--block-visible-bbox (blkEnt / obj bb)
  (setq obj (if (vlax-objectp blkEnt) blkEnt (vlax-ename->vla-object blkEnt)))
  (setq bb (degk--get-bbox-visible-by-explode obj))
  (if (null bb)
    (setq bb (degk--ent-bbox obj))
  )
  bb
)

(defun DEGDC--bbox-support (bb axis / mn mx hx hy)
  (if (null bb)
    0.0
    (progn
      (setq mn (car bb) mx (cadr bb))
      (setq hx (/ (- (car mx) (car mn)) 2.0))
      (setq hy (/ (- (cadr mx) (cadr mn)) 2.0))
      (+ (* hx (abs (car axis))) (* hy (abs (cadr axis))))
    )
  )
)

(defun DEGDC--seg-hit-bbox-p (a b bb / pA pB mn mx p1 p2 p3 p4)
  (setq pA (deg-pt3 a))
  (setq pB (deg-pt3 b))
  (and pA pB bb
       (or
         (degw-point-in-bbox-p pA bb)
         (degw-point-in-bbox-p pB bb)
         (progn
           (setq mn (car bb) mx (cadr bb))
           (setq p1 (list (car mn) (cadr mn) 0.0))
           (setq p2 (list (car mx) (cadr mn) 0.0))
           (setq p3 (list (car mx) (cadr mx) 0.0))
           (setq p4 (list (car mn) (cadr mx) 0.0))
           (or (inters pA pB p1 p2 T)
               (inters pA pB p2 p3 T)
               (inters pA pB p3 p4 T)
               (inters pA pB p4 p1 T))
         )
       )
  )
)

(defun DEGDC--curve-unit-tangent (ent pt / obj segTan d endPar endDist span d1 d2 p1 p2 dx dy len)
  (setq segTan (DEGDC--segment-unit-at-point ent pt))
  (if segTan
    segTan
    (progn
      (setq obj (if (vlax-objectp ent) ent (vlax-ename->vla-object ent)))
      (setq d (deg-safe-dist-at-point obj pt))
      (setq endPar (vl-catch-all-apply 'vlax-curve-getEndParam (list obj)))
      (if (vl-catch-all-error-p endPar)
        nil
        (progn
          (setq endDist (vl-catch-all-apply 'vlax-curve-getDistAtParam (list obj endPar)))
          (if (or (vl-catch-all-error-p endDist) (not (numberp endDist)))
            nil
            (progn
              (setq span (min 1.0 (max 0.01 (/ endDist 100.0))))
              (setq d1 (max 0.0 (- d span)))
              (setq d2 (min endDist (+ d span)))
              (if (<= (abs (- d2 d1)) 1e-9)
                nil
                (progn
                  (setq p1 (vl-catch-all-apply 'vlax-curve-getPointAtDist (list obj d1)))
                  (setq p2 (vl-catch-all-apply 'vlax-curve-getPointAtDist (list obj d2)))
                  (if (or (vl-catch-all-error-p p1) (vl-catch-all-error-p p2))
                    nil
                    (progn
                      (setq p1 (deg-pt3 p1))
                      (setq p2 (deg-pt3 p2))
                      (if (or (null p1) (null p2))
                        nil
                        (progn
                          (setq dx (- (car p2) (car p1)))
                          (setq dy (- (cadr p2) (cadr p1)))
                          (setq len (sqrt (+ (* dx dx) (* dy dy))))
                          (if (> len 1e-9)
                            (list (/ dx len) (/ dy len) 0.0)
                            nil
                          )
                        )
                      )
                    )
                  )
                )
              )
            )
          )
        )
      )
    )
  )
)
(defun DEGDC--shift-point-on-curve (ent pt delta / obj curDist endPar endDist target res)
  (setq obj (if (vlax-objectp ent) ent (vlax-ename->vla-object ent)))
  (setq curDist (deg-safe-dist-at-point obj pt))
  (setq endPar (vl-catch-all-apply 'vlax-curve-getEndParam (list obj)))
  (if (vl-catch-all-error-p endPar)
    nil
    (progn
      (setq endDist (vl-catch-all-apply 'vlax-curve-getDistAtParam (list obj endPar)))
      (if (vl-catch-all-error-p endDist)
        nil
        (progn
          (setq target (+ curDist delta))
          (if (< target 0.0) (setq target 0.0))
          (if (> target endDist) (setq target endDist))
          (setq res (vl-catch-all-apply 'vlax-curve-getPointAtDist (list obj target)))
          (if (vl-catch-all-error-p res)
            nil
            (deg-pt3 res)
          )
        )
      )
    )
  )
)

(defun DEGDC--pick-directed-join-rec (fromPt joinRec / pickPt joinPt joinEnt uTan rawTan prefTan dir bias shift newJoin)
  (setq pickPt (deg-pt3 *DEGDC_PICKPT*))
  (if (or (null joinRec) (null pickPt))
    joinRec
    (progn
      (setq joinPt (car joinRec) joinEnt (cadr joinRec))
      (setq uTan (DEGDC--curve-unit-tangent joinEnt joinPt))
      (if (null uTan)
        joinRec
        (progn
          (setq rawTan (+ (* (- (car fromPt) (car joinPt)) (car uTan)) (* (- (cadr fromPt) (cadr joinPt)) (cadr uTan))))
          (setq prefTan (+ (* (- (car pickPt) (car joinPt)) (car uTan)) (* (- (cadr pickPt) (cadr joinPt)) (cadr uTan))))
          (cond
            ((> prefTan 1e-6) (setq dir 1.0))
            ((< prefTan -1e-6) (setq dir -1.0))
            ((> rawTan 1e-6) (setq dir -1.0))
            ((< rawTan -1e-6) (setq dir 1.0))
            (T (setq dir 1.0))
          )
          (setq bias (max (* 2.0 (DEG:CFG-NUM-OR 'DC_FILLET_R 10.0)) 1.0))
          (setq shift (+ rawTan (* dir bias)))
          (setq newJoin (DEGDC--shift-point-on-curve joinEnt joinPt shift))
          (if newJoin
            (list newJoin joinEnt (distance fromPt newJoin))
            joinRec
          )
        )
      )
    )
  )
)

(defun DEGDC--ortho-join-pts (fromPt joinPt joinEnt / uTan uPerp vx vy rawTan rawPerp pickPt prefTan projTan perpDir rad stubLen pStub pMid)
  (setq uTan (DEGDC--curve-unit-tangent joinEnt joinPt))
  (if (null uTan)
    (list (deg-pt3 joinPt))
    (progn
      (setq uPerp (list (- (cadr uTan)) (car uTan) 0.0))
      (setq vx (- (car fromPt) (car joinPt)))
      (setq vy (- (cadr fromPt) (cadr joinPt)))
      (setq rawTan  (+ (* vx (car uTan))  (* vy (cadr uTan))))
      (setq rawPerp (+ (* vx (car uPerp)) (* vy (cadr uPerp))))
      (setq pickPt (deg-pt3 *DEGDC_PICKPT*))
      (if pickPt
        (setq prefTan (+ (* (- (car pickPt) (car joinPt)) (car uTan)) (* (- (cadr pickPt) (cadr joinPt)) (cadr uTan))))
        (setq prefTan rawTan)
      )
      (cond
        ((> prefTan 1e-6) (setq projTan (abs rawTan)))
        ((< prefTan -1e-6) (setq projTan (- (abs rawTan))))
        (T (setq projTan rawTan))
      )
      (cond
        ((> rawPerp 1e-6) (setq perpDir 1.0))
        ((< rawPerp -1e-6) (setq perpDir -1.0))
        (T (setq perpDir 1.0))
      )
      (setq rad (DEG:CFG-NUM-OR 'DC_FILLET_R 10.0))
      (if (<= rad 0.0) (setq rad 10.0))
      (setq stubLen (max (* rad 2.0) 1.0))
      (setq pStub
        (list
          (+ (car joinPt) (* perpDir stubLen (car uPerp)))
          (+ (cadr joinPt) (* perpDir stubLen (cadr uPerp)))
          (if (caddr joinPt) (caddr joinPt) 0.0)
        )
      )
      (setq pMid
        (list
          (+ (car pStub) (* projTan (car uTan)))
          (+ (cadr pStub) (* projTan (cadr uTan)))
          (if (caddr joinPt) (caddr joinPt) 0.0)
        )
      )
      (g365_clean_pts (list pMid pStub (deg-pt3 joinPt)))
    )
  )
)
(defun DEGDC--tail-hit-bbox-p (fromPt tail bb / segA segB)
  (and bb tail (> (length tail) 0)
       (or
         (DEGDC--seg-hit-bbox-p fromPt (car tail) bb)
         (and (> (length tail) 1)
              (setq segA (nth (- (length tail) 2) tail))
              (setq segB (car (last tail)))
              (DEGDC--seg-hit-bbox-p segA segB bb))
       )
  )
)

(defun DEGDC--adjust-join-for-bbox (fromPt joinRec bb / gap joinPt joinEnt tail segA segB uTan ctr d need signs scales sc s newJoin newTail chosen)
  (setq gap (DEG:CFG-NUM-OR 'DC_CLEAR_GAP 5.0))
  (if (<= gap 0.0) (setq gap 5.0))
  (if (or (null bb) (null joinRec))
    joinRec
    (progn
      (setq joinPt (car joinRec) joinEnt (cadr joinRec))
      (setq tail (DEGDC--ortho-join-pts fromPt joinPt joinEnt))
      (if (or (null tail) (< (length tail) 2))
        joinRec
        (progn
          (setq segA (nth (- (length tail) 2) tail))
          (setq segB (car (last tail)))
          (if (not (DEGDC--seg-hit-bbox-p segA segB bb))
            joinRec
            (progn
              (setq uTan (DEGDC--curve-unit-tangent joinEnt joinPt))
              (if (null uTan)
                joinRec
                (progn
                  (setq ctr (degw-bbox-center bb))
                  (setq d (DEGDC--dot2 (list (- (car joinPt) (car ctr)) (- (cadr joinPt) (cadr ctr)) 0.0) uTan))
                  (setq need (- (+ (DEGDC--bbox-support bb uTan) gap) (abs d)))
                  (if (<= need 0.0) (setq need gap))
                  (setq signs (if (>= d 0.0) (list 1.0 -1.0) (list -1.0 1.0)))
                  (setq scales (list 1.0 1.5 2.0 3.0 4.0 6.0 8.0 12.0))
                  (foreach sc scales
                    (foreach s signs
                      (if (null chosen)
                        (progn
                          (setq newJoin (DEGDC--shift-point-on-curve joinEnt joinPt (* s need sc)))
                          (if newJoin
                            (progn
                              (setq newTail (DEGDC--ortho-join-pts fromPt newJoin joinEnt))
                              (if (and newTail (> (length newTail) 1)
                                       (not (DEGDC--seg-hit-bbox-p (nth (- (length newTail) 2) newTail) (car (last newTail)) bb)))
                                (setq chosen (list newJoin joinEnt (distance fromPt newJoin)))
                              )
                            )
                          )
                        )
                      )
                    )
                  )
                  (if chosen chosen joinRec)
                )
              )
            )
          )
        )
      )
    )
  )
)

(defun DEGDC--safe-tail-pts (fromPt joinRec blkEnt / gap bb joinAdj tail firstPt uTan uPerp ctr d need signs scales sc s esc tail2 chosen)
  (setq gap (DEG:CFG-NUM-OR 'DC_CLEAR_GAP 5.0))
  (if (<= gap 0.0) (setq gap 5.0))
  (setq bb (DEGDC--block-visible-bbox blkEnt))
  (if bb
    (setq bb (degw-bbox-expand bb gap))
  )
  (setq joinAdj (if bb (DEGDC--adjust-join-for-bbox fromPt joinRec bb) joinRec))
  (if (null joinAdj)
    nil
    (progn
      (setq tail (DEGDC--ortho-join-pts fromPt (car joinAdj) (cadr joinAdj)))
      (if (or (null bb) (null tail) (= (length tail) 0))
        tail
        (progn
          (if (DEGDC--tail-hit-bbox-p fromPt tail bb)
            (progn
              (setq joinAdj (DEGDC--adjust-join-for-bbox fromPt joinAdj (degw-bbox-expand bb gap)))
              (setq tail (DEGDC--ortho-join-pts fromPt (car joinAdj) (cadr joinAdj)))
            )
          )
          (if (not (DEGDC--tail-hit-bbox-p fromPt tail bb))
            tail
            (progn
              (setq firstPt (car tail))
              (if (not (DEGDC--seg-hit-bbox-p fromPt firstPt bb))
                nil
                (progn
                  (setq uTan (DEGDC--curve-unit-tangent (cadr joinAdj) (car joinAdj)))
                  (if (null uTan)
                    tail
                    (progn
                      (setq uPerp (list (- (cadr uTan)) (car uTan) 0.0))
                      (setq ctr (degw-bbox-center bb))
                      (setq d (DEGDC--dot2 (list (- (car fromPt) (car ctr)) (- (cadr fromPt) (cadr ctr)) 0.0) uPerp))
                      (setq need (- (+ (DEGDC--bbox-support bb uPerp) gap) (abs d)))
                      (if (<= need 0.0) (setq need gap))
                      (setq signs (if (>= d 0.0) (list 1.0 -1.0) (list -1.0 1.0)))
                      (setq scales (list 1.0 1.5 2.0 3.0 4.0 6.0))
                      (foreach sc scales
                        (foreach s signs
                          (if (null chosen)
                            (progn
                              (setq esc (DEGDC--pt+scale fromPt uPerp (* s need sc)))
                              (setq tail2 (DEGDC--ortho-join-pts esc (car joinAdj) (cadr joinAdj)))
                              (if (and tail2 (> (length tail2) 0)
                                       (not (DEGDC--seg-hit-bbox-p fromPt esc bb))
                                       (not (DEGDC--tail-hit-bbox-p esc tail2 bb)))
                                (setq chosen (append (list esc) tail2))
                              )
                            )
                          )
                        )
                      )
                      (if chosen chosen tail)
                    )
                  )
                )
              )
            )
          )
        )
      )
    )
  )
)

(defun DEGDC--build-link-pts (blkEnt ents / blkObj ins rot downAng pDown joinRec tailPts downLen)
  (if (and blkEnt (entget blkEnt))
    (progn
      (setq blkObj (vlax-ename->vla-object blkEnt))
      (setq ins (deg-get-inspt blkObj))
      (if ins
        (progn
          (setq downLen (DEG:CFG-NUM-OR 'DC_DOWN_LEN 200.0))
          (if (<= downLen 0.0) (setq downLen 200.0))
          (setq rot     (DEGDC--block-rotation blkEnt))
          (setq downAng (- rot (/ pi 2.0)))
          (setq pDown   (DEGDC--offset-point ins downAng downLen))
          (setq joinRec (DEGDC--closest-on-ents pDown ents))
          (if joinRec
            (progn
              (setq tailPts (g365_clean_pts (DEGDC--ortho-join-pts pDown (car joinRec) (cadr joinRec))))
              (if tailPts
                (g365_clean_pts (append (list ins pDown) tailPts))
                nil
              )
            )
            nil
          )
        )
        nil
      )
    )
    nil
  )
)
(defun DEGDC--cross2 (a b)
  (- (* (car a) (cadr b)) (* (cadr a) (car b)))
)

(defun DEGDC--clamp (v lo hi)
  (max lo (min hi v))
)

(defun DEGDC--acos (x / xc y)
  (setq xc (DEGDC--clamp x -1.0 1.0))
  (cond
    ((>= xc 1.0) 0.0)
    ((<= xc -1.0) pi)
    (T
      (setq y (sqrt (max 0.0 (- 1.0 (* xc xc)))))
      (atan y xc)
    )
  )
)

(defun DEGDC--tan (x / c)
  (setq c (cos x))
  (if (< (abs c) 1e-12)
    nil
    (/ (sin x) c)
  )
)

(defun DEGDC--unit-from-to (a b / dx dy len)
  (setq dx (- (car b) (car a)))
  (setq dy (- (cadr b) (cadr a)))
  (setq len (sqrt (+ (* dx dx) (* dy dy))))
  (if (> len 1e-9)
    (list (/ dx len) (/ dy len) 0.0)
    nil
  )
)

(defun DEGDC--closest-point-on-seg (a b p / pA pB pP ax ay bx by px py vx vy wx wy vv t)
  (setq pA (deg-pt3 a))
  (setq pB (deg-pt3 b))
  (setq pP (deg-pt3 p))
  (if (or (null pA) (null pB) (null pP))
    nil
    (progn
      (setq ax (car pA) ay (cadr pA))
      (setq bx (car pB) by (cadr pB))
      (setq px (car pP) py (cadr pP))
      (setq vx (- bx ax) vy (- by ay))
      (setq wx (- px ax) wy (- py ay))
      (setq vv (+ (* vx vx) (* vy vy)))
      (if (<= vv 1e-12)
        pA
        (progn
          (setq t (/ (+ (* wx vx) (* wy vy)) vv))
          (if (< t 0.0) (setq t 0.0))
          (if (> t 1.0) (setq t 1.0))
          (list
            (+ ax (* t vx))
            (+ ay (* t vy))
            (if (caddr pP) (caddr pP) 0.0)
          )
        )
      )
    )
  )
)

(defun DEGDC--segment-unit-at-point (ent pt / pts basePt bestU bestD i p1 p2 cp d)
  (setq pts (g365_get_pts ent))
  (setq basePt (deg-pt3 pt))
  (if (and basePt pts (> (length pts) 1))
    (progn
      (setq bestU nil bestD nil i 0)
      (while (< i (1- (length pts)))
        (setq p1 (deg-pt3 (nth i pts)))
        (setq p2 (deg-pt3 (nth (1+ i) pts)))
        (if (and p1 p2 (> (distance p1 p2) 1e-9))
          (progn
            (setq cp (DEGDC--closest-point-on-seg p1 p2 basePt))
            (if cp
              (progn
                (setq d (distance basePt cp))
                (if (or (null bestD) (< d bestD))
                  (progn
                    (setq bestD d)
                    (setq bestU (DEGDC--unit-from-to p1 p2))
                  )
                )
              )
            )
          )
        )
        (setq i (1+ i))
      )
      bestU
    )
    nil
  )
)

(defun DEGDC--zeros (n / out)
  (setq out nil)
  (while (> n 0)
    (setq out (cons 0.0 out))
    (setq n (1- n))
  )
  out
)

(defun DEGDC--set-nth (lst idx val / out i)
  (setq out nil i 0)
  (foreach x lst
    (setq out (cons (if (= i idx) val x) out))
    (setq i (1+ i))
  )
  (reverse out)
)

(defun DEGDC--entmake-open-poly-bulges (lay pts buls / data i pt b)
  (if (and pts (> (length pts) 1))
    (progn
      (setq data (list
        (cons 0 "LWPOLYLINE")
        (cons 100 "AcDbEntity")
        (cons 8 lay)
        (cons 100 "AcDbPolyline")
        (cons 90 (length pts))
        (cons 70 0)
        (cons 38 0.0)
        (cons 43 0.0)
      ))
      (setq i 0)
      (while (< i (length pts))
        (setq pt (nth i pts))
        (setq data (append data (list (cons 10 (list (car pt) (cadr pt))))))
        (setq b (if (and buls (< i (length buls))) (nth i buls) 0.0))
        (if (and b (/= b 0.0))
          (setq data (append data (list (cons 42 b))))
        )
        (setq i (1+ i))
      )
      (entmakex data)
    )
    nil
  )
)

(defun DEGDC--fillet-last-corner-data (pts rad / n prev corner next u1 u2 len1 len2 dot ang trim maxTrim pA pB prefix outPts buls bulge i bulIdx)
  (setq pts (g365_clean_pts pts))
  (setq n (length pts))
  (if (or (null pts) (< n 4) (null rad) (<= rad 1e-9))
    (list pts nil)
    (progn
      (setq prev   (nth (- n 3) pts))
      (setq corner (nth (- n 2) pts))
      (setq next   (nth (- n 1) pts))
      (setq u1 (DEGDC--unit-from-to prev corner))
      (setq u2 (DEGDC--unit-from-to corner next))
      (if (or (null u1) (null u2))
        (list pts nil)
        (progn
          (setq len1 (distance prev corner))
          (setq len2 (distance corner next))
          (setq dot (DEGDC--clamp (DEGDC--dot2 u1 u2) -1.0 1.0))
          (setq ang (DEGDC--acos dot))
          (if (or (<= ang 1e-6) (>= ang (- pi 1e-6)))
            (list pts nil)
            (progn
              (setq trim (* rad (DEGDC--tan (/ ang 2.0))))
              (setq maxTrim (- (min len1 len2) 1e-6))
              (if (or (null trim) (> trim maxTrim)) (setq trim maxTrim))
              (if (<= trim 1e-6)
                (list pts nil)
                (progn
                  (setq pA (DEGDC--pt+scale corner u1 (- trim)))
                  (setq pB (DEGDC--pt+scale corner u2 trim))
                  (setq prefix nil)
                  (setq i 0)
                  (while (<= i (- n 3))
                    (setq prefix (append prefix (list (nth i pts))))
                    (setq i (1+ i))
                  )
                  (if (< (distance pB next) 1e-6)
                    (setq outPts (append prefix (list pA next)))
                    (setq outPts (append prefix (list pA pB next)))
                  )
                  (setq outPts (g365_clean_pts outPts))
                  (setq buls (DEGDC--zeros (length outPts)))
                  (setq bulge (* (if (< (DEGDC--cross2 u1 u2) 0.0) -1.0 1.0) (DEGDC--tan (/ ang 4.0))))
                  (setq bulIdx (length prefix))
                  (if (and (>= bulIdx 0) (< bulIdx (length buls)))
                    (setq buls (DEGDC--set-nth buls bulIdx bulge))
                  )
                  (list outPts buls)
                )
              )
            )
          )
        )
      )
    )
  )
)
(defun DEGDC--draw-link (mainEnt pts / lay rad filletData pts2 buls newEnt)
  (setq lay (getvar "CLAYER"))
  (setq rad (DEG:CFG-NUM-OR 'DC_FILLET_R 10.0))
  (if (and pts (> (length pts) 1))
    (progn
      (setq filletData (vl-catch-all-apply 'DEGDC--fillet-last-corner-data (list pts rad)))
      (if (vl-catch-all-error-p filletData)
        (setq newEnt (g365_entmake_open_poly lay pts))
        (progn
          (setq pts2 (car filletData))
          (setq buls (cadr filletData))
          (if (and buls pts2 (> (length pts2) 1))
            (progn
              (setq newEnt (vl-catch-all-apply 'DEGDC--entmake-open-poly-bulges (list lay pts2 buls)))
              (if (vl-catch-all-error-p newEnt)
                (setq newEnt nil)
              )
            )
          )
          (if (null newEnt)
            (setq newEnt (g365_entmake_open_poly lay pts))
          )
        )
      )
      newEnt
    )
    nil
  )
)

(defun DC_ORIG (/ sel mainEnt found ssSel ssBlk i blkEnt pts newEnt cnt)
  (vl-load-com)
  (setq sel (entsel "\nDC: Polyline sec (bagli hatlari bul): "))
  (if (null sel)
    (princ "\nSecim yok.")
    (progn
      (setq mainEnt (car sel))
      (setq *DEGDC_PICKPT* (cadr sel))
      (if (not (wcmatch (cdr (assoc 0 (entget mainEnt))) "LWPOLYLINE,POLYLINE,LINE"))
        (princ "\nGecerli bir polyline/line sec.")
        (progn
          (setq found (DEGDC--collect-connected mainEnt))
          (if (and found (> (length found) 0))
            (progn
              (setq ssSel (g415_ss_from_list found))
              (sssetfirst nil ssSel)
              (princ (strcat "\nDC: " (itoa (DEG:SS-LEN ssSel)) " obje secildi."))
              (prompt "\nDC: Block'lari sec (INSERT): ")
              (setq ssBlk (ssget '((0 . "INSERT"))))
              (if (null ssBlk)
                (princ "\nBlock secimi yok.")
                (progn
                  (setq i 0 cnt 0)
                  (while (< i (sslength ssBlk))
                    (setq blkEnt (ssname ssBlk i))
                    (setq pts (vl-catch-all-apply 'DEGDC--build-link-pts (list blkEnt found)))
                    (if (vl-catch-all-error-p pts)
                      (setq pts nil)
                    )
                    (if pts
                      (progn
                        (setq newEnt (vl-catch-all-apply 'DEGDC--draw-link (list mainEnt pts)))
                        (if (vl-catch-all-error-p newEnt)
                          (setq newEnt nil)
                        )
                        (if newEnt
                          (setq cnt (1+ cnt))
                        )
                      )
                    )
                    (setq i (1+ i))
                  )
                  (princ (strcat "\nDC: " (itoa cnt) " baglanti cizildi."))
                )
              )
            )
            (progn
              (sssetfirst nil nil)
              (princ "\nDC: Bagli hat bulunamadi.")
            )
          )
        )
      )
    )
  )
  (setq *DEGDC_PICKPT* nil)
  (princ)
)

(defun c:DC ()
  (if (KC:InitLicense)
    (DC_ORIG)
    (KC:Blocked)
  )
)
(defun DEG:UNDO-GROUP-BEGIN (/ app doc res)
  (vl-load-com)
  (setq app (vl-catch-all-apply 'vlax-get-acad-object '()))
  (if (not (vl-catch-all-error-p app))
    (setq doc (vl-catch-all-apply 'vla-get-ActiveDocument (list app)))
  )
  (if (and doc (not (vl-catch-all-error-p doc)))
    (setq res (vl-catch-all-apply 'vla-StartUndoMark (list doc)))
  )
  (if (and doc (not (vl-catch-all-error-p doc))
           (not (vl-catch-all-error-p res)))
    (list 'VLA doc)
    (progn
      (setq res (vl-catch-all-apply 'vl-cmdf (list "_.UNDO" "_Begin")))
      (if (vl-catch-all-error-p res) nil (list 'CMD nil))
    )
  )
)

(defun DEG:UNDO-GROUP-END (token)
  (cond
    ((and token (= (car token) 'VLA) (cadr token))
      (vl-catch-all-apply 'vla-EndUndoMark (list (cadr token))))
    ((and token (= (car token) 'CMD))
      (vl-catch-all-apply 'vl-cmdf (list "_.UNDO" "_End")))
  )
  nil
)

;; Ana hatta dik bir sirada bulunan yakin blocklar, dogrudan ana hatta
;; baglandiklarinda ayni agzi paylasip ust uste binebilir. Bu ozel durumda
;; ana hatta temas eden ve block sirasinin 40 cm gerisinden gecen bir alt dal
;; olusturulur. Mevcut DD/DZ cizicisi blocklari bu dal uzerinden ayri ayri
;; baglar; diger blocklar normal ana-hat akisini kullanmaya devam eder.
(defun DEGZ--selected-block-groups (ss nearLim / cell cells parents data i blk ip key cx cy ix iy rec item blk2 ip2)
  (setq cell (max nearLim 1e-6)
        cells '()
        parents '()
        data '())
  (if (and ss (= (type ss) 'PICKSET))
    (progn
      (setq i 0)
      (while (< i (sslength ss))
        (setq blk (ssname ss i))
        (if (and blk (entget blk) (not (DEGZ--skip-block-p blk)))
          (progn
            (setq ip (DEGZ--pt2d (cdr (assoc 10 (entget blk))))
                  parents (DEGZ--uf-init parents blk)
                  data (append data (list (list blk ip)))
                  key (DEGZ--cellkey ip cell)
                  cx (car key)
                  cy (cadr key)
                  ix -1)
            (while (<= ix 1)
              (setq iy -1)
              (while (<= iy 1)
                (setq rec (assoc (list (+ cx ix) (+ cy iy)) cells))
                (if rec
                  (foreach item (cdr rec)
                    (setq blk2 (car item)
                          ip2 (cadr item))
                    (if (and blk2 ip2 (<= (DEGZ--safe-distance ip ip2) nearLim))
                      (setq parents (DEGZ--uf-union parents blk blk2))
                    )
                  )
                )
                (setq iy (1+ iy))
              )
              (setq ix (1+ ix))
            )
            (setq cells (DEGZ--cells-put cells (list cx cy) (list blk ip)))
          )
        )
        (setq i (1+ i))
      )
    )
  )
  (DEGZ--groups-build parents data)
)

(defun DEGZ--row-axis-from-records (recs / bestD bestA bestB r1 r2 p1 p2 d)
  (setq bestD 0.0)
  (foreach r1 recs
    (setq p1 (DEGZ--pt2d (cadr r1)))
    (foreach r2 recs
      (setq p2 (DEGZ--pt2d (cadr r2))
            d (DEGZ--safe-distance p1 p2))
      (if (> d bestD)
        (setq bestD d
              bestA p1
              bestB p2))))
  (if (> bestD 1e-6)
    (DEGZ--canonical-vector
      (- (car bestB) (car bestA))
      (- (cadr bestB) (cadr bestA)))
    nil)
)

(defun DEGZ--compatible-parent-record
  (mainCrv avg rowAxis / e pts ed closed n lim i a b segLen segAxis dotAbs hit d2 bestD bestPt bestTan)
  ;; En yakin herhangi bir parcayi degil, block sirasina dik olan en yakin
  ;; ana/cocuk hat parcasini ebeveyn sec.
  (setq e (DEGZ--ename mainCrv)
        pts (if e (DEGZ--get-lwpts e))
        ed (if e (entget e))
        closed (if ed (cdr (assoc 70 ed)) 0))
  (if (null closed) (setq closed 0))
  (if (and pts rowAxis (>= (length pts) 2))
    (progn
      (setq n (length pts)
            lim (if (/= (logand closed 1) 0) n (1- n))
            i 0
            bestD 1e99)
      (while (< i lim)
        (setq a (DEGZ--pt2d (nth i pts))
              b (DEGZ--pt2d (nth (if (= i (1- n)) 0 (1+ i)) pts))
              segLen (DEGZ--safe-distance a b))
        (if (> segLen 1e-6)
          (progn
            (setq segAxis (DEGZ--canonical-vector
                            (- (car b) (car a))
                            (- (cadr b) (cadr a)))
                  dotAbs (abs (+ (* (car segAxis) (car rowAxis))
                                 (* (cadr segAxis) (cadr rowAxis)))))
            (if (< dotAbs 0.25)
              (progn
                (setq hit (DEGZ--closest-on-seg a b avg)
                      d2 (cadr hit))
                (if (< d2 bestD)
                  (setq bestD d2
                        bestPt (car hit)
                        bestTan segAxis))))))
        (setq i (1+ i)))
      (if bestPt
        (list bestPt bestTan (DEGZ--safe-distance avg bestPt))))
  )
)

(defun DEGZ--perp-row-branch-points (mainCrv recs alignTol dropDist extend maxConnectDist / count sx sy avg cp tan tx ty nx ny minT maxT minN maxN r ip vx vy qT qN rowSide rowSign downSign target attach ux uy along maxAlong valid endDist connectDist rowAxis parentRec)
  (if (< (length recs) 2)
    nil
    (progn
      (setq count 0 sx 0.0 sy 0.0)
      (foreach r recs
        (setq ip (DEGZ--pt2d (cadr r))
              sx (+ sx (car ip))
              sy (+ sy (cadr ip))
              count (1+ count))
      )
      (setq avg (list (/ sx count) (/ sy count))
            rowAxis (DEGZ--row-axis-from-records recs)
            parentRec (DEGZ--compatible-parent-record mainCrv avg rowAxis)
            cp (if parentRec
                 (car parentRec)
                 (DEGZ--pt2d (deg-safe-closest-point mainCrv avg)))
            connectDist (if parentRec
                          (caddr parentRec)
                          (DEGZ--safe-distance avg cp))
            tan (if parentRec
                  (cadr parentRec)
                  (DEGZ--canonical-tangent-at mainCrv cp))
            tx (car tan)
            ty (cadr tan)
            nx (- ty)
            ny tx
            minT nil maxT nil minN nil maxN nil)
      (foreach r recs
        (setq ip (DEGZ--pt2d (cadr r))
              vx (- (car ip) (car avg))
              vy (- (cadr ip) (cadr avg))
              qT (+ (* vx tx) (* vy ty))
              qN (+ (* vx nx) (* vy ny)))
        (if (or (null minT) (< qT minT)) (setq minT qT))
        (if (or (null maxT) (> qT maxT)) (setq maxT qT))
        (if (or (null minN) (< qN minN)) (setq minN qN))
        (if (or (null maxN) (> qN maxN)) (setq maxN qN))
      )
      (setq rowSide
        (+ (* (- (car avg) (car cp)) nx)
           (* (- (cadr avg) (cadr cp)) ny)))
      (if (or (> (- maxT minT) alignTol)
              (<= (- maxN minN) 1e-6)
              (<= (abs rowSide) alignTol)
              (and (numberp maxConnectDist)
                   (> maxConnectDist 0.0)
                   (> connectDist maxConnectDist)))
        nil
        (progn
          ;; Kanonik tegetin WCS'te asagi bakan yonunu sec. Yatay tegette
          ;; ayni geometrik kural, tegetin eksi yonunu kullanir.
          (setq downSign
            (cond
              ((> ty 1e-8) -1.0)
              ((< ty -1e-8) 1.0)
              (T -1.0)))
          (setq target
            (list (+ (car avg) (* tx downSign dropDist))
                  (+ (cadr avg) (* ty downSign dropDist)))
                attach (DEGZ--pt2d (deg-safe-closest-point mainCrv target))
                rowSign (if (>= rowSide 0.0) 1.0 -1.0)
                ux (* nx rowSign)
                uy (* ny rowSign)
                maxAlong 0.0
                valid T)
          (foreach r recs
            (setq ip (DEGZ--pt2d (cadr r))
                  along (+ (* (- (car ip) (car attach)) ux)
                           (* (- (cadr ip) (cadr attach)) uy)))
            (if (< along (- alignTol)) (setq valid nil))
            (if (> along maxAlong) (setq maxAlong along))
          )
          (if (not valid)
            nil
            (progn
              (setq endDist (+ maxAlong extend))
              (list attach
                    (list (+ (car attach) (* ux endDist))
                          (+ (cadr attach) (* uy endDist))))
            )
          )
        )
      )
    )
  )
)

(defun DEGZ--selected-aligned-groups (mainCrv ss alignTol dropDist extend maxConnectDist / data rows i blk ip rec best bestDist g candidate branchPts d r newRows)
  ;; Bu ozel 40 cm dal gruplamasinda bloklarin birbirine uzakligi sinir degildir.
  ;; Bir blok birden fazla hizaya uyarsa yalnizca en yakin mevcut hizaya eklenir.
  (setq data '()
        rows '())
  (if (and ss (= (type ss) 'PICKSET))
    (progn
      (setq i 0)
      (while (< i (sslength ss))
        (setq blk (ssname ss i))
        (if (and blk (entget blk) (not (DEGZ--skip-block-p blk)))
          (progn
            (setq ip (DEGZ--pt2d (cdr (assoc 10 (entget blk)))))
            (setq data (append data (list (list blk ip))))
          )
        )
        (setq i (1+ i))
      )
    )
  )
  (foreach rec data
    (setq best nil
          bestDist nil)
    (foreach g rows
      (setq candidate (append (cdr g) (list rec))
            branchPts (DEGZ--perp-row-branch-points
                        mainCrv candidate alignTol dropDist extend maxConnectDist))
      (if branchPts
        (progn
          (setq d nil)
          (foreach r (cdr g)
            (if (or (null d)
                    (< (DEGZ--safe-distance (cadr rec) (cadr r)) d))
              (setq d (DEGZ--safe-distance (cadr rec) (cadr r)))
            )
          )
          (if (or (null bestDist) (< d bestDist))
            (setq best g
                  bestDist d)
          )
        )
      )
    )
    (if best
      (progn
        (setq newRows '())
        (foreach g rows
          (if (eq g best)
            (setq newRows
              (append newRows
                (list (cons (car g) (append (cdr g) (list rec))))))
            (setq newRows (append newRows (list g)))
          )
        )
        (setq rows newRows)
      )
      (setq rows (append rows (list (list (car rec) rec))))
    )
  )
  rows
)

(defun DEGZ--records-average (recs / count sx sy rec ip)
  (setq count 0
        sx 0.0
        sy 0.0)
  (foreach rec recs
    (setq ip (DEGZ--pt2d (cadr rec))
          sx (+ sx (car ip))
          sy (+ sy (cadr ip))
          count (1+ count)))
  (if (> count 0)
    (list (/ sx count) (/ sy count))
    nil)
)

(defun DEGZ--axis-level (pt axis)
  (+ (* (car pt) (car axis))
     (* (cadr pt) (cadr axis)))
)

(defun DEGZ--row-level-match-count (recsA recsB axis tol / count recA recB levelA levelB matched)
  (setq count 0)
  (foreach recA recsA
    (setq levelA (DEGZ--axis-level (DEGZ--pt2d (cadr recA)) axis)
          matched nil)
    (foreach recB recsB
      (setq levelB (DEGZ--axis-level (DEGZ--pt2d (cadr recB)) axis))
      (if (<= (abs (- levelA levelB)) tol)
        (setq matched T)))
    (if matched (setq count (1+ count))))
  count
)

(defun DEGZ--records-by-axis-level (recs axis tol / parents i j recA recB levelA levelB groups)
  ;; Ortak omurgadaki blocklari ayni kot/seviye satirlarina ayir.
  (setq parents '())
  (foreach recA recs
    (setq parents (DEGZ--uf-init parents (car recA))))
  (setq i 0)
  (while (< i (length recs))
    (setq recA (nth i recs)
          levelA (DEGZ--axis-level (DEGZ--pt2d (cadr recA)) axis)
          j (1+ i))
    (while (< j (length recs))
      (setq recB (nth j recs)
            levelB (DEGZ--axis-level (DEGZ--pt2d (cadr recB)) axis))
      (if (<= (abs (- levelA levelB)) tol)
        (setq parents (DEGZ--uf-union parents (car recA) (car recB))))
      (setq j (1+ j)))
    (setq i (1+ i)))
  (setq groups (DEGZ--groups-build parents recs))
  (mapcar (function (lambda (group) (cdr group))) groups)
)

(defun DEGZ--extend-branch-for-records (branchPts recs extend / attach far dir originalLen maxAlong rec ip along)
  (setq attach (DEGZ--pt2d (car branchPts))
        far (DEGZ--pt2d (cadr branchPts))
        dir (DEGZ--unit (- (car far) (car attach))
                        (- (cadr far) (cadr attach)))
        originalLen (DEGZ--safe-distance attach far)
        maxAlong 0.0)
  (foreach rec recs
    (setq ip (DEGZ--pt2d (cadr rec))
          along (+ (* (- (car ip) (car attach)) (car dir))
                   (* (- (cadr ip) (cadr attach)) (cadr dir))))
    (if (> along maxAlong) (setq maxAlong along)))
  (setq maxAlong (max originalLen (+ maxAlong extend)))
  (list attach
        (list (+ (car attach) (* (car dir) maxAlong))
              (+ (cadr attach) (* (cadr dir) maxAlong))))
)

(defun DEGZ--insert-child-detour (mainCrv branchPts short / attachBase farCenter dMid maxDist distPair mouthA mouthB deltaA deltaB farA farB res)
  ;; Ortak omurganin bir kenarinda agiz acip seviyeye cift hatli cocuk dal ekle.
  (setq mainCrv (DEGZ--ename mainCrv)
        attachBase (DEGZ--pt2d (car branchPts))
        farCenter (DEGZ--pt2d (cadr branchPts))
        dMid (vl-catch-all-apply
               'vlax-curve-getDistAtPoint
               (list mainCrv (DEGZ--pt3d attachBase))))
  (if (vl-catch-all-error-p dMid)
    nil
    (progn
      (setq dMid (DEGZ--corner-mouth-center-dist
                   mainCrv attachBase farCenter dMid (* 0.5 short))
            maxDist (DEGZ--curve-total mainCrv)
            distPair (DEGZ--distpair10 dMid 1.0 maxDist (* 0.5 short))
            mouthA (DEGZ--pt2d
                     (vlax-curve-getPointAtDist mainCrv (car distPair)))
            mouthB (DEGZ--pt2d
                     (vlax-curve-getPointAtDist mainCrv (cadr distPair)))
            deltaA (list (- (car mouthA) (car attachBase))
                         (- (cadr mouthA) (cadr attachBase)))
            deltaB (list (- (car mouthB) (car attachBase))
                         (- (cadr mouthB) (cadr attachBase)))
            farA (list (+ (car farCenter) (car deltaA))
                       (+ (cadr farCenter) (cadr deltaA)))
            farB (list (+ (car farCenter) (car deltaB))
                       (+ (cadr farCenter) (cadr deltaB)))
            res (vl-catch-all-apply
                  'DEGZ--insert-detour
                  (list mainCrv mouthA mouthB (list farA farB))))
      (if (and (not (vl-catch-all-error-p res))
               res
               (entget (DEGZ--ename res)))
        (DEGZ--ename res)
        nil)))
)

(defun DEGZ--aligned-group-descriptor
  (mainCrv g alignTol dropDist extend maxConnectDist / recs branchPts axis avg perp trans branchDir)
  (setq recs (cdr g)
        branchPts (DEGZ--perp-row-branch-points
                    mainCrv recs alignTol dropDist extend maxConnectDist)
        axis (DEGZ--row-axis-from-records recs)
        avg (DEGZ--records-average recs))
  (if (and branchPts axis avg)
    (progn
      (setq perp (DEGZ--canonical-vector (- (cadr axis)) (car axis))
            trans (DEGZ--axis-level avg perp)
            branchDir (DEGZ--unit
                        (- (car (cadr branchPts)) (car (car branchPts)))
                        (- (cadr (cadr branchPts)) (cadr (car branchPts)))))
      (list g recs branchPts axis avg trans branchDir))
    nil)
)

(defun DEGZ--aligned-descriptors-same-bank-p
  (descA descB alignTol dropDist extend / axisA axisB dirA dirB dotAxis dotDir transGap gapLimit matches)
  (setq axisA (nth 3 descA)
        axisB (nth 3 descB)
        dirA (nth 6 descA)
        dirB (nth 6 descB)
        dotAxis (abs (+ (* (car axisA) (car axisB))
                        (* (cadr axisA) (cadr axisB))))
        dotDir (+ (* (car dirA) (car dirB))
                  (* (cadr dirA) (cadr dirB)))
        transGap (abs (- (nth 5 descA) (nth 5 descB)))
        gapLimit (max (* 2.0 dropDist) (* 2.0 extend))
        matches (DEGZ--row-level-match-count
                  (nth 1 descA) (nth 1 descB) axisA alignTol))
  ;; En az iki ortak seviye, iki komsu block sutununun ayni banka ait
  ;; oldugunu gosterir. Tek ortak seviye tesadufi kesisme sayilir.
  (and (>= dotAxis 0.98)
       (>= dotDir 0.90)
       (<= transGap gapLimit)
       (>= matches 2))
)

(defun DEGZ--descriptor-fits-column-bank-p
  (candidate hostDescs alignTol / hostAxis candAxis dotAxis hostPerp rec recTrans hostDesc d bestD bestTrans used allMatch)
  ;; Greedy secimde yatay bir cift ayri grup kalabilir. Bu ciftin her blogu
  ;; birlesmis bankanin farkli bir dikey kolonuna oturuyorsa ayni seviyedir.
  (setq hostAxis (nth 3 (car hostDescs))
        candAxis (nth 3 candidate)
        dotAxis (abs (+ (* (car hostAxis) (car candAxis))
                        (* (cadr hostAxis) (cadr candAxis))))
        hostPerp (DEGZ--canonical-vector (- (cadr hostAxis)) (car hostAxis))
        used '()
        allMatch T)
  (if (or (>= dotAxis 0.25) (< (length (nth 1 candidate)) 2))
    nil
    (progn
      (foreach rec (nth 1 candidate)
        (setq recTrans (DEGZ--axis-level (DEGZ--pt2d (cadr rec)) hostPerp)
              bestD nil
              bestTrans nil)
        (foreach hostDesc hostDescs
          (setq d (abs (- recTrans (nth 5 hostDesc))))
          (if (or (null bestD) (< d bestD))
            (setq bestD d
                  bestTrans (nth 5 hostDesc))))
        (if (and bestD (<= bestD alignTol))
          (if (not (member bestTrans used))
            (setq used (cons bestTrans used)))
          (setq allMatch nil)))
      (and allMatch (>= (length used) 2))))
)

(defun DEGZ--descriptor-by-id (descs id / found desc)
  (foreach desc descs
    (if (equal (car (car desc)) id) (setq found desc)))
  found
)

(defun DEGZ--aligned-group-jobs
  (mainCrv groups alignTol dropDist extend maxConnectDist
   / descs g desc parents i j descA descB idA idB banks rep bank host other hostRep hostDescs candidate candidateId absorbMap owner newBanks newDescs pair extraDesc extraRecs jobs descList base axis allRecs branchPts rowGroups)
  (setq descs '()
        parents '())
  (foreach g groups
    (setq desc (DEGZ--aligned-group-descriptor
                 mainCrv g alignTol dropDist extend maxConnectDist))
    (if desc
      (progn
        (setq descs (append descs (list desc)))
        (setq parents (DEGZ--uf-init parents (car (car desc)))))))

  (setq i 0)
  (while (< i (length descs))
    (setq descA (nth i descs)
          idA (car (car descA))
          j (1+ i))
    (while (< j (length descs))
      (setq descB (nth j descs)
            idB (car (car descB)))
      (if (DEGZ--aligned-descriptors-same-bank-p
            descA descB alignTol dropDist extend)
        (setq parents (DEGZ--uf-union parents idA idB)))
      (setq j (1+ j)))
    (setq i (1+ i)))

  (setq banks '())
  (foreach desc descs
    (setq rep (DEGZ--uf-find parents (car (car desc)))
          bank (assoc rep banks))
    (if bank
      (setq banks
        (subst (cons rep (append (cdr bank) (list desc))) bank banks))
      (setq banks (append banks (list (list rep desc))))))

  ;; Ayni iki kolona oturan tek yatay sirayi bankanin yon tanimina katma.
  ;; Yalnizca block kayitlarini ekle; boylece WCS koordinat buyuklukleri
  ;; omurga referansini yatay gruba ceviremez.
  (setq absorbMap '())
  (foreach host banks
    (setq hostRep (car host)
          hostDescs (cdr host))
    (if (> (length hostDescs) 1)
      (foreach other banks
        (if (and (not (equal (car other) hostRep))
                 (= (length (cdr other)) 1))
          (progn
            (setq candidate (cadr other)
                  candidateId (car (car candidate)))
            (if (and (null (assoc candidateId absorbMap))
                     (DEGZ--descriptor-fits-column-bank-p
                       candidate hostDescs alignTol))
              (setq absorbMap
                (cons (cons candidateId hostRep) absorbMap))))))))

  (if absorbMap
    (progn
      (setq newBanks '())
      (foreach bank banks
        (setq rep (car bank)
              newDescs '())
        (foreach desc (cdr bank)
          (setq owner (assoc (car (car desc)) absorbMap))
          (if (null owner)
            (setq newDescs (append newDescs (list desc)))))
        (if newDescs
          (setq newBanks
            (append newBanks (list (cons rep newDescs))))))
      (setq banks newBanks)))

  (setq jobs '())
  (foreach bank banks
    (setq descList (cdr bank)
          base (car descList)
          allRecs '()
          extraRecs '())
    ;; Kanonik en dis sutunu ortak omurganin referansi yap.
    (foreach desc descList
      (setq allRecs (append allRecs (nth 1 desc)))
      (if (< (nth 5 desc) (nth 5 base)) (setq base desc)))
    (foreach pair absorbMap
      (if (equal (cdr pair) (car bank))
        (progn
          (setq extraDesc (DEGZ--descriptor-by-id descs (car pair)))
          (if extraDesc
            (setq extraRecs
              (append extraRecs (nth 1 extraDesc)))))))
    (setq allRecs (append allRecs extraRecs))
    (setq axis (nth 3 base)
          branchPts (DEGZ--extend-branch-for-records
                      (nth 2 base) allRecs extend)
          rowGroups (if (> (length descList) 1)
                      (DEGZ--records-by-axis-level allRecs axis alignTol)
                      (list allRecs)))
    (setq jobs
      (append jobs
        (list (list branchPts rowGroups allRecs (length descList))))))
  jobs
)

(defun DEGZ--canonical-vector (dx dy / unit tx ty)
  (setq unit (DEGZ--unit dx dy)
        tx (car unit)
        ty (cadr unit))
  (if (or (< tx -1e-10)
          (and (<= (abs tx) 1e-10) (< ty 0.0)))
    (setq tx (- tx)
          ty (- ty)))
  (list tx ty)
)

(defun DEGZ--corner-mouth-center-dist
  (crv attach farPt dMid half
   / total eps before after vb va branch lenB lenA straightDot scoreB scoreA center)
  ;; Agiz bir L kosesine denk gelirse iki ofset noktasi farkli segmentlere
  ;; dagilmasin. Cocuk dala daha dik olan ana-hat segmentini sec ve agzin
  ;; iki ucunu o segment uzerinde tut.
  (setq total (DEGZ--curve-total crv)
        eps (max 1e-3 (* 0.25 (DEG:PLAN-UNIT-SCALE)))
        before (DEGZ--pt2d
                 (vlax-curve-getPointAtDist crv (max 0.0 (- dMid eps))))
        after (DEGZ--pt2d
                (vlax-curve-getPointAtDist crv (min total (+ dMid eps))))
        lenB (DEGZ--safe-distance attach before)
        lenA (DEGZ--safe-distance attach after)
        vb (DEGZ--canonical-vector
             (- (car attach) (car before))
             (- (cadr attach) (cadr before)))
        va (DEGZ--canonical-vector
             (- (car after) (car attach))
             (- (cadr after) (cadr attach)))
        branch (DEGZ--canonical-vector
                 (- (car farPt) (car attach))
                 (- (cadr farPt) (cadr attach)))
        straightDot (abs (+ (* (car vb) (car va))
                            (* (cadr vb) (cadr va)))))
  (if (or (<= lenB 1e-9)
          (<= lenA 1e-9)
          (>= straightDot 0.98))
    dMid
    (progn
      (setq scoreB (abs (+ (* (car vb) (car branch))
                           (* (cadr vb) (cadr branch))))
            scoreA (abs (+ (* (car va) (car branch))
                           (* (cadr va) (cadr branch))))
            center (if (< scoreA scoreB)
                     (+ dMid half)
                     (- dMid half)))
      (DEGZ--clamp center half (max half (- total half)))
    )
  )
)

(defun DEGDD--mode-key (ddKey dfKey)
  (if (and (boundp '*DEG_DD_MODE*) (eq *DEG_DD_MODE* 'DF)) dfKey ddKey)
)

(defun DEGZ--opposite-side (side)
  (cond
    ((eq side 'BOTTOM) 'TOP)
    ((eq side 'TOP) 'BOTTOM)
    ((eq side 'LEFT) 'RIGHT)
    ((eq side 'RIGHT) 'LEFT)
    (T nil))
)

(defun DEGZ--ray-hit-for-side
  (crv origin side / pts ed closed count limit dir rayEnd i a b hit segHit along best bestD tol)
  (setq crv (DEGZ--ename crv)
        origin (DEGZ--pt2d origin)
        pts (if crv (DEGZ--get-lwpts crv) nil)
        ed (if crv (entget crv) nil)
        closed (if ed (cdr (assoc 70 ed)) 0)
        closed (if (and closed (/= (logand closed 1) 0)) 1 0)
        dir (cond
              ((eq side 'BOTTOM) '(0.0 -1.0))
              ((eq side 'TOP) '(0.0 1.0))
              ((eq side 'LEFT) '(-1.0 0.0))
              ((eq side 'RIGHT) '(1.0 0.0))
              (T nil))
        tol 1e-5)
  (if (and dir pts (> (length pts) 1))
    (progn
      (setq rayEnd (list (+ (car origin) (car dir))
                         (+ (cadr origin) (cadr dir)))
            count (length pts)
            limit (if (= closed 1) count (1- count))
            i 0)
      (while (< i limit)
        (setq a (DEGZ--pt2d (nth i pts))
              b (DEGZ--pt2d (nth (rem (1+ i) count) pts))
              hit (inters origin rayEnd a b nil))
        (if hit
          (progn
            (setq hit (DEGZ--pt2d hit)
                  segHit (DEGZ--closest-on-seg a b hit)
                  along (+ (* (- (car hit) (car origin)) (car dir))
                           (* (- (cadr hit) (cadr origin)) (cadr dir))))
            (if (and (> along tol)
                     (<= (cadr segHit) (* tol tol))
                     (or (null bestD) (< along bestD)))
              (setq best hit
                    bestD along))))
        (setq i (1+ i)))
      best))
)

(defun DEGZ--common-side-candidate (mainCrv recs side / out rec hit score ok)
  (setq out '()
        score 0.0
        ok T)
  (foreach rec recs
    (setq hit (DEGZ--ray-hit-for-side mainCrv (cadr rec) side))
    (if hit
      (progn
        (setq score (+ score (DEGZ--safe-distance (cadr rec) hit)))
        (setq out (append out (list (list (car rec) side hit)))))
      (setq ok nil)))
  (if ok (list score out) nil)
)

(defun DEGZ--pre-common-target-map
  (mainCrv ss mode / nearKey nearLim groups g recs minX maxX minY maxY rec ip spreadX spreadY avg cp fallback preferred other candA candB chosen out)
  (setq nearKey (cond
                  ((eq mode 'DD) 'DD_BLOK_YAKINLIK)
                  ((eq mode 'DF) 'DF_BLOK_YAKINLIK)
                  (T 'DZ_BLOK_YAKINLIK))
        nearLim (DEG:CFG-DDDZ-NUM-OR nearKey 100.0))
  (if (<= nearLim 0.0)
    (setq nearLim (* 100.0 (DEG:PLAN-UNIT-SCALE))))
  (setq groups (DEGZ--selected-block-groups ss nearLim)
        out '())
  (foreach g groups
    (setq recs (cdr g))
    (if (> (length recs) 1)
      (progn
        (setq minX nil maxX nil minY nil maxY nil)
        (foreach rec recs
          (setq ip (DEGZ--pt2d (cadr rec)))
          (if (or (null minX) (< (car ip) minX)) (setq minX (car ip)))
          (if (or (null maxX) (> (car ip) maxX)) (setq maxX (car ip)))
          (if (or (null minY) (< (cadr ip) minY)) (setq minY (cadr ip)))
          (if (or (null maxY) (> (cadr ip) maxY)) (setq maxY (cadr ip))))
        (setq spreadX (- maxX minX)
              spreadY (- maxY minY)
              avg (DEGZ--records-average recs)
              cp (DEGZ--pt2d (deg-safe-closest-point mainCrv avg))
              fallback (DEGZ--side-from-group-alignment cp avg recs)
              preferred (DEGZ--normal-group-no-cross-side cp avg recs fallback))
        ;; Ayni hizada bloklarda yalniz dizilim eksenine dik iki ortak yonu dene.
        (if (>= spreadX spreadY)
          (if (not (member preferred '(TOP BOTTOM))) (setq preferred 'BOTTOM))
          (if (not (member preferred '(LEFT RIGHT))) (setq preferred 'LEFT)))
        (setq other (DEGZ--opposite-side preferred)
              candA (DEGZ--common-side-candidate mainCrv recs preferred)
              candB (DEGZ--common-side-candidate mainCrv recs other)
              chosen (cond
                       ((and candA candB) (if (<= (car candA) (car candB)) candA candB))
                       (candA candA)
                       (candB candB)
                       (T nil)))
        (if chosen (setq out (append (cadr chosen) out))))))
  out
)

(defun DEGDF--clicked-segment (ent pick / e ed typ cp param endParam maxSeg seg p0 p1 props guide)
  (setq e (DEGZ--ename ent)
        ed (if e (entget e))
        typ (if ed (cdr (assoc 0 ed))))
  (if (not (member typ '("LWPOLYLINE" "POLYLINE")))
    nil
    (progn
      (setq cp (vl-catch-all-apply
                 'vlax-curve-getClosestPointTo
                 (list e (DEGZ--pt3d pick))))
      (if (vl-catch-all-error-p cp)
        nil
        (progn
          (setq param (vl-catch-all-apply
                        'vlax-curve-getParamAtPoint
                        (list e cp))
                endParam (vl-catch-all-apply
                           'vlax-curve-getEndParam
                           (list e)))
          (if (or (vl-catch-all-error-p param)
                  (vl-catch-all-error-p endParam)
                  (< endParam 1.0))
            nil
            (progn
              (setq maxSeg (1- (fix endParam))
                    seg (fix param))
              (if (< seg 0) (setq seg 0))
              (if (> seg maxSeg) (setq seg maxSeg))
              (setq p0 (vl-catch-all-apply
                         'vlax-curve-getPointAtParam
                         (list e seg))
                    p1 (vl-catch-all-apply
                         'vlax-curve-getPointAtParam
                         (list e (1+ seg))))
              (if (or (vl-catch-all-error-p p0)
                      (vl-catch-all-error-p p1)
                      (equal (DEGZ--pt2d p0) (DEGZ--pt2d p1) 1e-9))
                nil
                (progn
                  (setq props (DEGZ--safe-props e)
                        guide (DEGZ--entmakex-lwpoly
                                (list (DEGZ--pt2d p0) (DEGZ--pt2d p1))
                                props 0))
                  guide
                )
              )
            )
          )
        )
      )
    )
  )
)

(defun DEGZ--route-has-block-point-p (points ip / found)
  ;; Every completed block detour contains its insertion point as a vertex.
  (setq found nil)
  (while (and points (not found))
    (if (equal (DEGZ--pt2d (car points)) (DEGZ--pt2d ip) 1e-6)
      (setq found T))
    (setq points (cdr points)))
  found)

(defun DEGZ--preprocess-perp-row-groups (mainCrv ss mode / shortKey mouthKey short mouth alignTol dropDist extend childMaxDist groups jobs job recs branchPts rowGroups rowRecs rowItem allRecs bankCount groupSS r applyFn applyRes applyOk handled remaining i ent guideCrv detectPts detectProps detectClosed detectCrv detectOwned attachBase farCenter dMid maxDist distPair mouthA mouthB deltaA deltaB farA farB mainRes rowBranchPts rowMainRes rowGuideCrv readyRows commonSS commonMap finalPoints *DEGZ_ROW_GUIDE*)
  (setq mainCrv (DEGZ--ename mainCrv))
  (setq guideCrv (if (and (eq mode 'DF)
                          (boundp '*DEG_DF_GUIDE*)
                          *DEG_DF_GUIDE*
                          (entget (DEGZ--ename *DEG_DF_GUIDE*)))
                   (DEGZ--ename *DEG_DF_GUIDE*)
                   mainCrv)
        shortKey (cond ((eq mode 'DD) 'DD_OFFSET)
                       ((eq mode 'DF) 'DF_OFFSET)
                       (T 'DZ_OFFSET))
        mouthKey (cond ((eq mode 'DD) 'DD_AGIZ_ARAMA)
                       ((eq mode 'DF) 'DF_AGIZ_ARAMA)
                       (T 'DZ_AGIZ_ARAMA))
        short    (DEG:CFG-DDDZ-NUM-OR shortKey 10.0)
        mouth    (DEG:CFG-DDDZ-NUM-OR mouthKey 20.0)
        dropDist (* 40.0 (DEG:PLAN-UNIT-SCALE)))
  (if (<= short 0.0) (setq short (* 10.0 (DEG:PLAN-UNIT-SCALE))))
  (if (<= mouth 0.0) (setq mouth (* 20.0 (DEG:PLAN-UNIT-SCALE))))
  (setq childMaxDist (if (eq mode 'DZ)
                       (DEG:CFG-DDDZ-NUM-OR 'DZ_COCUK_HAT_MESAFE 750.0)
                       nil)
        alignTol (max (* 0.5 short) (* 0.5 (DEG:PLAN-UNIT-SCALE)))
        extend (+ mouth short)
        groups (DEGZ--selected-aligned-groups
                 guideCrv ss alignTol dropDist extend childMaxDist)
        applyFn (if (member mode '(DD DF)) 'DEGDD--APPLY 'DEGZ--APPLY)
        handled '())
  (setq *DEGZ_PRE_COMMON_TARGET_MAP*
    (append (DEGZ--pre-common-target-map guideCrv ss mode)
            (if (and (boundp '*DEGZ_PRE_COMMON_TARGET_MAP*)
                     *DEGZ_PRE_COMMON_TARGET_MAP*)
              *DEGZ_PRE_COMMON_TARGET_MAP*
              '())))

  ;; Keep one untouched detector curve. Each successful mouth operation replaces
  ;; mainCrv, while the remaining row tests must still use the original geometry.
  (setq detectPts (DEGZ--get-lwpts guideCrv)
        detectProps (DEGZ--safe-props guideCrv)
        detectClosed (cdr (assoc 70 (entget guideCrv))))
  (if (null detectClosed) (setq detectClosed 0))
  (setq detectClosed (if (/= (logand detectClosed 1) 0) 1 0)
        detectCrv (DEGZ--entmakex-lwpoly detectPts detectProps detectClosed)
        detectOwned T)
  (if (not (and detectCrv (entget detectCrv)))
    (setq detectCrv mainCrv
          detectOwned nil))

  (setq jobs (DEGZ--aligned-group-jobs
               detectCrv groups alignTol dropDist extend childMaxDist))

  (foreach job jobs
    (setq branchPts (car job)
          rowGroups (cadr job)
          allRecs (caddr job)
          recs allRecs
          bankCount (cadddr job))
    (if branchPts
      (progn
        (setq attachBase (DEGZ--pt2d (car branchPts))
              farCenter  (DEGZ--pt2d (cadr branchPts))
              dMid       (vl-catch-all-apply
                           'vlax-curve-getDistAtPoint
                           (list (DEGZ--ename detectCrv) (DEGZ--pt3d attachBase))))
        (if (not (vl-catch-all-error-p dMid))
          (progn
            (setq dMid (DEGZ--corner-mouth-center-dist
                         detectCrv attachBase farCenter dMid (* 0.5 short))
                  maxDist (DEGZ--curve-total detectCrv)
                  ;; OFFSET iki agiz arasindaki toplam mesafedir; her yana yarisi dusur.
                  distPair (DEGZ--distpair10 dMid 1.0 maxDist (* 0.5 short))
                  mouthA (DEGZ--pt2d
                           (vlax-curve-getPointAtDist
                             (DEGZ--ename detectCrv) (car distPair)))
                  mouthB (DEGZ--pt2d
                           (vlax-curve-getPointAtDist
                             (DEGZ--ename detectCrv) (cadr distPair)))
                  deltaA (list (- (car mouthA) (car attachBase))
                               (- (cadr mouthA) (cadr attachBase)))
                  deltaB (list (- (car mouthB) (car attachBase))
                               (- (cadr mouthB) (cadr attachBase)))
                  farA (list (+ (car farCenter) (car deltaA))
                             (+ (cadr farCenter) (cadr deltaA)))
                  farB (list (+ (car farCenter) (car deltaB))
                             (+ (cadr farCenter) (cadr deltaB)))
                  mainRes (vl-catch-all-apply
                            'DEGZ--insert-detour
                            (list mainCrv mouthA mouthB (list farA farB))))
            (if (and (not (vl-catch-all-error-p mainRes))
                     mainRes
                     (entget (DEGZ--ename mainRes)))
              (progn
                (setq mainCrv (DEGZ--ename mainRes)
                      applyOk T)
                ;; Ortak omurgayi koru; blocklari baglamadan once her seviyede
                ;; omurgadan gercek bir agiz ve cift hatli cocuk dal olustur.
                (setq readyRows '())
                (foreach rowRecs rowGroups
                  (setq readyRows
                    (append readyRows
                      (list
                        (list rowRecs
                          ;; DF bloklari yeniden tiklanan ana segmente donmesin;
                          ;; az once uretilen cocuk dali baglanti kilavuzu yap.
                          (if (eq mode 'DF) branchPts nil))))))
                (if (> bankCount 1)
                  (progn
                    (setq readyRows '())
                    (foreach rowRecs rowGroups
                      (setq rowBranchPts
                        (DEGZ--perp-row-branch-points
                          mainCrv rowRecs alignTol dropDist extend childMaxDist)
                            rowMainRes nil)
                      (if rowBranchPts
                        (setq rowMainRes
                          (DEGZ--insert-child-detour
                            mainCrv rowBranchPts short)))
                      (if (and rowMainRes
                               (entget (DEGZ--ename rowMainRes)))
                        (progn
                          (setq mainCrv (DEGZ--ename rowMainRes))
                          (setq readyRows
                            (append readyRows
                              (list (list rowRecs rowBranchPts)))))
                        (setq applyOk nil)))))

                ;; Cocuk dallar artik geometride. Satirlar ayri cizim
                ;; cagrilarina bolunmeden once yakin bloklarin ortak yonunu ve
                ;; o yondeki gercek ana-hat hedefini birlikte kaydet.
                (setq commonSS (ssadd))
                (foreach r allRecs (ssadd (car r) commonSS))
                (setq commonMap
                  (DEGZ--pre-common-target-map mainCrv commonSS mode))
                (if commonMap
                  (setq *DEGZ_PRE_COMMON_TARGET_MAP*
                    (append commonMap *DEGZ_PRE_COMMON_TARGET_MAP*)))

                ;; Artik her block sirasi omurgaya degil kendi cocuk dalina gider.
                (foreach rowItem readyRows
                  (setq rowRecs (car rowItem)
                        rowBranchPts (cadr rowItem)
                        rowGuideCrv nil)
                  (if rowBranchPts
                    (setq rowGuideCrv
                      (DEGZ--entmakex-lwpoly
                        (list (DEGZ--pt2d (car rowBranchPts))
                              (DEGZ--pt2d (cadr rowBranchPts)))
                        (DEGZ--safe-props mainCrv)
                        0)))
                  (setq groupSS (ssadd))
                  (foreach r rowRecs (ssadd (car r) groupSS))
                  (setq *DEGZ_ROW_GUIDE* rowGuideCrv)
                  (setq applyRes (vl-catch-all-apply applyFn (list mainCrv groupSS)))
                  (setq *DEGZ_ROW_GUIDE* nil)
                  (if (and rowGuideCrv (entget rowGuideCrv))
                    (entdel rowGuideCrv))
                  (if (vl-catch-all-error-p applyRes)
                    (progn
                      (setq applyOk nil)
                      (princ
                        (strcat "\n" (vl-symbol-name mode)
                                " alt dal hata: " (vl-catch-all-error-message applyRes))))
                    (progn
                      (if (and applyRes (entget (DEGZ--ename applyRes)))
                        (setq mainCrv (DEGZ--ename applyRes)))
                      (setq finalPoints (DEGZ--get-lwpts mainCrv))
                      (foreach r rowRecs
                        (if (DEGZ--route-has-block-point-p finalPoints (cadr r))
                          (setq handled (cons (car r) handled))
                          (setq applyOk nil))))))
                (if applyOk
                  (if (> bankCount 1)
                    (princ
                      (strcat "\n" (vl-symbol-name mode)
                              ": " (itoa (length allRecs))
                              " block ortak dikey cocuk omurgaya baglandi."))
                    (princ
                      (strcat "\n" (vl-symbol-name mode)
                              ": Ayni hizadaki " (itoa (length recs))
                              " block ana polyline agzindan 40 cm alt dala baglandi."))))
              )
            )
          )
        )
      )
    )
  )
  (if (and detectOwned detectCrv (entget detectCrv)) (entdel detectCrv))
  ;; A later detour may have replaced an earlier mouth; verify the final route.
  (setq finalPoints (DEGZ--get-lwpts mainCrv))
  (setq remaining (ssadd))
  (if (and ss (= (type ss) 'PICKSET))
    (progn
      (setq i 0)
      (while (< i (sslength ss))
        (setq ent (ssname ss i))
        (if (or (not (member ent handled))
                (not (DEGZ--route-has-block-point-p finalPoints
                       (cdr (assoc 10 (entget ent))))))
          (ssadd ent remaining))
        (setq i (1+ i))
      )
    )
  )
  (list mainCrv remaining)
)

(defun DEGZ--preprocess-perp-row-chain (mainCrv ss mode / pass maxPass prevCount nextCount prepRes keepGoing)
  ;; Ilk varsayilan dal olustuktan sonra kalan blocklari guncel geometriye gore
  ;; yeniden tara. Boylece yeni dal da ana hat gibi davranip gerekiyorsa devam eder.
  (setq pass 0
        maxPass (if (and ss (= (type ss) 'PICKSET))
                  (max 1 (sslength ss))
                  1)
        keepGoing T)
  (while (and keepGoing
              (< pass maxPass)
              ss
              (= (type ss) 'PICKSET)
              (> (sslength ss) 1))
    (setq prevCount (sslength ss)
          prepRes (DEGZ--preprocess-perp-row-groups mainCrv ss mode)
          mainCrv (car prepRes)
          ss (cadr prepRes)
          nextCount (if (and ss (= (type ss) 'PICKSET))
                      (sslength ss)
                      0))
    (if (< nextCount prevCount)
      (setq pass (1+ pass))
      (setq keepGoing nil)
    )
  )
  (list mainCrv ss)
)

(defun DZ_ORIG (/ *error* sel crv0 pick ss dist newPl snapLimit undoToken oldCm oldRegen prepRes *DEGZ_PRE_COMMON_TARGET_MAP*)
  (vl-load-com)
  (setq oldCm (getvar "CMDECHO")
        oldRegen (vl-catch-all-apply 'getvar (list "REGENMODE")))
  (if (vl-catch-all-error-p oldRegen) (setq oldRegen nil))

  (defun *error* (msg)
    (if undoToken
      (progn
        (DEG:UNDO-GROUP-END undoToken)
        (setq undoToken nil)
      )
    )
    (if (numberp oldCm) (setvar "CMDECHO" oldCm))
    (if (numberp oldRegen)
      (vl-catch-all-apply 'setvar (list "REGENMODE" oldRegen)))
    (redraw)
    (if (and msg (not (wcmatch (strcase msg) "*CANCEL*,*QUIT*,*BREAK*")))
      (princ (strcat "\nDZ hata: " msg))
    )
    (princ)
  )

  (setvar "CMDECHO" 0)
  (if (numberp oldRegen)
    (vl-catch-all-apply 'setvar (list "REGENMODE" 0)))

  (prompt "\nDZ: Ana hat icin bir polyline sec (tikla): ")
  (setq sel (entsel))
  (if (null sel)
    (princ "\nSecim yok.")
    (progn
      (setq crv0 (car sel)
            pick (cadr sel))
      (prompt "\nDZ: Ana hatta baglanacak BLOCK'lari sec (INSERT): ")
      (setq ss (ssget '((0 . "INSERT"))))
      (if (null ss)
        (princ "\nBlock secimi yok.")
        (progn
          (setq *DEGZ_PRE_COMMON_TARGET_MAP* nil
                snapLimit (DEG:CFG-DDDZ-NUM-OR 'DZ_OFFSET 10.0))
          (if (<= snapLimit 0.0) (setq snapLimit 5.0))
          (setq dist (/ snapLimit 2.0))
          ;; DR ve DZ'nin tum ara olustur/sil adimlari tek Undo islemi olsun.
          (setq undoToken (DEG:UNDO-GROUP-BEGIN))
          (princ "\nDEG_R324 RUNNING (DR -> DZ)")
          (setq newPl (DEGDR--RUN crv0 pick dist))
          (if (and newPl (entget newPl))
            (progn
              (setq prepRes (DEGZ--preprocess-perp-row-chain newPl ss 'DZ)
                    newPl (car prepRes)
                    ss (cadr prepRes))
              (if (> (sslength ss) 0)
                (setq newPl (DEGZ--APPLY newPl ss)))
              (if (and newPl (entget newPl))
                (setq newPl (DEGZ--snap-close-double-turn-entity newPl snapLimit)))
              (princ "\nDZ tamam.")
            )
            (princ "\nDR sonucunda yeni polyline olusmadi. DZ calistirilamadi.")
          )
          (if undoToken
            (progn
              (DEG:UNDO-GROUP-END undoToken)
              (setq undoToken nil)
            )
          )
        )
      )
    )
  )

  (if (numberp oldCm) (setvar "CMDECHO" oldCm))
  (if (numberp oldRegen)
    (vl-catch-all-apply 'setvar (list "REGENMODE" oldRegen)))
  (redraw)
  (princ)
)
(defun DR_ORIG (/ sel mainEnt pick dist newPl ss)
  (vl-load-com)
  (setq sel (entsel "\nDR: Ana hat polyline sec (tikla): "))
  (if (null sel)
    (princ "\nSecim yok.")
    (progn
      (setq mainEnt (car sel))
      (setq pick    (cadr sel))

      (setq dist (getdist "\nMesafe <5>: "))
      (if (null dist) (setq dist 5.0))

      (princ "\nDR calisiyor...")
      (setq newPl (DEGDR--RUN mainEnt pick dist))

      (if (and newPl (entget newPl))
        (progn
          (prompt "\nDR->DZ: Ana hatta baglanacak BLOCK'lari sec (INSERT) [Enter=Iptal]: ")
          (setq ss (ssget '((0 . "INSERT"))))
          (if (and ss (= (type ss) 'PICKSET) (> (sslength ss) 0))
            (progn
              (DEGZ--APPLY newPl ss)
              (princ "\nDR+DZ tamam.")
            )
            (princ "\nDR tamam. DZ icin block secilmedi.")
          )
        )
        (princ "\nDR sonucunda yeni polyline olusmadi. DZ calistirilamadi.")
      )
    )
  )
  (princ)
)




(defun DZO-ORIG ()
  (DZ_ORIG)
)


;;; --- DD icin ayri ofset uygulamasi ---
(defun DEGDD--APPLY (crv0 ss / crv i blk ip blk2 ip2
               ptsMain propsMain mainTmp mainClosed guideCrv
               joinCand short shift approach
               vvx vvy uu dx dy len rx ry ipRin
               nearLim mainFarLim mergeOff
               cell cells
               parents data
               groups
               forcedReps sideMap segMap groupDirMap groupDir
               anchorMap stemMap  remoteMap mergeMap
               dirMap dirRec udir mdx mdy p1 ipb p1b pJoin stemRec stemA stemB cpSec pStep pStepb
               g rep recs r bestRec bestIp bestD dNow segIdx choosePlus
               procData anchorRec remote
               forceMain isAnchor cpMain cpCur cpE cpEshort
               uTan uPerp corner1 corner2 paramCur distEnds
               pDown pDownRin uDirRemote anchorStemDir
               key cx cy ix iy rec item mergePt isTargetSide
               sX sY sideFact cpERes shortRes 
               ipAvg pMid paramMid deriv Tlen Tx Ty Lx Ly dotProd dirSign distMid distDown distDownRin maxDist
               pMerge pMergeRin pLeft pRight ipLeft ipRight pMainTop pMainBot ipTop ipBot yTop yBot pTopA pBotA pTopB pBotB pTopDrop pBotDrop scoreA scoreB outsideLeft fromTop sideMode shortIp longIp calcCrv sideBase sideDx sideDy blockSide blockSideMap oblique alignedPair rowGuideActive preRec preSide preTarget)

  (vl-load-com)

  (setq joinCand (DEG:CFG-DDDZ-NUM-OR
                   (DEGDD--mode-key 'DD_AGIZ_ARAMA 'DF_AGIZ_ARAMA) 20.0))
  (if (<= joinCand 0.0)
    (setq joinCand (* 20.0 (DEG:PLAN-UNIT-SCALE))))
  (setq short (DEG:CFG-DDDZ-NUM-OR
                (DEGDD--mode-key 'DD_OFFSET 'DF_OFFSET) 10.0))
  (if (<= short 0.0)
    (setq short (* 10.0 (DEG:PLAN-UNIT-SCALE))))
  (setq shift short)
  (setq approach short)

  (setq nearLim (DEG:CFG-DDDZ-NUM-OR
                  (DEGDD--mode-key 'DD_BLOK_YAKINLIK 'DF_BLOK_YAKINLIK) 100.0))
  (if (<= nearLim 0.0)
    (setq nearLim (* 100.0 (DEG:PLAN-UNIT-SCALE))))
  (setq mainFarLim (DEG:CFG-DDDZ-NUM-OR
                     (DEGDD--mode-key 'DD_DIRSEK_DIST 'DF_DIRSEK_DIST) 200.0))
  (if (<= mainFarLim 0.0)
    (setq mainFarLim (* 200.0 (DEG:PLAN-UNIT-SCALE))))
  (setq mergeOff (DEG:CFG-DDDZ-NUM-OR
                   (DEGDD--mode-key 'DD_DIRSEK_KACIS 'DF_DIRSEK_KACIS) 50.0))
  (if (<= mergeOff 0.0)
    (setq mergeOff (* 50.0 (DEG:PLAN-UNIT-SCALE))))

  (setq crv0 (DEGZ--ename crv0))

  (if (not (and crv0 (entget crv0)))
    (progn (princ "\nDZ: Gecersiz polyline.") (princ))
    (if (not (and ss (= (type ss) 'PICKSET) (> (sslength ss) 0)))
      (progn (princ "\nDZ: Block secimi yok.") (princ))
      (progn

        (setq guideCrv
          (cond
            ((and (boundp '*DEGZ_ROW_GUIDE*)
                  *DEGZ_ROW_GUIDE*
                  (entget (DEGZ--ename *DEGZ_ROW_GUIDE*)))
              (DEGZ--ename *DEGZ_ROW_GUIDE*))
            ((and (boundp '*DEG_DF_GUIDE*)
                  *DEG_DF_GUIDE*
                  (entget (DEGZ--ename *DEG_DF_GUIDE*)))
              (DEGZ--ename *DEG_DF_GUIDE*))
            (T crv0)))
        (setq rowGuideActive
          (and (boundp '*DEGZ_ROW_GUIDE*)
               *DEGZ_ROW_GUIDE*
               (eq guideCrv (DEGZ--ename *DEGZ_ROW_GUIDE*))))
        (setq ptsMain   (DEGZ--get-lwpts guideCrv))
        (setq propsMain (DEGZ--safe-props guideCrv))
        (setq mainClosed (if (eq guideCrv crv0)
                           (cdr (assoc 70 (entget crv0)))
                           0))
        (if (null mainClosed) (setq mainClosed 0))
        (setq mainClosed (if (/= (logand mainClosed 1) 0) 1 0))
        (setq mainTmp   (DEGZ--entmakex-lwpoly ptsMain propsMain mainClosed))

        (setq cell    nearLim)
        (setq cells   '())
        (setq parents '())
        (setq data    '())

        (setq i 0)
        (while (< i (sslength ss))
          (setq blk (ssname ss i))
          (if (not (DEGZ--skip-block-p blk))
            (progn
              (setq ip (DEGZ--pt2d (cdr (assoc 10 (entget blk)))))

              (setq parents (DEGZ--uf-init parents blk))
              (setq data (append data (list (list blk ip))))

              (setq key (DEGZ--cellkey ip cell))
              (setq cx (car key) cy (cadr key))

              (setq ix -1)
              (while (<= ix 1)
                (setq iy -1)
                (while (<= iy 1)
                  (setq rec (assoc (list (+ cx ix) (+ cy iy)) cells))
                  (if rec
                    (foreach item (cdr rec)
                      (setq blk2 (car item))
                      (setq ip2  (cadr item))
                      (if (and blk2 ip2 (<= (DEGZ--safe-distance ip ip2) nearLim))
                        (setq parents (DEGZ--uf-union parents blk blk2))
                      )
                    )
                  )
                  (setq iy (1+ iy))
                )
                (setq ix (1+ ix))
              )

              (setq cells (DEGZ--cells-put cells (list cx cy) (list blk ip)))
            )
          )
          (setq i (1+ i))
        )

        (setq groups (DEGZ--groups-build parents data))

        (setq forcedReps '())
        (setq sideMap    '())
        (setq segMap     '())
        (setq anchorMap  '())
        (setq stemMap    '())
        (setq remoteMap  '())
        (setq mergeMap   '())
        (setq dirMap     '())
        (setq blockSideMap '())
        (setq groupDirMap '())

        (foreach g groups
          (setq rep  (car g))
          (setq recs (cdr g))

          (setq bestRec nil)
          (setq bestD   1e99)
          (foreach r recs
            (setq ip (cadr r))
            (setq cpMain (deg-safe-closest-point mainTmp ip))
            (setq dNow (DEGZ--safe-distance (DEGZ--pt2d ip) (DEGZ--pt2d cpMain)))
            (if (< dNow bestD)
              (progn (setq bestD dNow) (setq bestRec r))
            )
          )
          (if (null bestRec) (setq bestRec (car recs)))
          (setq bestIp (cadr bestRec))
          (setq anchorMap (cons (cons rep bestRec) anchorMap))

          (setq cpMain (deg-safe-closest-point mainTmp bestIp))
          (setq stemMap (cons (cons rep (list (DEGZ--pt2d bestIp) (DEGZ--pt2d cpMain))) stemMap))
          (setq choosePlus (DEGZ--choosePlus-main mainTmp bestIp cpMain joinCand))
          (setq sideMap (cons (cons rep choosePlus) sideMap))
          (setq segIdx (DEGZ--poly-closest-seg-index ptsMain bestIp mainClosed))
          (setq segMap (cons (cons rep segIdx) segMap))

          ;; Cikinti yonu grupta tek karar olsun: tum bloklarin merkezini ana hatta gore oku.
          (setq sX 0.0)
          (setq sY 0.0)
          (setq scoreB 0)
          (foreach r recs
            (setq ip (DEGZ--pt2d (cadr r)))
            (setq sX (+ sX (car ip)))
            (setq sY (+ sY (cadr ip)))
            (setq scoreB (1+ scoreB))
          )
          (if (> scoreB 0)
            (setq ipAvg (list (/ sX scoreB) (/ sY scoreB)))
            (setq ipAvg bestIp)
          )
          (setq cpMain (deg-safe-closest-point mainTmp ipAvg))
          (setq blockSide (DEGZ--side-from-group-alignment cpMain ipAvg recs))
          (setq blockSideMap (cons (cons rep blockSide) blockSideMap))
          (setq groupDirMap
            (cons (cons rep (DEGZ--group-approach-unit cpMain ipAvg recs)) groupDirMap))

          ;; Anchor secimi ana hat acisi degisse de ayni blokta kalsin.
          ;; Egik hatta yerel teget sirasi; yatay/dikey hatta mevcut kural kullanilir.
          (if (> (length recs) 1)
            (progn
              (setq scoreA nil)
              (foreach r recs
                (setq ip (DEGZ--pt2d (cadr r)))
                (setq uTan (DEGZ--canonical-tangent-at mainTmp cpMain))
                (setq scoreB
                  (if (and (> (abs (car uTan)) 1e-4)
                           (> (abs (cadr uTan)) 1e-4))
                    ;; Egik hatta X/Y esigi kullanma; bloklari yerel ana-hat ekseninde sirala.
                    (- (+ (* (car ip) (car uTan))
                          (* (cadr ip) (cadr uTan))))
                    ;; Yatay/dikey mevcut davranisi koru.
                    (cond
                      ((eq blockSide 'LEFT) (- (cadr ip)))
                      ((eq blockSide 'RIGHT) (cadr ip))
                      ((or (eq blockSide 'TOP) (eq blockSide 'BOTTOM)) (- (car ip)))
                      (T 0.0)
                    )
                  )
                )
                (if (or (null scoreA) (< scoreB scoreA))
                  (progn
                    (setq scoreA scoreB)
                    (setq bestRec r)
                  )
                )
              )
              (setq bestIp (cadr bestRec))
              (setq anchorMap (cons (cons rep bestRec) anchorMap))
              (setq cpMain (deg-safe-closest-point mainTmp bestIp))
              (setq stemMap (cons (cons rep (list (DEGZ--pt2d bestIp) (DEGZ--pt2d cpMain))) stemMap))
              (setq choosePlus (DEGZ--choosePlus-main mainTmp bestIp cpMain joinCand))
              (setq sideMap (cons (cons rep choosePlus) sideMap))
              (setq segIdx (DEGZ--poly-closest-seg-index ptsMain bestIp mainClosed))
              (setq segMap (cons (cons rep segIdx) segMap))
            )
          )

          (if (> (length recs) 1)
            (progn
               ;; Ozel cocuk-dal kilavuzunda uzaklik remote/dirsek karari
               ;; degildir; dal zaten bu yakin blok sirasi icin olusturulmustur.
               (if (and (> bestD mainFarLim) (not rowGuideActive))
                (progn
                  (setq remoteMap (cons (cons rep T) remoteMap))
                  (setq mergePt (DEGZ--point-toward bestIp cpMain mergeOff))
                  (setq mergeMap (cons (cons rep mergePt) mergeMap))

                  (setq udir (DEGZ--unit (- (car bestIp) (car cpMain)) (- (cadr bestIp) (cadr cpMain))))
                  (setq dirMap (cons (cons rep (list (car udir) (cadr udir))) dirMap))
                )
                (progn
                  (setq remoteMap (cons (cons rep nil) remoteMap))
                  (setq forcedReps (cons rep forcedReps))
                  ;; DD/DF normal ciziminde de yakin grup ayni carpismasiz
                  ;; ortak taraftan baglanir; dirsekli dal degistirilmez.
                  (setq cpMain (deg-safe-closest-point mainTmp ipAvg)
                        blockSide
                          (DEGZ--normal-group-no-cross-side
                            cpMain ipAvg recs blockSide))
                  (setq blockSideMap (cons (cons rep blockSide) blockSideMap)
                        groupDirMap
                          (cons
                            (cons rep (DEGZ--approach-unit-for-side blockSide))
                            groupDirMap))
                )
              )
            )
            (setq remoteMap (cons (cons rep nil) remoteMap))
          )
        )

        (setq procData '())
        (foreach g groups
          (setq rep  (car g))
          (setq recs (cdr g))
          (setq remote (cdr (assoc rep remoteMap)))
          (if (and remote (> (length recs) 1))
            (progn
              (setq anchorRec (cdr (assoc rep anchorMap)))
              (setq procData (append procData (list anchorRec)))
              (foreach r recs
                (if (not (equal (car r) (car anchorRec)))
                  (setq procData (append procData (list r)))
                )
              )
            )
            (setq procData (append procData recs))
          )
        )

        (setq crv crv0)

        (foreach rec procData
          (setq blk (car rec))
          (setq ip  (cadr rec))

          (setq rep (DEGZ--uf-find parents blk))
          (setq choosePlus (cdr (assoc rep sideMap)))
          (if (null choosePlus) (setq choosePlus T))
          (setq remote (cdr (assoc rep remoteMap)))
          (setq preRec
            (if (and (boundp '*DEGZ_PRE_COMMON_TARGET_MAP*)
                     *DEGZ_PRE_COMMON_TARGET_MAP*)
              (assoc blk *DEGZ_PRE_COMMON_TARGET_MAP*)
              nil)
                preSide (if preRec (cadr preRec) nil)
                preTarget (if preRec (caddr preRec) nil))

          (setq anchorRec (cdr (assoc rep anchorMap)))
          (setq isAnchor (and remote anchorRec (equal blk (car anchorRec))))
          (setq forceMain (if (member rep forcedReps) T nil))

          (cond
            (forceMain
              (progn
                (setq segIdx (cdr (assoc rep segMap)))
                (if (null segIdx) (setq segIdx 0))
                (setq cpMain (DEGZ--poly-closest-on-seg ptsMain segIdx ip mainClosed))
              )
            )
            (remote
              (if isAnchor
                (progn
                  (setq segIdx (cdr (assoc rep segMap)))
                  (if (null segIdx) (setq segIdx 0))
                  (setq cpMain (DEGZ--poly-closest-on-seg ptsMain segIdx ip mainClosed))
                )
                (progn
                  (setq cpMain (deg-safe-closest-point mainTmp ip))
                )
              )
            )
            (T (setq cpMain (deg-safe-closest-point mainTmp ip)))
          )
          (if (and preTarget (not remote))
            (setq cpMain preTarget))

          (setq cpCur (deg-safe-closest-point crv cpMain))

          (setq ip     (DEGZ--pt2d ip))
          (setq cpMain (DEGZ--pt2d cpMain))
          (setq cpCur  (DEGZ--pt2d cpCur))

          (setq vvx (- (car ip) (car cpMain)))
          (setq vvy (- (cadr ip) (cadr cpMain)))

          ;; Cikinti tarafi block'un baglanti/base noktasindan gorunen govdesine bakarak belirlenir.
          ;; Ana hat noktasi veya block rotasyonu bu karari bozmasin.
          (setq blockSide (cdr (assoc rep blockSideMap)))
          (if (null blockSide)
            (setq blockSide (DEGZ--side-from-connect-to-block cpMain ip))
          )
          (if (and preSide (not remote))
            (setq blockSide preSide))
          
          (DEGZ--dbg-cikinti "DD" blockSide remote isAnchor forceMain ip cpMain)
          (setq orthoForced nil)
(setq shiftBlk shift)
          (setq uu (DEGZ--unit vvx vvy))
              (if (and (boundp '*DEG-DDDZ-CIKINTI-DEBUG*) *DEG-DDDZ-CIKINTI-DEBUG*)
                (princ "\nDD step=UNIT")
              )
          (setq dx (car uu) dy (cadr uu) len (caddr uu))

          (if (and remote (not isAnchor))
            (progn
              (setq uDirRemote (cdr (assoc rep dirMap)))
              (setq dx (car uDirRemote))
              (setq dy (cadr uDirRemote))
              (setq len 100.0)
            )
          )
          (setq groupDir (cdr (assoc rep groupDirMap)))
          (if (and preSide (not remote))
            (setq groupDir (DEGZ--approach-unit-for-side preSide)))
          (if groupDir
            (setq dx (car groupDir)
                  dy (cadr groupDir)
                  len 100.0)
          )

          (if (> len 1e-9)
            (progn
              (setq rx dy)
              (setq ry (- dx))

              ;; =========================================================
              ;; 1. BLOK BACAK YONU VE TARAF KONTROLU (HERKES ICIN)
              ;; =========================================================
              (setq oblique (DEGZ--oblique-vector-p dx dy))
              (if oblique
                (progn
                  ;; Egik hatta taraf karari aciya ve RIGHT/TOP etiketine bagli degildir.
                  (setq sideFact
                    (DEGZ--local-side-factor mainTmp cpMain dx dy rx ry)
                  )
                  (setq isTargetSide (< sideFact 0.0))
                )
                (progn
                  (setq isTargetSide
                    (or (eq blockSide 'BOTTOM) (eq blockSide 'RIGHT))
                  )
                  (setq sideFact (if isTargetSide -1.0 1.0))
                )
              )

              ;; Plan tarafina gore gerekirse bacaklari ters yone cevir
              (setq ipRin
                (list
                  (+ (car ip) (* rx shiftBlk sideFact))
                  (+ (cadr ip) (* ry shiftBlk sideFact))
                )
              )
              (setq ipRin
                 (list 
                   (- (car ipRin) (* dx approach))
                   (- (cadr ipRin) (* dy approach))
                 )
              )
              ;; Sabit cikinti yonu icin ipRin WCS'te uretilir.
              ;; LEFT: altta, RIGHT: ustte, TOP/BOTTOM: solda.
              (if (not oblique)              (setq ipRin
                (cond
                  ((eq blockSide 'LEFT)
                    (list (- (car ip) approach) (- (cadr ip) shiftBlk))
                  )
                  ((eq blockSide 'RIGHT)
                    (list (+ (car ip) approach) (- (cadr ip) shiftBlk))
                  )
                  ((eq blockSide 'TOP)
                    (list (- (car ip) shiftBlk) (+ (cadr ip) approach))
                  )
                  ((eq blockSide 'BOTTOM)
                    (list (- (car ip) shiftBlk) (- (cadr ip) approach))
                  )
                  (T ipRin)
                )
              )              
              )
              ;; cpE noktasini da tarafa gore duzelt (Referans icin)
              (setq rx (* rx sideFact))
              (setq ry (* ry sideFact))

              ;; Remote + anchor + sol/ust ise ANA HAT UZERINDEKI CIKIS VERTEX'INI OBUR TARAFA AL
              ;; (blok bacagi/yonu degismez, sadece ana hatta degdigi taraf degisir)
              (if (and remote isAnchor isTargetSide)
                (setq choosePlus (if choosePlus nil T))
              )

              (if (and (boundp '*DEG-DDDZ-CIKINTI-DEBUG*) *DEG-DDDZ-CIKINTI-DEBUG*)
                (princ "\nDD step=CPE_START")
              )
              (if (or forceMain remote)
                (setq cpERes (vl-catch-all-apply 'DEGZ--cpE-side-flag (list crv cpCur joinCand choosePlus)))
                (setq cpERes (vl-catch-all-apply 'DEGZ--cpE-side      (list crv cpCur joinCand rx ry)))
              )
              (if (vl-catch-all-error-p cpERes)
                (progn
                  (if (and (boundp '*DEG-DDDZ-CIKINTI-DEBUG*) *DEG-DDDZ-CIKINTI-DEBUG*)
                    (princ (strcat "\nDD CPE hata: " (vl-catch-all-error-message cpERes)))
                  )
                  (setq cpE cpCur)
                )
                (setq cpE cpERes)
              )
              (if (and (boundp '*DEG-DDDZ-CIKINTI-DEBUG*) *DEG-DDDZ-CIKINTI-DEBUG*)
                (princ "\nDD step=CPE_DONE")
              )
              (setq cpCur (DEGZ--pt2d-safe cpCur cpMain))
              (setq cpE   (DEGZ--pt2d-safe cpE cpCur))
              (if (and cpCur cpE)
                (progn
                  (setq shortRes
                    (vl-catch-all-apply
                      'DEGZ--shorten-toward-cp
                      (list crv cpCur cpE (min short (* (DEGZ--safe-distance cpCur cpE) 0.45)))
                    )
                  )
                  (if (vl-catch-all-error-p shortRes)
                    (progn
                      (if (and (boundp '*DEG-DDDZ-CIKINTI-DEBUG*) *DEG-DDDZ-CIKINTI-DEBUG*)
                        (princ (strcat "\nDD SHORT hata: " (vl-catch-all-error-message shortRes)))
                      )
                      (setq cpEshort cpCur)
                    )
                    (setq cpEshort shortRes)
                  )
                )
                (setq cpEshort cpCur)
              )
              (setq cpEshort (DEGZ--pt2d-safe cpEshort cpCur))
              (if (and groupDir remote isAnchor
                       (> (abs vvx) joinCand)
                       (> (abs vvy) joinCand))
                (progn
                  (setq alignedPair
                    (DEGZ--corner-mouth-pair-by-approach crv cpMain groupDir short))
                  (if alignedPair
                    (setq cpCur (car alignedPair)
                          cpEshort (cadr alignedPair)))
                )
              )
              (if (and (boundp '*DEG-DDDZ-CIKINTI-DEBUG*) *DEG-DDDZ-CIKINTI-DEBUG*)
                (princ "\nDD step=SHORT_DONE")
              )

              (if (and cpCur cpEshort (> (DEGZ--safe-distance cpCur cpEshort) 1e-4))
                (progn
                  
                  (if (and remote (not isAnchor))
                     ;; =====================================================
                     ;; DURUM A: UZAK BLOKLAR (REMOTE) -> L-SHAPE / MERGE
                     ;; =====================================================
                     ;; * Bu bloklar komsu hattina baglanmali (Merge).
                     ;; * Hesaplamalar 'crv' (islenmis hat) uzerinde yapilmali.
                     (progn
                       ;; pMerge: ip'den mergeOff kadar asagi
                       (setq pMerge
                        (list
                          (+ (car ip) (* (- dx) mergeOff))
                          (+ (cadr ip) (* (- dy) mergeOff))
                        )
                       )
                       ;; pMergeRin: ipRin hizasinda
                       (setq pMergeRin
                        (list
                          (+ (car pMerge) (- (car ipRin) (car ip)))
                          (+ (cadr pMerge) (- (cadr ipRin) (cadr ip)))
                        )
                       )
                       
                       ;; Dis L eslesmesi:
                       ;; Ana hatta devam eden cift hatta soldaki kol ust yataya,
                       ;; sagdaki kol alt yataya baglanir. Boylece capraz eslesme olmaz.
                       (if (or (< (car pMerge) (car pMergeRin))
                               (and (equal (car pMerge) (car pMergeRin) 1e-9)
                                    (> (cadr pMerge) (cadr pMergeRin))))
                         (progn
                           (setq pLeft pMerge)
                           (setq ipLeft ip)
                           (setq pRight pMergeRin)
                           (setq ipRight ipRin)
                         )
                         (progn
                           (setq pLeft pMergeRin)
                           (setq ipLeft ipRin)
                           (setq pRight pMerge)
                           (setq ipRight ip)
                         )
                       )

                       (if (>= (cadr pLeft) (cadr pRight))
                         (progn (setq yTop (cadr pLeft)) (setq yBot (cadr pRight)))
                         (progn (setq yTop (cadr pRight)) (setq yBot (cadr pLeft)))
                       )

                       ;; Cikinti tarafindaki kisa ucu dis tarafa al.
                       ;; Ustten/alttan gelise gore capraz ureten eslesmeyi secme.
                       (setq outsideLeft
                         (>= (+ (* (car ipLeft) rx) (* (cadr ipLeft) ry))
                             (+ (* (car ipRight) rx) (* (cadr ipRight) ry)))
                       )
                       ;; Ustten gelen durumda cikinti aynalanir; kisa ucu dis tarafa almak icin eslesmeyi tersle.
                       (setq fromTop (eq blockSide 'TOP))
                       (if fromTop
                         (setq outsideLeft (if outsideLeft nil T))
                       )
                       ;; Asagidan geliste ust-alt eslesmesi ayri aynalanir.
                       (if (eq blockSide 'BOTTOM)
                         (setq outsideLeft (if outsideLeft nil T))
                       )
                       (setq pTopA (list (car pLeft) yTop))
                       (setq pBotA (list (car pRight) yBot))
                       (setq pTopB (list (car pRight) yTop))
                       (setq pBotB (list (car pLeft) yBot))
                       (if outsideLeft
                         (progn
                           (setq ipTop ipLeft)
                           (setq ipBot ipRight)
                           (setq pMainTop pTopA)
                           (setq pMainBot pBotA)
                         )
                         (progn
                           (setq ipTop ipRight)
                           (setq ipBot ipLeft)
                           (setq pMainTop pTopB)
                           (setq pMainBot pBotB)
                         )
                       )
                       ;; DD main/ip pair alignment: pMainTop/pMainBot ile ipTop/ipBot ters siralanirsa
                       ;; secilen polyline agzinda bosluk capraz kapanir. Once bu ciftleri ayni yone al.
                       (if (< (+ (* (- (car pMainBot) (car pMainTop)) (- (car ipBot) (car ipTop)))
                                 (* (- (cadr pMainBot) (cadr pMainTop)) (- (cadr ipBot) (cadr ipTop))))
                              0.0)
                         (progn
                           (setq pStep ipTop)
                           (setq ipTop ipBot)
                           (setq ipBot pStep)
                         )
                       )
                        ;; Ana hat agzinda capraz eslesme olmasin:
                        ;; ust/alt (veya sol/sag) ana hat ucu ayni siradaki blok ucuna baglansin.
                        (setq dirRec (DEGZ--pair-main-block-no-cross blockSide pMerge pMergeRin ip ipRin))
                        (setq pMainTop (car dirRec))
                        (setq pMainBot (cadr dirRec))
                        (setq ipTop (caddr dirRec))
                        (setq ipBot (cadddr dirRec))
                       ;; Ana hat uzerindeki noktalar (Mevcut 'crv' uzerinden alinir)
                       (setq cpCur    (deg-safe-closest-point crv pMainTop))
                       (setq cpEshort (deg-safe-closest-point crv pMainBot))
                       
                       ;; Alt kol ana hatta baglanir; ust kol dis L'yi tamamlar.
                       (setq pJoin
                         (inters
                           (list (car pMainBot) (cadr pMainBot) 0.0)
                           (list (+ (car pMainBot) rx) (+ (cadr pMainBot) ry) 0.0)
                           (list (car cpEshort) (cadr cpEshort) 0.0)
                           (list (+ (car cpEshort) dx) (+ (cadr cpEshort) dy) 0.0)
                           nil
                         )
                       )
                       (if pJoin
                         (setq pJoin (DEGZ--pt2d pJoin))
                         (setq pJoin (list (car cpEshort) (cadr pMainBot)))
                       )
                       ;; Blok cikislarina direkt capraz gitme.
                       ;; Ana hat noktasi ile blok cikisi hem X hem Y farkliyse araya kirim koy.
                       (setq sideMode
                         (or
                           (eq blockSide 'LEFT)
                           (eq blockSide 'RIGHT)
                           (and (> (abs (- (car pMainTop) (car ipTop))) 1e-6)
                                (> (abs (- (cadr pMainTop) (cadr ipTop))) 1e-6))
                           (and (> (abs (- (car pMainBot) (car ipBot))) 1e-6)
                                (> (abs (- (cadr pMainBot) (cadr ipBot))) 1e-6))
                         )
                       )
                        (if sideMode
                          (progn
                            ;; Sabit cikinti yonu:
                            ;; LEFT/RIGHT -> cikinti altta.
                            ;; TOP/BOTTOM -> cikinti solda.
                            (setq shortIp nil)
                            (setq longIp nil)
                            (if oblique
                              (if (or (eq blockSide 'LEFT) (eq blockSide 'RIGHT))
                                (progn
                                  ;; Bu dallarda pMainTop-longIp ve pJoin-shortIp ayni ofset kolunda kalir.
                                  (setq longIp ipTop)
                                  (setq shortIp ipBot)
                                )
                                (progn
                                  ;; Bu dallarda pMainTop-shortIp ve pJoin-longIp ayni ofset kolunda kalir.
                                  (setq shortIp ipTop)
                                  (setq longIp ipBot)
                                )
                              )
                              (cond
                                ((or (eq blockSide 'LEFT) (eq blockSide 'RIGHT))
                                  ;; Yatay gelislerde alt nokta short, ust nokta long olur.
                                  ;; Yatay dallar zit cizer: RIGHT short-first, LEFT long-first.
                                  (if (<= (cadr ipTop) (cadr ipBot))
                                    (progn (setq shortIp ipTop) (setq longIp ipBot))
                                    (progn (setq shortIp ipBot) (setq longIp ipTop))
                                  )
                                )
                                ((or (eq blockSide 'TOP) (eq blockSide 'BOTTOM))
                                  ;; Dikey gelislerde sol nokta short, sag nokta long olur.
                                  (if (<= (car ipTop) (car ipBot))
                                    (progn (setq shortIp ipTop) (setq longIp ipBot))
                                    (progn (setq shortIp ipBot) (setq longIp ipTop))
                                  )
                                )
                              )
                            )
                            (if oblique
                              (progn
                                ;; Egik dirsekte hat kimligini koru: pMerge-ip, pMergeRin-ipRin.
                                ;; Uclar ayrica siralanmaz; boylece aciya bagli Z/capraz dirsek olusmaz.
                                (setq pTopDrop
                                  (DEGZ--local-bend-point pMainTop ipTop dx dy rx ry blockSide)
                                )
                                (setq pBotDrop
                                  (DEGZ--local-bend-point pJoin ipBot dx dy rx ry blockSide)
                                )
                                (setq crv
                                  (DEGZ--insert-detour
                                    crv
                                    cpCur
                                    cpEshort
                                    (list pMainTop pTopDrop ipTop ipBot pBotDrop pJoin)
                                  )
                                )
                              )
                              (cond
                                ((eq blockSide 'TOP)
                                        ;; Ustten geliste mevcut dogru eslesme korunur.
                                        (if (not shortIp)
                                          (if (<= (DEGZ--safe-distance pMainTop ipTop) (DEGZ--safe-distance pMainTop ipBot))
                                            (progn (setq shortIp ipTop) (setq longIp ipBot))
                                            (progn (setq shortIp ipBot) (setq longIp ipTop))
                                          )
                                        )
                                        (setq pTopDrop
                                          (if oblique
                                            (DEGZ--local-bend-point pMainTop shortIp dx dy rx ry blockSide)
                                            (list (car pMainTop) (cadr shortIp))
                                          )
                                        )
                                        (setq pBotDrop
                                          (if oblique
                                            (DEGZ--local-bend-point pJoin longIp dx dy rx ry blockSide)
                                            (list (car pJoin) (cadr longIp))
                                          )
                                        )
                                        (setq crv
                                          (DEGZ--insert-detour
                                            crv
                                            cpCur
                                            cpEshort
                                            (list pMainTop pTopDrop shortIp longIp pBotDrop pJoin)
                                          )
                                        )                              )
                                ((eq blockSide 'BOTTOM)
                                  ;; Asagidan geliste cikinti kisa/uzun eslesmesi secim asamasinda aynalanir.
                                  (if (not shortIp)
                                    (if (<= (DEGZ--safe-distance pMainTop ipTop) (DEGZ--safe-distance pMainTop ipBot))
                                      (progn (setq shortIp ipTop) (setq longIp ipBot))
                                      (progn (setq shortIp ipBot) (setq longIp ipTop))
                                    )
                                  )
                                  (setq pTopDrop
                                          (if oblique
                                            (DEGZ--local-bend-point pMainTop shortIp dx dy rx ry blockSide)
                                            (list (car pMainTop) (cadr shortIp))
                                          )
                                        )
                                  (setq pBotDrop
                                          (if oblique
                                            (DEGZ--local-bend-point pJoin longIp dx dy rx ry blockSide)
                                            (list (car pJoin) (cadr longIp))
                                          )
                                        )
                                  (setq crv
                                    (DEGZ--insert-detour
                                      crv
                                      cpCur
                                      cpEshort
                                      (list pMainTop pTopDrop shortIp longIp pBotDrop pJoin)
                                    )
                                  )
                                )
                                ((eq blockSide 'RIGHT)
                                        ;; Sagdan geliste de UP/BOTTOM ile ayni agiz sirasi kullanilir.
                                        (if (not shortIp)
                                          (if (<= (DEGZ--safe-distance pMainBot ipTop) (DEGZ--safe-distance pMainBot ipBot))
                                            (progn (setq shortIp ipTop) (setq longIp ipBot))
                                            (progn (setq shortIp ipBot) (setq longIp ipTop))
                                          )
                                        )
                                        (setq pTopDrop
                                          (if oblique
                                            (DEGZ--local-bend-point pMainTop shortIp dx dy rx ry blockSide)
                                            (list (car pMainTop) (cadr shortIp))
                                          )
                                        )
                                        (setq pBotDrop
                                          (if oblique
                                            (DEGZ--local-bend-point pJoin longIp dx dy rx ry blockSide)
                                            (list (car pJoin) (cadr longIp))
                                          )
                                        )
                                        (setq crv
                                          (DEGZ--insert-detour
                                            crv
                                            cpCur
                                            cpEshort
                                            (list pMainTop pTopDrop shortIp longIp pBotDrop pJoin)
                                          )
                                        )                              )
                                ((eq blockSide 'LEFT)
                                        ;; LEFT, RIGHT'in aynasi olarak uzun ucu ust agza baglar.
                                        (if (not shortIp)
                                          (if (<= (DEGZ--safe-distance pMainTop ipTop) (DEGZ--safe-distance pMainTop ipBot))
                                            (progn (setq shortIp ipTop) (setq longIp ipBot))
                                            (progn (setq shortIp ipBot) (setq longIp ipTop))
                                          )
                                        )
                                        (setq pTopDrop
                                          (if oblique
                                            (DEGZ--local-bend-point pMainTop longIp dx dy rx ry blockSide)
                                            (list (car pMainTop) (cadr longIp))
                                          )
                                        )
                                        (setq pBotDrop
                                          (if oblique
                                            (DEGZ--local-bend-point pJoin shortIp dx dy rx ry blockSide)
                                            (list (car pJoin) (cadr shortIp))
                                          )
                                        )
                                        (setq crv
                                          (DEGZ--insert-detour
                                            crv
                                            cpCur
                                            cpEshort
                                            (list pMainTop pTopDrop longIp shortIp pBotDrop pJoin)
                                          )
                                        )                              )
                                (T
                                        ;; Belirsiz yonde varsayilan dogru eslesme.
                                        (if (not shortIp)
                                          (if (<= (DEGZ--safe-distance pMainTop ipTop) (DEGZ--safe-distance pMainTop ipBot))
                                            (progn (setq shortIp ipTop) (setq longIp ipBot))
                                            (progn (setq shortIp ipBot) (setq longIp ipTop))
                                          )
                                        )
                                        (setq pTopDrop
                                          (if oblique
                                            (DEGZ--local-bend-point pMainTop shortIp dx dy rx ry blockSide)
                                            (list (car pMainTop) (cadr shortIp))
                                          )
                                        )
                                        (setq pBotDrop
                                          (if oblique
                                            (DEGZ--local-bend-point pJoin longIp dx dy rx ry blockSide)
                                            (list (car pJoin) (cadr longIp))
                                          )
                                        )
                                        (setq crv
                                          (DEGZ--insert-detour
                                            crv
                                            cpCur
                                            cpEshort
                                            (list pMainTop pTopDrop shortIp longIp pBotDrop pJoin)
                                          )
                                        )                              )
                              )
                            )
                          )
                          (setq crv
                            (DEGZ--insert-detour
                              crv
                              cpCur
                              cpEshort
                              (list pMainTop ipTop ipBot pMainBot pJoin)
                            )
                          )
                        )
                      )
                      
                     ;; =====================================================
                     ;; DURUM B: YAKIN BLOKLAR (DIRECT CONNECT)
                     ;; =====================================================
                     ;; * Bu bloklar DIREKT ana hatta baglanmali.
                     ;; * Komsunun bacagina YAPISMAMALI.
                     ;; * Bu yuzden referans olarak 'mainTmp' (Temiz Hat) kullanilmali.
                     (progn
                        (if (and remote isAnchor)
                            ;; Anchor ozel durumu (Pahli Baglanti)
                            (progn
                              (setq dirRec
                                 (if oblique
                                   (DEGZ--pair-by-local-offset cpCur cpEshort ip ipRin rx ry)
                                   (DEGZ--direct-detour-order blockSide cpCur cpEshort ip ipRin)
                                 )
                               )
                              (if dirRec
                                (progn
                                  (setq cpCur    (car dirRec))
                                  (setq cpEshort (cadr dirRec))
                                  (setq ipTop    (caddr dirRec))
                                  (setq ipBot    (cadddr dirRec))
                                  (setq distEnds (DEGZ--safe-distance cpCur cpEshort))
                                  (if (> distEnds 1e-9)
                                    (progn
                                      (setq uTan (list (/ (- (car cpEshort) (car cpCur)) distEnds)
                                                       (/ (- (cadr cpEshort) (cadr cpCur)) distEnds)))
                                      (setq uPerp (list (- (cadr uTan)) (car uTan)))
                                      (if alignedPair
                                        (progn
                                          (setq corner1 (DEGZ--corner-at-block-axis cpCur ipTop groupDir)
                                                corner2 (DEGZ--corner-at-block-axis cpEshort ipBot groupDir))
                                          (setq crv (DEGZ--insert-detour crv cpCur cpEshort
                                            (list corner1 ipTop ipBot corner2))))
                                        (progn
                                          (setq corner1 (DEGZ--calc-L-corner cpCur ipTop uPerp)
                                                corner2 (DEGZ--calc-L-corner cpEshort ipBot uPerp))
                                          (setq crv (DEGZ--insert-detour crv cpCur cpEshort
                                            (list corner1 ipTop ipBot corner2)))))
                                    )
                                  )
                                )
                              )
                            )
                            
                            ;; STANDART DIREKT BAGLANTI (VEKTOREL HIZALAMA)
                            (progn
                                ;; *** ONEMLI: Hesaplamalarda 'mainTmp' (Temiz Hat) kullan! ***
                                (setq calcCrv mainTmp) 
                                
                                ;; A. Orta noktayi bul
                                (setq ipAvg (list (/ (+ (car ip) (car ipRin)) 2.0) (/ (+ (cadr ip) (cadr ipRin)) 2.0)))
                                ;; DD/DF tarafinda da ortak hedef son yakin-hat
                                ;; hesabindan once korunur.
                                (setq pMid
                                  (if (and preTarget (not remote))
                                    (deg-safe-closest-point calcCrv preTarget)
                                    (deg-safe-closest-point calcCrv ipAvg)))
                                
                                ;; B. Hattin yonunu bul (Temiz hat uzerinden)
                                (setq paramMid (vlax-curve-getParamAtPoint (DEGZ--ename calcCrv) (DEGZ--pt3d pMid)))
                                (setq deriv (vlax-curve-getFirstDeriv (DEGZ--ename calcCrv) paramMid))
                                (setq Tlen (DEGZ--safe-distance '(0 0 0) deriv))
                                (if (< Tlen 1e-9)
                                   (progn (setq Tx rx) (setq Ty ry))
                                   (progn (setq Tx (/ (car deriv) Tlen)) (setq Ty (/ (cadr deriv) Tlen)))
                                )

                                ;; C. Hizalama Yonu
                                (setq Lx (- (car ipRin) (car ip)))
                                (setq Ly (- (cadr ipRin) (cadr ip)))
                                (setq dotProd (+ (* Tx Lx) (* Ty Ly)))
                                (setq dirSign (if (>= dotProd 0) 1.0 -1.0))

                                ;; Remote + anchor + target side: reverse direction so the short piece is taken from the other side
                                (if (and remote isAnchor isTargetSide)
                                  (setq dirSign (- dirSign))
                                )
                                
                                ;; D. Sabit 10 birim aralik (Merkezden +/- 5.0)
                                (setq distMid (vlax-curve-getDistAtParam (DEGZ--ename calcCrv) paramMid))
                                (setq maxDist (DEGZ--curve-total calcCrv))
                                
                                (setq distPair (DEGZ--distpair10 distMid dirSign maxDist shift))
                                (setq distDown (car distPair))
                                (setq distDownRin (cadr distPair))
                                
                                ;; Noktalari Temiz Hat uzerinden al (Komsunun bacagina carpmaz)
                                (setq pDown    (DEGZ--pt2d (vlax-curve-getPointAtDist (DEGZ--ename calcCrv) distDown)))
                                (setq pDownRin (DEGZ--pt2d (vlax-curve-getPointAtDist (DEGZ--ename calcCrv) distDownRin)))
                                ;; Detour ekleme noktalarini guncel 'crv' uzerinde bul
                                ;; pDown temiz hat uzerinde oldugu icin, 'crv' uzerinde de govdeye denk gelir.
                                (setq cpCur    (deg-safe-closest-point crv pDown))
                                (setq cpEshort (deg-safe-closest-point crv pDownRin))
                                
                                (setq ipRin (DEGZ--direct-offset-end ip ipRin cpCur cpEshort short))
                                ;; DIREKT BAGLANTI LISTESI
                                (setq dirRec
                                 (DEGZ--pair-by-local-offset cpCur cpEshort ip ipRin
                                   (- (car cpEshort) (car cpCur))
                                   (- (cadr cpEshort) (cadr cpCur)))
                               )
                                (if dirRec
                                  (progn
                                    (setq cpCur    (car dirRec))
                                    (setq cpEshort (cadr dirRec))
                                    (setq ipTop    (caddr dirRec))
                                    (setq ipBot    (cadddr dirRec))
                                    (setq distEnds (DEGZ--safe-distance cpCur cpEshort))
                                    (if (> distEnds 1e-9)
                                      (progn
                                        (setq uTan (list (/ (- (car cpEshort) (car cpCur)) distEnds)
                                                         (/ (- (cadr cpEshort) (cadr cpCur)) distEnds)))
                                        (setq uPerp (list (- (cadr uTan)) (car uTan)))
                                        (setq corner1 (DEGZ--calc-L-corner cpCur ipTop uPerp))
                                        (setq corner2 (DEGZ--calc-L-corner cpEshort ipBot uPerp))
                                        (setq crv (DEGZ--insert-detour crv cpCur cpEshort (list corner1 ipTop ipBot corner2)))
                                      )
                                      (setq crv (DEGZ--insert-detour crv cpCur cpEshort (list ipTop ipBot)))
                                    )
                                  )
                                )
                            )
                        )
                     )
                  )
                )
              )
            )
          )
        )

        (if mainTmp (entdel mainTmp))
      )
    )
  )
  (if (and crv (entget crv)) crv nil)
)



;; =============================================================
;; DS - block sembol/adet listesi
;; =============================================================
(defun DS--app () "DEG_DS")

(defun DS--regapp (/ app)
  (setq app (DS--app))
  (if (not (tblsearch "APPID" app)) (regapp app))
  app
)

(defun DS--created-p (e / xd rec)
  (setq xd (assoc -3 (entget e (list (DS--app)))))
  (setq rec (if (and xd (listp (cadr xd))) (cadr xd) nil))
  (and rec (= (car rec) (DS--app)))
)

(defun DS--mark-created (e / app)
  (if e
    (progn
      (DS--regapp)
      (setq app (DS--app))
      (vl-catch-all-apply 'entmod (list (append (entget e) (list (list -3 (list app (cons 1000 "CREATED")))))))
      (vl-catch-all-apply 'entupd (list e))
    )
  )
  e
)

(defun DS--num (key def / v)
  (setq v (DEG:CFG-GETNUM key))
  (* (if (> v 0.0) v def) (DEG:PLAN-UNIT-SCALE))
)

(defun DS--exclude-list (/ raw parts out p u)
  (setq raw (DEG:CFG-GET 'DS_EXCLUDE_BLOCKS))
  (if (= (DEGDO--trim raw) "")
    (setq raw "E_OK,E_ARROW,E_DÖÞEME,E_DÖSEME,E_DOSEME")
  )
  (setq parts (DEGDO--split-delim raw ","))
  (foreach p parts
    (setq u (strcase (DEGDO--trim p)))
    (if (/= u "")
      (setq out (append out (list u)))
    )
  )
  out
)

(defun DS--excluded-block-p (u / hit pat)
  (foreach pat (DS--exclude-list)
    (if (wcmatch u (strcat "*" pat "*"))
      (setq hit T)
    )
  )
  hit
)

(defun DS--block-name-ok-p (nm / u)
  (setq u (if nm (strcase nm) ""))
  (and (/= u "")
       (not (DS--excluded-block-p u))
  )
)

(defun DS--symbol-raw (blk / vals s)
  (setq vals (get-sembol-adi-from-block blk))
  (setq s (if (and vals (car vals)) (car (car vals)) ""))
  (setq s (deg-trim-string (vl-princ-to-string s)))
  (if s s "")
)

(defun DS--block-count (blk / symPairs adet)
  (setq symPairs (get-sembol-adi-from-block blk))
  (setq adet     (get-adet-from-block blk))
  (cond
    ((> adet 0) adet)
    ((and symPairs (> (cdr (car symPairs)) 0))
     (cdr (car symPairs)))
    (T 1)
  )
)

(defun DS--symbol-display (blk sym / s)
  (setq s (deg-trim-string (vl-princ-to-string sym)))
  (if (= s "")
    (setq s "-")
  )
  (if s s "-")
)

(defun DS--sort-key (row / sym nm key)
  (setq sym (deg-trim-string (vl-princ-to-string (nth 2 row))))
  (setq nm  (deg-trim-string (vl-princ-to-string (nth 1 row))))
  (setq key (deg-trim-string (vl-princ-to-string (car row))))
  (if (= sym "")
    (strcat "1|" (strcase nm) "|" (strcase key))
    (strcat "0|" (strcase sym) "|" (strcase key))
  )
)

(defun DS--sort-rows (rows)
  (vl-sort rows
    (function
      (lambda (a b)
        (< (DS--sort-key a) (DS--sort-key b))
      )
    )
  )
)

(defun DS--text-height ()
  (DS--num 'DS_TEXT_HEIGHT 25.0)
)

(defun DS--text-layer () "e_sembol_listesi_yazý_ds")

(defun DS--layer-flag-state (flags mask)
  (if (/= 0 (logand flags mask)) :vlax-true :vlax-false)
)

(defun DS--set-layer-flag-state (flags mask state)
  (if (= state :vlax-true)
    (logior flags mask)
    (- flags (logand flags mask))
  )
)

(defun DS--layer-state-record (layData / layName color flags)
  (if layData
    (progn
      (setq layName (cdr (assoc 2 layData)))
      (setq color   (cdr (assoc 62 layData)))
      (setq flags   (cdr (assoc 70 layData)))
      (if (null color) (setq color 7))
      (if (null flags) (setq flags 0))
      (list
        (strcase layName)
        layName
        (if (< color 0) :vlax-false :vlax-true)
        (DS--layer-flag-state flags 1)
        (DS--layer-flag-state flags 4)
      )
    )
  )
)

(defun DS--snapshot-all-layer-states (/ layData state)
  ;; DS block kopyalarken nested obje layerlarini da gecici olarak acabilir.
  ;; Komut basinda butun mevcut layerlari saklamak, hata/iptal dahil tam geri donus saglar.
  (setq *DS-LAYER-STATES* nil)
  (setq layData (tblnext "LAYER" T))
  (while layData
    (setq state (DS--layer-state-record layData))
    (if state
      (setq *DS-LAYER-STATES* (cons state *DS-LAYER-STATES*))
    )
    (setq layData (tblnext "LAYER"))
  )
  *DS-LAYER-STATES*
)

(defun DS--remember-layer-state (layName / key state)
  ;; Snapshot sonrasinda DS'nin olusturmadigi ama sonradan karsilastigi layerlari da sakla.
  (if (and (boundp '*DS-LAYER-STATES*)
           (= (type layName) 'STR)
           (/= layName "")
           (tblsearch "LAYER" layName))
    (progn
      (setq key (strcase layName))
      (if (not (assoc key *DS-LAYER-STATES*))
        (progn
          (setq state (DS--layer-state-record (tblsearch "LAYER" layName)))
          (if state
            (setq *DS-LAYER-STATES* (cons state *DS-LAYER-STATES*))
          )
        )
      )
    )
  )
  layName
)

(defun DS--remember-object-layer-states (obj / lay atts a)
  (if (and obj (= (type obj) 'VLA-OBJECT))
    (progn
      (setq lay (vl-catch-all-apply 'vla-get-Layer (list obj)))
      (if (not (vl-catch-all-error-p lay))
        (DS--remember-layer-state lay)
      )
      (setq atts (degk--att-list obj))
      (foreach a atts
        (setq lay (vl-catch-all-apply 'vla-get-Layer (list a)))
        (if (not (vl-catch-all-error-p lay))
          (DS--remember-layer-state lay)
        )
      )
    )
  )
  obj
)

(defun DS--restore-layer-states (/ rec layEnt layData color flags newColor newFlags)
  (if (boundp '*DS-LAYER-STATES*)
    (progn
      (foreach rec *DS-LAYER-STATES*
        (setq layEnt (tblobjname "LAYER" (cadr rec)))
        (if layEnt
          (progn
            (setq layData (entget layEnt))
            (setq color (cdr (assoc 62 layData)))
            (setq flags (cdr (assoc 70 layData)))
            (if (null color) (setq color 7))
            (if (null flags) (setq flags 0))
            (setq newColor
              (if (= (nth 2 rec) :vlax-true)
                (abs color)
                (- (abs color))))
            (setq newFlags (DS--set-layer-flag-state flags 1 (nth 3 rec)))
            (setq newFlags (DS--set-layer-flag-state newFlags 4 (nth 4 rec)))
            (if (assoc 62 layData)
              (setq layData (subst (cons 62 newColor) (assoc 62 layData) layData))
              (setq layData (append layData (list (cons 62 newColor))))
            )
            (if (assoc 70 layData)
              (setq layData (subst (cons 70 newFlags) (assoc 70 layData) layData))
              (setq layData (append layData (list (cons 70 newFlags))))
            )
            (vl-catch-all-apply 'entmod (list layData))
          )
        )
      )
      (setq *DS-LAYER-STATES* nil)
    )
  )
  T
)

(defun DS--ensure-text-layer (/ layName layObj)
  (setq layName (DS--text-layer))
  (DS--remember-layer-state layName)
  (if (not (tblsearch "LAYER" layName))
    (entmake
      (list
        (cons 0 "LAYER")
        (cons 100 "AcDbSymbolTableRecord")
        (cons 100 "AcDbLayerTableRecord")
        (cons 2 layName)
        (cons 70 0)
        (cons 62 7)
      )
    )
  )
  (setq layObj (tblobjname "LAYER" layName))
  (if layObj
    (progn
      (entmod (subst (cons 62 7) (assoc 62 (entget layObj)) (entget layObj)))
      (entupd layObj)
    )
  )
  (degk--ensure-layer-editable layName)
  layName
)

(defun DS--make-table-poly (pts / lay data e p)
  (setq lay (DS--ensure-text-layer))
  (if (and pts (> (length pts) 1))
    (progn
      (setq data
        (list
          (cons 0 "LWPOLYLINE")
          (cons 100 "AcDbEntity")
          (cons 8 lay)
          (cons 100 "AcDbPolyline")
          (cons 90 (length pts))
          (cons 70 0)
        )
      )
      (foreach p pts
        (setq data (append data (list (cons 10 (list (car p) (cadr p))))))
      )
      (setq e (entmakex data))
      (if e (DS--mark-created e))
      e
    )
  )
)

(defun DS--draw-table-frame (base rowCount / rowH blockW symbolW countW left x1 x2 right top bottom i y x z)
  (if (and base rowCount (> rowCount 0))
    (progn
      (setq rowH (DS--num 'DS_ROW_SPACING 110.0))
      (setq blockW (DS--num 'DS_TABLE_BLOCK_W 110.0))
      (setq symbolW (DS--num 'DS_TABLE_SYMBOL_W 120.0))
      (setq countW (DS--num 'DS_TABLE_COUNT_W 120.0))
      (setq z (if (caddr base) (caddr base) 0.0))
      (setq left  (- (car base) (/ blockW 2.0)))
      (setq x1    (+ left blockW))
      (setq x2    (+ x1 symbolW))
      (setq right (+ x2 countW))
      (setq top    (+ (cadr base) (/ rowH 2.0)))
      (setq bottom (- (cadr base) (* (- rowCount 1) rowH) (/ rowH 2.0)))
      (setq i 0)
      (while (<= i rowCount)
        (setq y (- top (* i rowH)))
        (DS--make-table-poly (list (list left y z) (list right y z)))
        (setq i (1+ i))
      )
      (foreach x (list left x1 x2 right)
        (DS--make-table-poly (list (list x top z) (list x bottom z)))
      )
    )
  )
)

(defun DS--add-text (pt txt align / doc ms p tx res lay)
  (vl-load-com)
  (setq txt (degk--clean-text txt))
  (if (and pt txt (/= txt ""))
    (progn
      (degk--ensure-textstyle "STANDARD" "arial.ttf")
      (setq lay (DS--ensure-text-layer))
      (setq doc (vla-get-ActiveDocument (vlax-get-acad-object)))
      (setq ms  (vla-get-ModelSpace doc))
      (setq p   (deg-pt3 pt))
      (setq res (vl-catch-all-apply 'vla-AddText (list ms txt (vlax-3d-point p) (DS--text-height))))
      (if (vl-catch-all-error-p res)
        nil
        (progn
          (setq tx res)
          (if (vlax-property-available-p tx 'StyleName)
            (vl-catch-all-apply 'vla-put-StyleName (list tx "STANDARD"))
          )
          (if (and lay (/= lay ""))
            (vl-catch-all-apply 'vla-put-Layer (list tx lay))
          )
          (if (null align) (setq align acAlignmentMiddleLeft))
          (if (vlax-property-available-p tx 'Alignment)
            (vl-catch-all-apply 'vla-put-Alignment (list tx align))
          )
          (if (vlax-property-available-p tx 'TextAlignmentPoint)
            (vl-catch-all-apply 'vla-put-TextAlignmentPoint (list tx (vlax-3d-point p)))
          )
          tx
        )
      )
    )
  )
)

(defun DS--raw-to-list (raw)
  (cond
    ((vl-catch-all-error-p raw) nil)
    ((= (type raw) 'VARIANT)  (DS--raw-to-list (vlax-variant-value raw)))
    ((= (type raw) 'SAFEARRAY) (vlax-safearray->list raw))
    ((listp raw) raw)
    (T nil)
  )
)

(defun DS--constant-att-list (blk / raw)
  (if (and blk (= (type blk) 'VLA-OBJECT)
           (vlax-method-applicable-p blk 'GetConstantAttributes))
    (progn
      (setq raw (vl-catch-all-apply 'vlax-invoke (list blk 'GetConstantAttributes)))
      (DS--raw-to-list raw)
    )
    nil
  )
)

(defun DS--zero-inner-text-rotation (blk / atts a)
  (setq atts (append (degk--att-list blk) (DS--constant-att-list blk)))
  (foreach a atts
    (if (and a (= (type a) 'VLA-OBJECT) (vlax-property-available-p a 'Rotation))
      (vl-catch-all-apply 'vla-put-Rotation (list a 0.0))
    )
  )
  blk
)

(defun DS--zero-attrib-dxf-rotation (blk / e ad a)
  (setq e
    (cond
      ((= (type blk) 'ENAME) blk)
      ((= (type blk) 'VLA-OBJECT) (vlax-vla-object->ename blk))
      (T nil)
    )
  )
  (if e
    (progn
      (setq a (entnext e))
      (while (and a (setq ad (entget a)) (not (= (cdr (assoc 0 ad)) "SEQEND")))
        (if (= (cdr (assoc 0 ad)) "ATTRIB")
          (progn
            (if (assoc 50 ad)
              (setq ad (subst (cons 50 0.0) (assoc 50 ad) ad))
              (setq ad (append ad (list (cons 50 0.0))))
            )
            (vl-catch-all-apply 'entmod (list ad))
            (vl-catch-all-apply 'entupd (list a))
          )
        )
        (setq a (entnext a))
      )
      (vl-catch-all-apply 'entupd (list e))
    )
  )
  blk
)

(defun DS--make-scale-positive (blk / sx sy sz)
  (if (and blk (= (type blk) 'VLA-OBJECT)
           (vlax-property-available-p blk 'XScaleFactor)
           (vlax-property-available-p blk 'YScaleFactor)
           (vlax-property-available-p blk 'ZScaleFactor))
    (progn
      (setq sx (vl-catch-all-apply 'vla-get-XScaleFactor (list blk)))
      (setq sy (vl-catch-all-apply 'vla-get-YScaleFactor (list blk)))
      (setq sz (vl-catch-all-apply 'vla-get-ZScaleFactor (list blk)))
      (if (not (vl-catch-all-error-p sx))
        (vl-catch-all-apply 'vla-put-XScaleFactor (list blk (abs sx)))
      )
      (if (not (vl-catch-all-error-p sy))
        (vl-catch-all-apply 'vla-put-YScaleFactor (list blk (abs sy)))
      )
      (if (not (vl-catch-all-error-p sz))
        (vl-catch-all-apply 'vla-put-ZScaleFactor (list blk (abs sz)))
      )
    )
  )
  blk
)

(defun DS--reset-attribute-positions (insE)
  (if (and insE (= (type insE) 'ENAME))
    (vl-catch-all-apply 'degk--reset-insert-attrs (list insE))
  )
  insE
)

(defun DS--clear-attributes (blk / atts a tag)
  (setq atts (degk--att-list blk))
  (foreach a atts
    (if (and a (= (type a) 'VLA-OBJECT))
      (progn
        (setq tag (vl-catch-all-apply 'vla-get-TagString (list a)))
        (if (and (not (vl-catch-all-error-p tag))
                 (member (strcase (deg-trim-string tag)) '("ADET" "SIRA_NO" "SIRA NO"))
                 (vlax-property-available-p a 'TextString T))
          (vl-catch-all-apply 'vla-put-TextString (list a ""))
        )
      )
    )
  )
  (if (and blk (= (type blk) 'VLA-OBJECT)
           (vlax-method-applicable-p blk 'Update))
    (vl-catch-all-apply 'vla-Update (list blk))
  )
  blk
)

(defun DS--copy-block-to (blk target / copyObj copyE fromPt res msg nm)
  (setq res
    (vl-catch-all-apply
      (function
        (lambda ()
          (DS--remember-object-layer-states blk)
          (degk--make-object-and-atts-editable blk)
          (setq copyObj (vla-Copy blk))
          (setq copyE (vlax-vla-object->ename copyObj))
          (DS--remember-object-layer-states copyObj)
          (degk--make-object-and-atts-editable copyObj)
          (DS--make-scale-positive copyObj)
          (if (vlax-property-available-p copyObj 'Rotation)
            (vl-catch-all-apply 'vla-put-Rotation (list copyObj 0.0))
          )
          (DS--zero-inner-text-rotation copyObj)
          (setq fromPt (deg-get-inspt copyObj))
          (if fromPt
            (vla-Move copyObj (vlax-3d-point fromPt) (vlax-3d-point target))
          )
          (vl-catch-all-apply 'entupd (list copyE))
          (DS--reset-attribute-positions copyE)
          (DS--clear-attributes copyObj)
          (DS--remember-object-layer-states copyObj)
          (degk--make-object-and-atts-editable copyObj)
          (DS--zero-inner-text-rotation copyObj)
          (DS--zero-attrib-dxf-rotation copyObj)
          (DS--mark-created copyE)
          copyObj
        )
      )
      '()
    )
  )
  (if (vl-catch-all-error-p res)
    (progn
      (setq msg (vl-catch-all-error-message res))
      (setq nm (deg-block-name-raw blk))
      (princ (strcat "\nDS: " (if nm nm "<BLOCK>") " kopyalanamadi. Sebep: " msg))
      nil
    )
    res
  )
)

(defun DS--collect-blocks (ss / i ent obj nm sym rawSym adetUse key rec rows)
  (setq rows nil)
  (if ss
    (progn
      (setq i 0)
      (while (< i (sslength ss))
        (setq ent (ssname ss i))
        (setq obj (vlax-ename->vla-object ent))
        (setq nm  (deg-block-name obj))
        (if (and (not (DS--created-p ent)) (DS--block-name-ok-p nm))
          (progn
            (setq rawSym (DS--symbol-raw obj))
            (setq sym (DS--symbol-display obj rawSym))
            (setq adetUse (DS--block-count obj))
            (setq key (strcat (strcase nm) "|" (strcase rawSym)))
            (setq rec (assoc key rows))
            (if rec
              (setq rows (subst (list key nm rawSym sym (+ adetUse (nth 4 rec)) (nth 5 rec)) rec rows))
              (setq rows (append rows (list (list key nm rawSym sym adetUse obj))))
            )
          )
        )
        (setq i (1+ i))
      )
    )
  )
  (DS--sort-rows rows)
)

(defun DS_ORIG (/ *error* base ss rows row target sample sym count copied y oldTS oldCLayer *DS-LAYER-STATES*)
  (vl-load-com)
  (setq *DS-LAYER-STATES* nil
        oldTS (getvar "TEXTSTYLE")
        oldCLayer (getvar "CLAYER"))
  (defun *error* (msg)
    (if oldTS
      (vl-catch-all-apply 'setvar (list "TEXTSTYLE" oldTS))
    )
    (if oldCLayer
      (vl-catch-all-apply 'setvar (list "CLAYER" oldCLayer))
    )
    (DS--restore-layer-states)
    (if (and msg (not (wcmatch (strcase msg) "*CANCEL*,*QUIT*,*BREAK*")))
      (princ (strcat "\nDS hata: " msg))
    )
    (princ)
  )
  (DS--snapshot-all-layer-states)
  (princ "\nDS: Alan icindeki blocklari sec: ")
  (setq ss (ssget '((0 . "INSERT"))))
  (if (not ss)
    (princ "\nDS: Block secimi yok.")
    (progn
      (setq rows (DS--collect-blocks ss))
      (if (not rows)
        (princ "\nDS: Secilen alanda uygun block bulunamadi.")
        (progn
          (setq base (getpoint "\nDS: Liste baslangic noktasini tikla: "))
          (if (not base)
            (princ "\nDS: Nokta secilmedi.")
            (progn
              (degk--ensure-textstyle "STANDARD" "arial.ttf")
              (setvar "TEXTSTYLE" "STANDARD")
              (setq y 0)
              (foreach row rows
                (setq target (list (car base) (- (cadr base) (* y (DS--num 'DS_ROW_SPACING 110.0))) (if (caddr base) (caddr base) 0.0)))
                (setq sample (nth 5 row))
                (setq sym    (nth 3 row))
                (setq count  (nth 4 row))
                (setq copied (DS--copy-block-to sample target))
                (if copied
                  (progn
                    (DS--add-text (list (+ (car target) (DS--num 'DS_SYMBOL_DX 110.0)) (cadr target) (caddr target)) sym nil)
                    (DS--add-text (list (+ (car target) (DS--num 'DS_SYMBOL_DX 110.0) (DS--num 'DS_COUNT_DX 120.0)) (cadr target) (caddr target)) (itoa count) acAlignmentMiddleCenter)
                    (setq y (1+ y))
                  )
                )
              )
              (DS--draw-table-frame base y)
              (princ (strcat "\nDS tamam. " (itoa y) " satir olusturuldu."))
            )
          )
        )
      )
    )
  )
  (if oldTS
    (vl-catch-all-apply 'setvar (list "TEXTSTYLE" oldTS))
  )
  (if oldCLayer
    (vl-catch-all-apply 'setvar (list "CLAYER" oldCLayer))
  )
  (DS--restore-layer-states)
  (princ)
)


;; ============================================================
;; DT - 10 BIRIM KABLO TAVASI
;; Komut icinde cizdirilen acik polyline merkez hattini gizli katmanda saklar,
;; tava konturunu ve donus/T/+ baglanti elemanlarini cizer.
;; ============================================================

(defun DT--type-key (idx suffix)
  (read (strcat "DT_TYPE" (itoa idx) "_" suffix))
)

(defun DT--type-color-default (idx)
  (cond
    ((= idx 1) (DEG:CFG-ACI-OR 'DT_KA_COLOR 7))
    ((= idx 2) (DEG:CFG-ACI-OR 'DT_ZA_COLOR 7))
    (T 7)
  )
)

(defun DT--type-color (idx / key value)
  (setq key (DT--type-key idx "COLOR"))
  (if (assoc key *DEG_CFG_OVERRIDES*)
    (DEG:CFG-ACI-OR key (DT--type-color-default idx))
    (DT--type-color-default idx)
  )
)

(defun DT--type-hatch-pattern-default (idx)
  "SOLID"
)

(defun DT--type-hatch-pattern (idx / key s)
  (setq key (DT--type-key idx "HATCH_PATTERN"))
  (setq s (strcase (vl-string-trim " \t\r\n" (DEG:CFG-GET key))))
  (cond
    ((= s "SOLID") "SOLID")
    ((= s "HEX") "HEX")
    ((= s "") "SOLID")
    (T "HEX"))
)

(defun DT--type-hatch-color-default (idx)
  8
)

(defun DT--type-hatch-color (idx)
  (DEG:CFG-ACI-OR (DT--type-key idx "HATCH_COLOR") (DT--type-hatch-color-default idx))
)

(defun DT--type-hatch-scale-default (idx)
  10.0
)

(defun DT--type-hatch-scale (idx)
  (DEG:CFG-NUM-OR (DT--type-key idx "HATCH_SCALE") (DT--type-hatch-scale-default idx))
)

(defun DT--mode-hatch-pattern (mode / rec)
  (setq rec (DT--find-type (DT--normalize-mode mode)))
  (if rec (nth 4 rec) "SOLID")
)

(defun DT--mode-hatch-color (mode / rec)
  (setq rec (DT--find-type (DT--normalize-mode mode)))
  (if rec (nth 5 rec) 8)
)

(defun DT--mode-hatch-scale (mode / rec)
  (setq rec (DT--find-type (DT--normalize-mode mode)))
  (if rec (nth 6 rec) 10.0)
)

(defun DT--type-default-layer (code)
  (strcat "e_" (DT--name-safe code) "_tava")
)

(defun DT--type-configs (/ i code layer out)
  (setq i 1)
  (while (<= i 7)
    (setq code
      (strcase
        (vl-string-trim " \t\r\n" (DEG:CFG-GET (DT--type-key i "CODE")))
      )
    )
    (setq layer
      (vl-string-trim " \t\r\n" (DEG:CFG-GET (DT--type-key i "LAYER")))
    )
    ;; Kisa adi girilen tip palette mutlaka gelsin. Layer bos birakilmissa
    ;; tip yine cizilebilir olsun ve tahmin edilebilir bir layer kullansin.
    (if (and (/= code "") (= layer ""))
      (setq layer (DT--type-default-layer code)))
    (if (/= code "")
      (setq out
        (append out
          (list
            (list
              code
              layer
              (DT--type-color i)
              i
              (DT--type-hatch-pattern i)
              (DT--type-hatch-color i)
              (DT--type-hatch-scale i)
            )
          )
        )
      )
    )
    (setq i (1+ i))
  )
  out
)
(defun DT--find-type (mode / u rec hit)
  (setq u (if mode (strcase (vl-string-trim " \t\r\n" mode)) ""))
  (if (= u "LV") (setq u "KA"))
  (if (= u "WC") (setq u "ZA"))
  (foreach rec (DT--type-configs)
    (if (= (car rec) u) (setq hit rec))
  )
  hit
)

(defun DT--normalize-mode (mode / rec types)
  (setq rec (DT--find-type mode))
  (if rec
    (car rec)
    (progn
      (setq types (DT--type-configs))
      (if types (caar types) "KA")
    )
  )
)

(defun DT--mode-layer (mode / rec)
  (setq rec (DT--find-type (DT--normalize-mode mode)))
  (if rec (cadr rec) "e_KA_tava")
)

(defun DT--mode-color (mode / rec)
  (setq rec (DT--find-type (DT--normalize-mode mode)))
  (if rec (nth 2 rec) 7)
)

(defun DT--mode-list-label (/ out rec)
  (foreach rec (DT--type-configs)
    (setq out
      (if out
        (strcat out "/" (car rec))
        (car rec)
      )
    )
  )
  (if out out "KA")
)

(defun DT--last-mode (/ s)
  (setq s (getenv "DEG_DT_LAST_MODE"))
  (DT--normalize-mode s)
)

(defun DT--remember-mode (mode)
  (setq *DT_ACTIVE_MODE* (DT--normalize-mode mode))
  (setq *DT_ACTIVE_LAYER* (DT--mode-layer *DT_ACTIVE_MODE*))
  (setenv "DEG_DT_LAST_MODE" *DT_ACTIVE_MODE*)
  *DT_ACTIVE_MODE*
)

(defun DT--mode-keyword (s / rec)
  (setq rec (DT--find-type s))
  (if rec (car rec) nil)
)

(defun DT--layer-visible ()
  (if (and *DT_ACTIVE_LAYER* (/= *DT_ACTIVE_LAYER* ""))
    *DT_ACTIVE_LAYER*
    (DT--mode-layer (DT--last-mode))
  )
)
(defun DT--layer-center  () "e_tava_dt_merkez")
(defun DT--layer-fitting () (DT--layer-visible))

(defun DT--line-layer-p (lay / u)
  (setq u (if lay (strcase lay) ""))
  (wcmatch u "*_ÇÝZGÝ,*_ÇIZGI")
)

(defun DT--base-layer-name (lay)
  (if (DT--line-layer-p lay)
    (substr lay 1 (- (strlen lay) 6))
    lay
  )
)

(defun DT--line-layer-name (lay)
  (if (DT--line-layer-p lay)
    lay
    (strcat (DT--base-layer-name lay) "_çizgi")
  )
)

(defun DT--layer-color-for-name (lay / base rec color)
  (setq base (strcase (DT--base-layer-name lay))
        color 7)
  (foreach rec (DT--type-configs)
    (if (= base (strcase (cadr rec))) (setq color (nth 2 rec))))
  color
)

(defun DT--layer-linework (/ base line)
  (setq base (DT--base-layer-name (DT--layer-visible))
        line (DT--line-layer-name base))
  (DT--ensure-layer line (DT--layer-color-for-name base) nil)
  line
)

(defun DT--tray-visible-layer-p (lay / u hit rec)
  (setq u (if lay (strcase (DT--base-layer-name lay)) ""))
  (if (= u "E_TAVA") (setq hit T))
  (foreach rec (DT--type-configs)
    (if (= u (strcase (cadr rec))) (setq hit T))
  )
  hit
)

(defun DT--visible-layer-filter (/ out rec)
  (setq out "e_tava,e_tava_çizgi")
  (foreach rec (DT--type-configs)
    (setq out
      (strcat out "," (cadr rec) "," (DT--line-layer-name (cadr rec))))
  )
  out
)

(defun DT--ensure-type-layers (/ rec)
  (foreach rec (DT--type-configs)
    (DT--ensure-layer (cadr rec) (nth 5 rec) nil)
    (DT--ensure-layer (DT--line-layer-name (cadr rec)) (nth 2 rec) nil)
  )
)

(defun DT--ensure-layer (name color offp / rec ed c)
  (setq c (abs color))
  (if offp (setq c (- c)))
  (if (not (tblsearch "LAYER" name))
    (entmakex
      (list
        (cons 0 "LAYER")
        (cons 100 "AcDbSymbolTableRecord")
        (cons 100 "AcDbLayerTableRecord")
        (cons 2 name)
        (cons 70 0)
        (cons 62 c)
        (cons 6 "CONTINUOUS")
      )
    )
  )
  (setq rec (tblobjname "LAYER" name))
  (if rec
    (progn
      (setq ed (entget rec))
      (if (assoc 62 ed)
        (setq ed (subst (cons 62 c) (assoc 62 ed) ed))
        (setq ed (append ed (list (cons 62 c))))
      )
      (entmod ed)
      (entupd rec)
    )
  )
  name
)

(defun DT--set-layer-bylayer (ent lay / ed obj)
  (setq ed (entget ent))
  (if (assoc 8 ed)
    (setq ed (subst (cons 8 lay) (assoc 8 ed) ed))
    (setq ed (append ed (list (cons 8 lay))))
  )
  (setq ed (vl-remove-if '(lambda (x) (member (car x) '(62 420 430))) ed))
  (entmod ed)
  (setq obj (vl-catch-all-apply 'vlax-ename->vla-object (list ent)))
  (if (and obj (not (vl-catch-all-error-p obj)))
    (progn
      (vl-catch-all-apply 'vla-put-Layer (list obj lay))
      (vl-catch-all-apply 'vla-put-Color (list obj 256))))
  (entupd ent)
  ent
)

(defun DT--closed-p (ent / flg)
  (setq flg (cdr (assoc 70 (entget ent))))
  (and flg (= 1 (logand flg 1)))
)

(defun DT--has-arc-p (ent / typ ed hit x v vd)
  (setq typ (cdr (assoc 0 (entget ent))) hit nil)
  (if (= typ "LWPOLYLINE")
    (progn
      (setq ed (entget ent))
      (foreach x ed
        (if (and (= (car x) 42) (> (abs (cdr x)) 1e-10)) (setq hit T))
      )
    )
    (if (= typ "POLYLINE")
      (progn
        (setq v (entnext ent))
        (while (and v (/= (cdr (assoc 0 (entget v))) "SEQEND"))
          (setq vd (entget v))
          (if (and (= (cdr (assoc 0 vd)) "VERTEX")
                   (assoc 42 vd)
                   (> (abs (cdr (assoc 42 vd))) 1e-10))
            (setq hit T)
          )
          (setq v (entnext v))
        )
      )
    )
  )
  hit
)

(defun DT--tray-height-elevation (value / text parsed)
  (setq text
    (vl-string-translate
      ","
      "."
      (vl-string-trim " \t\r\n" (if (= (type value) 'STR) value ""))))
  (setq parsed (if (/= text "") (distof text 2) nil))
  (if (numberp parsed) parsed 0.0)
)

(defun DT--active-elevation ()
  (if (and (boundp '*DT_ACTIVE_ELEVATION*) (numberp *DT_ACTIVE_ELEVATION*))
    *DT_ACTIVE_ELEVATION*
    0.0
  )
)

(defun DT--point-at-elevation (point elevation)
  (list (car point) (cadr point) (float elevation))
)

(defun DT--distance-xy (a b)
  (if (and a b)
    (distance (list (car a) (cadr a) 0.0)
              (list (car b) (cadr b) 0.0))
  )
)

(defun DT--entity-elevation (ent / ed typ value point)
  (if (and ent (setq ed (entget ent)))
    (progn
      (setq typ (cdr (assoc 0 ed)))
      (cond
        ((= typ "LWPOLYLINE")
          (setq value (cdr (assoc 38 ed))))
        ((member typ '("INSERT" "HATCH" "LINE" "CIRCLE" "ARC"))
          (setq point (cdr (assoc 10 ed))
                value (if (and point (caddr point)) (caddr point) 0.0)))
        (T (setq value 0.0))
      )
    )
  )
  (if (numberp value) value 0.0)
)

(defun DT--same-active-elevation-p (ent)
  (equal (DT--entity-elevation ent) (DT--active-elevation) 0.000001)
)

(defun DT--center-elevation-app () "DT_END_ELEVATION")

(defun DT--center-elevation-profile-app () "DT_ELEV_PROFILE")

(defun DT--set-center-end-elevations (center startZ endZ / app ed payload)
  (setq app (DT--center-elevation-app))
  (if (not (tblsearch "APPID" app)) (regapp app))
  (if (and center (entget center) (numberp startZ) (numberp endZ))
    (progn
      (setq payload (list app (cons 1040 (float startZ)) (cons 1040 (float endZ))))
      (setq ed (entget center '("*")))
      (setq ed (DT--xdata-set-app ed app payload))
      (entmod ed)
      (entupd center)
    )
  )
  center
)

(defun DT--set-center-base-elevation (center elevation / ed rec)
  (if (and center (numberp elevation)
           (setq ed (entget center '("*")))
           (= (cdr (assoc 0 ed)) "LWPOLYLINE"))
    (progn
      (setq rec (assoc 38 ed))
      (setq ed
        (if rec
          (subst (cons 38 (float elevation)) rec ed)
          (append ed (list (cons 38 (float elevation))))))
      (entmod ed)
      (entupd center)
    )
  )
  center
)

(defun DT--center-end-elevations (center / app ed xd rec item values fallback)
  (setq app      (DT--center-elevation-app)
        fallback (DT--entity-elevation center))
  (if (and center (entget center))
    (progn
      (setq ed  (entget center (list app))
            xd  (assoc -3 ed)
            rec (if xd (cadr xd) nil))
      (if (and rec (= (car rec) app))
        (foreach item (cdr rec)
          (if (= (car item) 1040)
            (setq values (append values (list (cdr item))))
          )
        )
      )
    )
  )
  (if (>= (length values) 2)
    (list (car values) (cadr values))
    (list fallback fallback)
  )
)

(defun DT--set-center-elevation-profile (center startTrim endTrim startLineZ endLineZ / app ed payload)
  (setq app (DT--center-elevation-profile-app))
  (if (not (tblsearch "APPID" app)) (regapp app))
  (if (and center (entget center) (numberp startTrim) (numberp endTrim))
    (progn
      (setq payload
        (list app
          (cons 1040 (float (max 0.0 startTrim)))
          (cons 1040 (float (max 0.0 endTrim)))))
      (if (and (numberp startLineZ) (numberp endLineZ))
        (setq payload
          (append payload
            (list (cons 1040 (float startLineZ))
                  (cons 1040 (float endLineZ)))))
      )
      (setq ed (entget center '("*")))
      (setq ed (DT--xdata-set-app ed app payload))
      (entmod ed)
      (entupd center)))
  center
)

(defun DT--center-elevation-profile (center / app ed xd rec item values)
  (setq app (DT--center-elevation-profile-app))
  (if (and center (entget center))
    (progn
      (setq ed  (entget center (list app))
            xd  (assoc -3 ed)
            rec (if xd (cadr xd) nil))
      (if (and rec (= (car rec) app))
        (foreach item (cdr rec)
          (if (= (car item) 1040)
            (setq values (append values (list (cdr item)))))))))
  (if (>= (length values) 2)
    (list (max 0.0 (car values))
          (max 0.0 (cadr values))
          (if (>= (length values) 4) (nth 2 values) nil)
          (if (>= (length values) 4) (nth 3 values) nil))
    (list 0.0 0.0 nil nil))
)

(defun DT--route-total-length (pts / total i)
  (setq total 0.0 i 0)
  (while (< i (1- (length pts)))
    (setq total (+ total (DT--distance-xy (nth i pts) (nth (1+ i) pts))))
    (setq i (1+ i))
  )
  total
)

(defun DT--route-distance-at-point (pt pts / total bestPos bestD i a b segLen rec cp d)
  (setq total 0.0 i 0)
  (while (< i (1- (length pts)))
    (setq a      (nth i pts)
          b      (nth (1+ i) pts)
          segLen (DT--distance-xy a b)
          rec    (g365_closest_on_seg pt a b))
    (if rec
      (progn
        (setq cp (car rec) d (nth 2 rec))
        (if (or (null bestD) (< d bestD))
          (setq bestD d bestPos (+ total (DT--distance-xy a cp)))
        )
      )
    )
    (setq total (+ total segLen)
          i     (1+ i))
  )
  (if (numberp bestPos) bestPos 0.0)
)

(defun DT--route-elevation-at-point (pt pts startZ endZ / total at ratio)
  (setq total (DT--route-total-length pts))
  (if (> total 0.000001)
    (progn
      (setq at    (DT--route-distance-at-point pt pts)
            ratio (max 0.0 (min 1.0 (/ at total))))
      (+ startZ (* ratio (- endZ startZ)))
    )
    startZ
  )
)

(defun DT--route-elevation-profile-at-point (pt pts startZ endZ startTrim endTrim startLineZ endLineZ / total at usable ratio tol)
  (setq total     (DT--route-total-length pts)
        startTrim (max 0.0 (if (numberp startTrim) startTrim 0.0))
        endTrim   (max 0.0 (if (numberp endTrim) endTrim 0.0))
        startLineZ (if (numberp startLineZ) startLineZ startZ)
        endLineZ   (if (numberp endLineZ) endLineZ endZ)
        tol         0.000001)
  (if (> total 0.000001)
    (progn
      (setq at       (DT--route-distance-at-point pt pts)
            usable   (- total startTrim endTrim))
      (cond
        ((<= usable 0.000001)
          (DT--route-elevation-at-point pt pts startZ endZ))
        ((< at (- startTrim tol)) startZ)
        ((> at (+ (- total endTrim) tol)) endZ)
        (T
          (setq ratio (/ (- at startTrim) usable))
          (setq ratio (max 0.0 (min 1.0 ratio)))
          (+ startLineZ (* ratio (- endLineZ startLineZ))))))
    startZ)
)

(defun DT--center-elevation-at-point (center pt / pts elevations profile)
  (setq pts        (g365_get_pts center)
        elevations (DT--center-end-elevations center)
        profile     (DT--center-elevation-profile center))
  (if (and pts (> (length pts) 1))
    (DT--route-elevation-profile-at-point
      pt pts
      (car elevations) (cadr elevations)
      (car profile) (cadr profile) (nth 2 profile) (nth 3 profile))
    (car elevations)
  )
)

(defun DT--build-elevation-at-point (pt)
  (if (and (boundp '*DT_BUILD_ROUTE_PTS*)
           (boundp '*DT_BUILD_START_ELEVATION*)
           (boundp '*DT_BUILD_END_ELEVATION*)
           *DT_BUILD_ROUTE_PTS*
           (numberp *DT_BUILD_START_ELEVATION*)
           (numberp *DT_BUILD_END_ELEVATION*))
    (DT--route-elevation-profile-at-point
      pt
      *DT_BUILD_ROUTE_PTS*
      *DT_BUILD_START_ELEVATION*
      *DT_BUILD_END_ELEVATION*
      (if (and (boundp '*DT_BUILD_START_TRIM*)
               (numberp *DT_BUILD_START_TRIM*))
        *DT_BUILD_START_TRIM* 0.0)
      (if (and (boundp '*DT_BUILD_END_TRIM*)
               (numberp *DT_BUILD_END_TRIM*))
        *DT_BUILD_END_TRIM* 0.0)
      (if (and (boundp '*DT_BUILD_START_LINE_ELEVATION*)
               (numberp *DT_BUILD_START_LINE_ELEVATION*))
        *DT_BUILD_START_LINE_ELEVATION* *DT_BUILD_START_ELEVATION*)
      (if (and (boundp '*DT_BUILD_END_LINE_ELEVATION*)
               (numberp *DT_BUILD_END_LINE_ELEVATION*))
        *DT_BUILD_END_LINE_ELEVATION* *DT_BUILD_END_ELEVATION*))
    (DT--active-elevation)
  )
)

(defun DT--make-poly (lay pts closedp / data p ent)
  (if (and pts (> (length pts) 1))
    (progn
      (setq data
        (list
          (cons 0 "LWPOLYLINE")
          (cons 100 "AcDbEntity")
          (cons 8 lay)
        )
      )
      ;; Merkez cizgisi gorunmez yardimci geometridir; sadece tava cizgileri 0.30 mm olur.
      (if (/= (strcase lay) (strcase (DT--layer-center)))
        (setq data (append data (list (cons 370 30))))
      )
      (setq data
        (append data
          (list
          (cons 100 "AcDbPolyline")
          (cons 90 (length pts))
          (cons 70 (if closedp 1 0))
          (cons 38 (DT--active-elevation))
          (cons 43 0.0)
          )
        )
      )
      (foreach p pts
        (setq data (append data (list (cons 10 (list (car p) (cadr p))))))
      )
      (setq ent (entmakex data))
      ent
    )
  )
)

(defun DT--make-poly3d (lay pts closedp / poly p made)
  (if (and pts (> (length pts) 1))
    (progn
      (setq made
        (entmake
          (list
            '(0 . "POLYLINE")
            '(100 . "AcDbEntity")
            (cons 8 lay)
            '(370 . 30)
            '(100 . "AcDb3dPolyline")
            '(66 . 1)
            '(10 0.0 0.0 0.0)
            (cons 70 (if closedp 9 8)))))
      (if made
        (progn
          (foreach p pts
            (entmake
              (list
                '(0 . "VERTEX")
                '(100 . "AcDbEntity")
                (cons 8 lay)
                '(100 . "AcDbVertex")
                '(100 . "AcDb3dPolylineVertex")
                (cons 10 (list (car p) (cadr p) (if (caddr p) (caddr p) 0.0)))
                '(70 . 32))))
          (entmake (list '(0 . "SEQEND") '(100 . "AcDbEntity") (cons 8 lay)))
          (setq poly (entlast))
        )
      )
      poly
    )
  )
)

(setq *DT_HATCH_PATTERN_CACHE* nil)

(defun DT--trim (s)
  (vl-string-trim " \t\r\n" (if (= (type s) 'STR) s ""))
)

(defun DT--split-comma (s / txt pos part out)
  (setq txt (if (= (type s) 'STR) s ""))
  (while (setq pos (vl-string-search "," txt))
    (setq part (substr txt 1 pos))
    (setq out (append out (list part)))
    (setq txt (substr txt (+ pos 2)))
  )
  (append out (list txt))
)

(defun DT--deg-rad (deg)
  (* pi (/ deg 180.0))
)

(defun DT--pat-line-numbers (line / part out)
  (foreach part (DT--split-comma line)
    (setq part (DT--trim part))
    (if (/= part "")
      (setq out (append out (list (atof part))))
    )
  )
  (if (>= (length out) 5) out nil)
)

(defun DT--pat-file ()
  (or
    (findfile "acad.pat")
    (findfile "acadiso.pat")
  )
)

(defun DT--read-pat-lines (pattern / key cached file f line s pos name found done nums out)
  (setq key (strcase (DT--trim pattern)))
  (setq cached (assoc key *DT_HATCH_PATTERN_CACHE*))
  (if cached
    (cdr cached)
    (progn
      (setq file (DT--pat-file))
      (if (and file (setq f (open file "r")))
        (progn
          (while (and (not done) (setq line (read-line f)))
            (setq s (DT--trim line))
            (cond
              ((= s ""))
              ((= (substr s 1 1) ";"))
              ((= (substr s 1 1) "*")
                (if found
                  (setq done T)
                  (progn
                    (setq pos (vl-string-search "," s))
                    (setq name
                      (strcase
                        (DT--trim
                          (if pos
                            (substr s 2 (1- pos))
                            (substr s 2)
                          )
                        )
                      )
                    )
                    (if (= name key) (setq found T))
                  )
                )
              )
              (found
                (setq nums (DT--pat-line-numbers s))
                (if nums (setq out (append out (list nums))))
              )
            )
          )
          (close f)
        )
      )
      (if out
        (setq *DT_HATCH_PATTERN_CACHE* (cons (cons key out) *DT_HATCH_PATTERN_CACHE*))
      )
      out
    )
  )
)

(defun DT--hex-pat-lines ()
  (list
    (list 0.0 0.0 0.0 0.0 0.21650635094610966 0.125 -0.25)
    (list 120.0 0.0 0.0 0.0 0.21650635094610966 0.125 -0.25)
    (list 60.0 0.125 0.0 0.0 0.21650635094610966 0.125 -0.25)
  )
)

(defun DT--pat-lines->dxfs (lines scale / out nums ang rad ca sa xo yo xd yd dx dy dash dashes)
  (foreach nums lines
    (setq ang (nth 0 nums)
          xo  (nth 1 nums)
          yo  (nth 2 nums)
          xd  (nth 3 nums)
          yd  (nth 4 nums)
          rad (DT--deg-rad ang)
          ca  (cos rad)
          sa  (sin rad)
          dx  (* scale (- (* xd ca) (* yd sa)))
          dy  (* scale (+ (* xd sa) (* yd ca)))
          dashes (cddddr (cdr nums)))
    (setq out
      (append out
        (list
          (cons 53 rad)
          (cons 43 (* xo scale))
          (cons 44 (* yo scale))
          (cons 45 dx)
          (cons 46 dy)
          (cons 79 (length dashes))
        )
      )
    )
    (foreach dash dashes
      (setq out (append out (list (cons 49 (* dash scale)))))
    )
  )
  out
)

(defun DT--hatch-scale ()
  (DT--mode-hatch-scale *DT_ACTIVE_MODE*)
)

(defun DT--hatch-pattern-info (pattern / name scale defs)
  (setq name (strcase (DT--trim pattern)))
  (if (= name "") (setq name "SOLID"))
  (cond
    ((= name "SOLID")
      (list "SOLID" nil))
    (T
      ;; DT icin HEX pattern'i dogrudan DXF tanimiyla uretiyoruz.
      ;; AutoCAD'in acad.pat okumasina baglanmak farkli kurulumlarda
      ;; "stringp T" hatasi verebildigi icin desteklenmeyen isimler HEX'e duser.
      (if (/= name "HEX") (setq name "HEX"))
      (setq scale (DT--hatch-scale))
      (setq defs (DT--pat-lines->dxfs (DT--hex-pat-lines) scale))
      (list name defs)
    )
  )
)

(defun DT--hatch-data (lay pts pattern color elevation / info pat defs solidp scale data i a b n)
  (if (and lay pts (>= (length pts) 3))
    (progn
      (setq info (DT--hatch-pattern-info pattern)
            pat  (car info)
            defs (cadr info)
            solidp (= pat "SOLID")
            scale (DT--hatch-scale)
            n (length pts))
      (setq data
        (list
          (cons 0 "HATCH")
          (cons 100 "AcDbEntity")
          (cons 8 lay)
          (cons 62 256)
          (cons 100 "AcDbHatch")
          (cons 10 (list 0.0 0.0 (if (numberp elevation) elevation 0.0)))
          (cons 210 (list 0.0 0.0 1.0))
          (cons 2 pat)
          (cons 70 (if solidp 1 0))
          (cons 71 0)
          (cons 91 1)
          (cons 92 1)
          (cons 93 n)
        )
      )
      (setq i 0)
      (while (< i n)
        (setq a (nth i pts)
              b (nth (rem (1+ i) n) pts))
        (setq data
          (append data
            (list
              (cons 72 1)
              (cons 10 (list (car a) (cadr a) 0.0))
              (cons 11 (list (car b) (cadr b) 0.0))
            )
          )
        )
        (setq i (1+ i))
      )
      (setq data
        (append data
          (list
            (cons 97 0)
            (cons 75 1)
            (cons 76 1)
          )
        )
      )
      (if (not solidp)
        (setq data
          (append data
            (list
              (cons 52 0.0)
              (cons 41 scale)
              (cons 77 0)
              (cons 78 (/ (length defs) 8))
            )
            defs
          )
        )
      )
      (append data (list (cons 98 0)))
    )
  )
)

(defun DT--hatch-data-assoc-at (lay pts pattern color elevation boundary / data out item)
  (setq data (DT--hatch-data lay pts pattern color elevation))
  (if (and data boundary (entget boundary))
    (progn
      (foreach item data
        (cond
          ((= (car item) 71)
            (setq out (append out (list (cons 71 1)))))
          ((= (car item) 97)
            (setq out (append out (list (cons 97 1) (cons 330 boundary)))))
          (T
            (setq out (append out (list item))))
        )
      )
      out
    )
    data
  )
)

(defun DT--hatch-data-assoc (lay pts pattern color boundary)
  (DT--hatch-data-assoc-at
    lay pts pattern color (DT--active-elevation) boundary)
)

(defun DT--vec3-sub (a b)
  (list (- (car a) (car b))
        (- (cadr a) (cadr b))
        (- (if (caddr a) (caddr a) 0.0) (if (caddr b) (caddr b) 0.0)))
)

(defun DT--cross3 (a b)
  (list
    (- (* (cadr a) (caddr b)) (* (caddr a) (cadr b)))
    (- (* (caddr a) (car b)) (* (car a) (caddr b)))
    (- (* (car a) (cadr b)) (* (cadr a) (car b))))
)

(defun DT--dot3 (a b)
  (+ (* (car a) (car b))
     (* (cadr a) (cadr b))
     (* (caddr a) (caddr b)))
)

(defun DT--unit3 (v / len)
  (setq len (sqrt (+ (* (car v) (car v))
                     (* (cadr v) (cadr v))
                     (* (caddr v) (caddr v)))))
  (if (> len 0.000000001)
    (list (/ (car v) len) (/ (cadr v) len) (/ (caddr v) len))
  )
)

(defun DT--plane-normal (pts / p0 p1 p2 normal)
  (if (>= (length pts) 3)
    (progn
      (setq p0     (car pts)
            p1     (nth 1 pts)
            p2     (g365_last pts)
            normal (DT--unit3
                     (DT--cross3 (DT--vec3-sub p1 p0) (DT--vec3-sub p2 p0))))
      (if (and normal (< (caddr normal) 0.0))
        (setq normal (list (- (car normal)) (- (cadr normal)) (- (caddr normal))))
      )
      normal
    )
  )
)

(defun DT--hatch-data-plane-assoc (lay pts pattern color boundary / info pat defs solidp scale normal ocsPts elevation data i n a b)
  (if (and lay pts (>= (length pts) 3) boundary (entget boundary))
    (progn
      (setq info      (DT--hatch-pattern-info pattern)
            pat       (car info)
            defs      (cadr info)
            solidp    (= pat "SOLID")
            scale     (DT--hatch-scale)
            normal    (DT--plane-normal pts)
            ocsPts    (if normal (mapcar '(lambda (p) (trans p 0 normal)) pts) nil)
            elevation (if ocsPts (caddr (car ocsPts)) 0.0)
            n         (length ocsPts))
      (if (and normal (>= n 3))
        (progn
          (setq data
            (list
              '(0 . "HATCH")
              '(100 . "AcDbEntity")
              (cons 8 lay)
              '(62 . 256)
              '(100 . "AcDbHatch")
              (cons 10 (list 0.0 0.0 elevation))
              (cons 210 normal)
              (cons 2 pat)
              (cons 70 (if solidp 1 0))
              '(71 . 1)
              '(91 . 1)
              '(92 . 1)
              (cons 93 n)))
          (setq i 0)
          (while (< i n)
            (setq a (nth i ocsPts)
                  b (nth (rem (1+ i) n) ocsPts)
                  data
                    (append data
                      (list
                        '(72 . 1)
                        (cons 10 (list (car a) (cadr a) 0.0))
                        (cons 11 (list (car b) (cadr b) 0.0)))))
            (setq i (1+ i))
          )
          (setq data
            (append data
              (list '(97 . 1) (cons 330 boundary) '(75 . 1) '(76 . 1))))
          (if (not solidp)
            (setq data
              (append data
                (list '(52 . 0.0) (cons 41 scale) '(77 . 0) (cons 78 (/ (length defs) 8)))
                defs))
          )
          (append data (list '(98 . 0)))
        )
      )
    )
  )
)

(defun DT--hatch-data-plane (lay pts pattern color / info pat defs solidp scale normal ocsPts elevation data i n a b)
  (if (and lay pts (>= (length pts) 3))
    (progn
      (setq info      (DT--hatch-pattern-info pattern)
            pat       (car info)
            defs      (cadr info)
            solidp    (= pat "SOLID")
            scale     (DT--hatch-scale)
            normal    (DT--plane-normal pts)
            ocsPts    (if normal (mapcar '(lambda (p) (trans p 0 normal)) pts) nil)
            elevation (if ocsPts (caddr (car ocsPts)) 0.0)
            n         (length ocsPts))
      (if (and normal (>= n 3))
        (progn
          (setq data
            (list
              '(0 . "HATCH")
              '(100 . "AcDbEntity")
              (cons 8 lay)
              '(62 . 256)
              '(100 . "AcDbHatch")
              (cons 10 (list 0.0 0.0 elevation))
              (cons 210 normal)
              (cons 2 pat)
              (cons 70 (if solidp 1 0))
              '(71 . 0)
              '(91 . 1)
              '(92 . 1)
              (cons 93 n)))
          (setq i 0)
          (while (< i n)
            (setq a (nth i ocsPts)
                  b (nth (rem (1+ i) n) ocsPts)
                  data
                    (append data
                      (list
                        '(72 . 1)
                        (cons 10 (list (car a) (cadr a) 0.0))
                        (cons 11 (list (car b) (cadr b) 0.0)))))
            (setq i (1+ i)))
          (setq data (append data (list '(97 . 0) '(75 . 1) '(76 . 1))))
          (if (not solidp)
            (setq data
              (append data
                (list '(52 . 0.0) (cons 41 scale) '(77 . 0) (cons 78 (/ (length defs) 8)))
                defs)))
          (append data (list '(98 . 0))))
      )
    )
  )
)

(defun DT--make-assoc-hatch-plane (boundary lay pts pattern color / data hatch)
  (setq data (DT--hatch-data-plane-assoc lay pts pattern color boundary))
  (if data
    (progn
      (setq hatch (entmakex data))
      (if hatch (DT--hatch-set-source hatch boundary))
    )
  )
)

(defun DT--make-hatch (lay pts pattern color / data)
  (setq data (DT--hatch-data lay pts pattern color (DT--active-elevation)))
  (if data (entmakex data))
)

(defun DT--make-assoc-hatch-vla (boundary lay pattern color / app doc space bobj info pat hatch sa var ok ent tryTypes typ)
  (if (and boundary (entget boundary))
    (progn
      (setq app (vl-catch-all-apply 'vlax-get-acad-object '()))
      (if (not (vl-catch-all-error-p app))
        (progn
          (setq doc (vl-catch-all-apply 'vla-get-ActiveDocument (list app)))
          (if (not (vl-catch-all-error-p doc))
            (progn
              (setq space
                (vl-catch-all-apply
                  (if (= (getvar "CVPORT") 1) 'vla-get-PaperSpace 'vla-get-ModelSpace)
                  (list doc)
                )
              )
              (setq bobj (vl-catch-all-apply 'vlax-ename->vla-object (list boundary)))
              (if (and (not (vl-catch-all-error-p space))
                       (not (vl-catch-all-error-p bobj)))
                (progn
                  (setq info (DT--hatch-pattern-info pattern)
                        pat  (car info)
                        tryTypes (list 0 1 2))
                  (foreach typ tryTypes
                    (if (or (null hatch) (vl-catch-all-error-p hatch))
                      (setq hatch
                        (vl-catch-all-apply
                          'vla-AddHatch
                          (list space typ pat :vlax-true)
                        )
                      )
                    )
                  )
                  (if (and hatch (not (vl-catch-all-error-p hatch)))
                    (progn
                      (setq sa (vlax-make-safearray vlax-vbObject '(0 . 0)))
                      (vlax-safearray-put-element sa 0 bobj)
                      (setq var (vlax-make-variant sa))
                      (setq ok (vl-catch-all-apply 'vla-AppendOuterLoop (list hatch var)))
                      (if (vl-catch-all-error-p ok)
                        (progn
                          (vl-catch-all-apply 'vla-Delete (list hatch))
                          (setq hatch nil)
                        )
                        (progn
                          (vl-catch-all-apply 'vla-put-Layer (list hatch lay))
                          (vl-catch-all-apply 'vla-put-Color (list hatch 256))
                          (vl-catch-all-apply 'vla-put-PatternScale (list hatch (DT--hatch-scale)))
                          (if (vlax-property-available-p hatch 'Elevation T)
                            (vl-catch-all-apply 'vla-put-Elevation (list hatch (DT--active-elevation)))
                          )
                          (vl-catch-all-apply 'vla-Evaluate (list hatch))
                          (setq ent (vl-catch-all-apply 'vlax-vla-object->ename (list hatch)))
                          (if (vl-catch-all-error-p ent) nil ent)
                        )
                      )
                    )
                  )
                )
              )
            )
          )
        )
      )
    )
  )
)

(defun DT--make-assoc-hatch (boundary lay pts pattern color / hatch data)
  (setq hatch (DT--make-assoc-hatch-vla boundary lay pattern color))
  (if (and hatch (entget hatch))
    (DT--hatch-set-source hatch boundary)
    (progn
      (setq data (DT--hatch-data-assoc lay pts pattern color boundary))
      (if data
        (progn
          (setq hatch (entmakex data))
          (if hatch (DT--hatch-set-source hatch boundary))
        )
      )
    )
  )
)
(defun DT--hatch-drop-last (lst / out i n)
  (setq n (length lst)
        i 0)
  (while (< i (1- n))
    (setq out (append out (list (nth i lst))))
    (setq i (1+ i))
  )
  out
)

(defun DT--bulge-segment-points (a b bulge / theta chord halfSin halfCos mid u nrm dist center rad start steps i ang out)
  (if (or (null bulge) (< (abs bulge) 1e-10) (< (distance a b) 1e-9))
    (list b)
    (progn
      (setq theta   (* 4.0 (atan bulge))
            chord   (distance a b)
            halfSin (sin (/ theta 2.0))
            halfCos (cos (/ theta 2.0)))
      (if (< (abs halfSin) 1e-9)
        (list b)
        (progn
          (setq mid
            (list
              (/ (+ (car a) (car b)) 2.0)
              (/ (+ (cadr a) (cadr b)) 2.0)
              0.0
            )
          )
          (setq u      (DT--seg-unit a b)
                nrm    (DT--perp u)
                dist   (/ (* chord halfCos) (* 2.0 halfSin))
                center (DT--pt+ mid nrm dist)
                rad    (abs (/ chord (* 2.0 halfSin)))
                start  (atan (- (cadr a) (cadr center)) (- (car a) (car center)))
                steps  (max 4 (fix (+ 1.0 (/ (abs theta) (/ pi 24.0)))))
                i      1)
          (while (<= i steps)
            (if (= i steps)
              (setq out (append out (list b)))
              (progn
                (setq ang (+ start (* theta (/ (float i) (float steps)))))
                (setq out
                  (append out
                    (list
                      (list
                        (+ (car center) (* rad (cos ang)))
                        (+ (cadr center) (* rad (sin ang)))
                        0.0
                      )
                    )
                  )
                )
              )
            )
            (setq i (1+ i))
          )
          out
        )
      )
    )
  )
)

(defun DT--flatten-bulged-pts (pts bulges / out n i a b bulge seg p)
  (if (and pts (> (length pts) 1))
    (progn
      (setq out (list (car pts))
            n   (length pts)
            i   0)
      (while (< i n)
        (setq a     (nth i pts)
              b     (nth (rem (1+ i) n) pts)
              bulge (if bulges (nth i bulges) 0.0)
              seg   (DT--bulge-segment-points a b bulge))
        (foreach p seg
          (setq out (append out (list p)))
        )
        (setq i (1+ i))
      )
      (if (and (> (length out) 1) (< (distance (car out) (last out)) 1e-8))
        (setq out (DT--hatch-drop-last out))
      )
      out
    )
    pts
  )
)

(defun DT--fitting-open-original-edges (pts bulges / maxRadius p radius n i a b mid edgeUnit radialUnit bulge dotv out)
  (setq maxRadius 0.0)
  (foreach p pts
    (setq radius (sqrt (+ (* (car p) (car p)) (* (cadr p) (cadr p)))))
    (if (> radius maxRadius) (setq maxRadius radius)))
  (setq n (length pts)
        i 0)
  (while (< i n)
    (setq a      (nth i pts)
          b      (nth (rem (1+ i) n) pts)
          bulge  (if bulges (nth i bulges) 0.0)
          mid    (list (/ (+ (car a) (car b)) 2.0)
                       (/ (+ (cadr a) (cadr b)) 2.0)
                       0.0)
          radius (sqrt (+ (* (car mid) (car mid)) (* (cadr mid) (cadr mid))))
          edgeUnit   (DT--seg-unit a b)
          radialUnit (if (> radius 1e-9)
                       (list (/ (car mid) radius) (/ (cadr mid) radius))
                       nil)
          dotv (if (and edgeUnit radialUnit)
                 (abs (g365_dot (car edgeUnit) (cadr edgeUnit)
                                (car radialUnit) (cadr radialUnit)))
                 1.0))
    (if (and (< (abs bulge) 1e-9)
             (> (distance a b) 1e-8)
             (> radius (* maxRadius 0.72))
             (< dotv 0.15))
      (setq out (append out (list i))))
    (setq i (1+ i)))
  out
)

(defun DT--fitting-flat-open-edges (pts bulges flat / original n i a b j found out)
  (setq original (DT--fitting-open-original-edges pts bulges)
        n        (length flat))
  (foreach i original
    (setq a     (nth i pts)
          b     (nth (rem (1+ i) (length pts)) pts)
          j     0
          found nil)
    (while (and (< j n) (null found))
      (if (and (equal a (nth j flat) 1e-6)
               (equal b (nth (rem (1+ j) n) flat) 1e-6))
        (setq found j)
        (setq j (1+ j))))
    (if found (setq out (append out (list found)))))
  out
)

(defun DT--nearest-flat-edge (flat target used / n i a b mid dist bestDist best)
  (setq n (length flat)
        i 0)
  (while (< i n)
    (if (not (member i used))
      (progn
        (setq a    (nth i flat)
              b    (nth (rem (1+ i) n) flat)
              mid  (list (/ (+ (car a) (car b)) 2.0)
                         (/ (+ (cadr a) (cadr b)) 2.0)
                         0.0)
              dist (distance mid target))
        (if (or (null bestDist) (< dist bestDist))
          (setq bestDist dist
                best i))))
    (setq i (1+ i)))
  best
)

(defun DT--fitting-port-open-edges (flat ports / used port idx)
  (foreach port ports
    (setq idx (DT--nearest-flat-edge flat port used))
    (if idx (setq used (append used (list idx)))))
  used
)

(defun DT--block-hatch-entmake (pts bulges boundary / data flatPts)
  (setq flatPts
    (if bulges
      (DT--flatten-bulged-pts pts bulges)
      pts
    )
  )
  (setq data
    (DT--hatch-data-assoc-at
      (DT--layer-fitting)
      flatPts
      (DT--mode-hatch-pattern *DT_ACTIVE_MODE*)
      (DT--mode-hatch-color *DT_ACTIVE_MODE*)
      0.0
      boundary
    )
  )
  (if data (entmake data))
)

(defun DT--block-local-2d-hatch-entmake (pts bulges / data flatPts)
  ;; 2D gorunum blocklarinda hatch siniri block-yerel koordinatlarla
  ;; sabittir. Associative obje referansi bazi CAD surumlerinde WCS'ye
  ;; kacabildigi icin burada hatch dongusunu bagimsiz olusturuyoruz.
  (setq flatPts
    (if bulges
      (DT--flatten-bulged-pts pts bulges)
      pts
    )
  )
  (setq data
    (DT--hatch-data
      (DT--layer-fitting)
      flatPts
      (DT--mode-hatch-pattern *DT_ACTIVE_MODE*)
      (DT--mode-hatch-color *DT_ACTIVE_MODE*)
      0.0
    )
  )
  (if data (entmake data))
)

(defun DT--boundary-add-hatch-reactor (boundary hatch / ed out item hasBlock inBlock found)
  (if (and boundary hatch (entget boundary) (entget hatch))
    (progn
      (setq ed (entget boundary))
      (foreach item ed
        (if (and (= (car item) 102) (= (cdr item) "{ACAD_REACTORS"))
          (setq hasBlock T)))
      (foreach item ed
        (cond
          ((and (= (car item) 102) (= (cdr item) "{ACAD_REACTORS"))
            (setq inBlock T)
            (setq out (append out (list item))))
          ((and inBlock (= (car item) 330) (= (cdr item) hatch))
            (setq found T)
            (setq out (append out (list item))))
          ((and inBlock (= (car item) 102) (= (cdr item) "}"))
            (if (not found) (setq out (append out (list (cons 330 hatch)))))
            (setq out (append out (list item))
                  inBlock nil))
          (T
            (setq out (append out (list item)))
            (if (and (not hasBlock) (= (car item) 5))
              (setq out
                (append out
                  (list '(102 . "{ACAD_REACTORS") (cons 330 hatch) '(102 . "}"))))))))
      (if (entmod out)
        (progn
          (entupd boundary)
          boundary)))
  )
)

(defun DT--hatch-set-source (hatch boundary / ed out item after97 linked)
  (if (and hatch boundary (entget hatch) (entget boundary))
    (progn
      (setq ed (entget hatch))
      (foreach item ed
        (cond
          ((= (car item) 71)
            (setq out (append out (list '(71 . 1)))))
          ((= (car item) 97)
            (setq out (append out (list '(97 . 1) (cons 330 boundary)))
                  after97 T))
          ((and after97 (= (car item) 330))
            (setq after97 nil))
          (T
            (setq out (append out (list item))))))
      (if (entmod out)
        (progn
          (entupd hatch)
          (setq linked (DT--boundary-add-hatch-reactor boundary hatch))
          (if linked hatch)))
    )
  )
)

(defun DT--block-next-boundary (ent used / cur typ found)
  (setq cur (entnext ent))
  (while (and cur
              (/= (cdr (assoc 0 (entget cur))) "ENDBLK")
              (null found))
    (setq typ (cdr (assoc 0 (entget cur))))
    (if (and (member typ '("LWPOLYLINE" "POLYLINE" "3DFACE" "REGION"))
             (not (member cur used)))
      (setq found cur))
    (setq cur (entnext cur)))
  found
)

(defun DT--block-associate-hatches (name / rec ent prev typ boundary used)
  (setq rec (if name (tblobjname "BLOCK" name)))
  (if rec
    (progn
      (setq ent (entnext rec))
      (while (and ent (/= (cdr (assoc 0 (entget ent))) "ENDBLK"))
        (setq typ (cdr (assoc 0 (entget ent))))
        (cond
          ((= typ "HATCH")
            (setq boundary
              (if (and prev (not (member prev used)))
                prev
                (DT--block-next-boundary ent used)))
            (if boundary
              (progn
                (DT--hatch-set-source ent boundary)
                (setq used (cons boundary used)))))
          ((member typ '("LWPOLYLINE" "POLYLINE" "3DFACE" "REGION"))
            (setq prev ent)))
        (setq ent (entnext ent)))
      T)
  )
)
(defun DT--pt+ (p u d)
  (list (+ (car p) (* (car u) d))
        (+ (cadr p) (* (cadr u) d))
        0.0)
)

(defun DT--perp (u) (list (- (cadr u)) (car u)))

(defun DT--seg-unit (a b)
  (g365_unit (- (car b) (car a)) (- (cadr b) (cadr a)))
)

(defun DT--draw-seam (pt dir half lay / n a b)
  (setq n (DT--perp dir))
  (setq a (DT--pt+ pt n half))
  (setq b (DT--pt+ pt n (- half)))
  (DT--make-poly lay (list a b) nil)
)

(defun DT--name-safe (s / bad i ch out)
  (setq bad "<>/\\\":;?*|,=`"
        i 1
        out "")
  (while (<= i (strlen s))
    (setq ch (substr s i 1))
    (setq out
      (strcat out
        (if (vl-string-search ch bad) "_" ch)
      )
    )
    (setq i (1+ i))
  )
  out
)

(defun DT--width-name (width / s)
  (setq s (rtos width 2 6))
  (while (and (vl-string-search "." s)
              (= (substr s (strlen s) 1) "0"))
    (setq s (substr s 1 (1- (strlen s))))
  )
  (if (= (substr s (strlen s) 1) ".")
    (setq s (substr s 1 (1- (strlen s))))
  )
  (vl-string-translate ".-" "_m" s)
)

(defun DT--active-side-height ()
  (if (and (boundp '*DT_ACTIVE_SIDE_HEIGHT*)
           (numberp *DT_ACTIVE_SIDE_HEIGHT*)
           (> *DT_ACTIVE_SIDE_HEIGHT* 0.0))
    *DT_ACTIVE_SIDE_HEIGHT*
    0.0
  )
)

(defun DT--active-side-height-mm ()
  (if (and (boundp '*DT_ACTIVE_SIDE_HEIGHT_MM*)
           (numberp *DT_ACTIVE_SIDE_HEIGHT_MM*)
           (> *DT_ACTIVE_SIDE_HEIGHT_MM* 0.0))
    *DT_ACTIVE_SIDE_HEIGHT_MM*
    0.0
  )
)

(defun DT--active-3d-enabled-p ()
  (if (boundp '*DT_ACTIVE_3D*)
    (if *DT_ACTIVE_3D* T nil)
    (DT--last-3d-enabled)
  )
)

(defun DT--fitting-block-name (kind width / mode sideMm)
  (setq mode (DT--normalize-mode *DT_ACTIVE_MODE*))
  (setq sideMm (DT--active-side-height-mm))
  (strcat
    "e_"
    (DT--name-safe mode)
    "_"
    (DT--name-safe kind)
    "_"
    (DT--width-name width)
    (if (> sideMm 0.0)
      (strcat "_H" (DT--width-name sideMm))
      "")
  )
)

(defun DT--cross2 (u v)
  (- (* (car u) (cadr v)) (* (cadr u) (car v)))
)

(defun DT--vec-angle (u)
  (atan (cadr u) (car u))
)

(defun DT--mirror-for (u v)
  (if (< (DT--cross2 u v) 0.0) -1.0 1.0)
)

(defun DT--local-pts-xform (pts base ang yscale / out p dx dy ca sa x y)
  (setq ca (cos ang)
        sa (sin ang))
  (foreach p pts
    (setq dx (- (car p) (car base))
          dy (- (cadr p) (cadr base))
          x  (+ (* dx ca) (* dy sa))
          y  (+ (* (- dx) sa) (* dy ca)))
    (if (< yscale 0.0) (setq y (- y)))
    (setq out (append out (list (list x y 0.0))))
  )
  out
)

(defun DT--local-bulges-xform (bulges yscale / out b)
  (if bulges
    (progn
      (foreach b bulges
        (setq out
          (append out
            (list
              (if (< yscale 0.0) (- b) b)
            )
          )
        )
      )
      out
    )
  )
)
(defun DT--block-poly-entmake-at (pts closedp bulges elevation / data p b i)
  (if (and pts (> (length pts) 1))
    (progn
      (setq data
        (list
          (cons 0 "LWPOLYLINE")
          (cons 100 "AcDbEntity")
          (cons 8 (DT--layer-linework))
          (cons 370 30)
          (cons 100 "AcDbPolyline")
          (cons 90 (length pts))
          (cons 70 (if closedp 1 0))
          (cons 38 (if (numberp elevation) elevation 0.0))
          (cons 43 0.0)
        )
      )
      (setq i 0)
      (foreach p pts
        (setq data (append data (list (cons 10 (list (car p) (cadr p))))))
        (setq b (if bulges (nth i bulges) 0.0))
        (if (and b (> (abs b) 1e-10))
          (setq data (append data (list (cons 42 b))))
        )
        (setq i (1+ i))
      )
      (entmake data)
    )
  )
)

(defun DT--block-poly-entmake (pts closedp bulges)
  (DT--block-poly-entmake-at pts closedp bulges 0.0)
)

(defun DT--block-line-entmake (a b)
  (if (and a b)
    (entmake
      (list
        '(0 . "LINE")
        '(100 . "AcDbEntity")
        (cons 8 (DT--layer-linework))
        '(370 . 30)
        '(100 . "AcDbLine")
        (cons 10 a)
        (cons 11 b)))
  )
)

(defun DT--block-raised-outline-entmake (pts closedp bulges / height p)
  (setq height (DT--active-side-height))
  (if (and closedp pts (> height 0.0))
    (progn
      (DT--block-poly-entmake-at pts T bulges height)
      (foreach p pts
        (DT--block-line-entmake
          (list (car p) (cadr p) 0.0)
          (list (car p) (cadr p) height)))
    )
  )
)


(defun DT--2d-points-variant (pts / sa i p)
  (setq sa (vlax-make-safearray vlax-vbDouble (cons 0 (1- (* 2 (length pts))))))
  (setq i 0)
  (foreach p pts
    (vlax-safearray-put-element sa i (float (car p)))
    (setq i (1+ i))
    (vlax-safearray-put-element sa i (float (cadr p)))
    (setq i (1+ i))
  )
  (vlax-make-variant sa)
)

(defun DT--clear-block-object (blk / objs obj)
  (vlax-for obj blk
    (setq objs (cons obj objs))
  )
  (foreach obj objs
    (vl-catch-all-apply 'vla-Delete (list obj))
  )
)

(defun DT--set-block-linework-050
  (name / rec ent ed typ pair layerPair nestedName nestedNames)
  ;; Daha once cizimde olusmus ayni adli DT blocklarini da yeni lineweight'e tasir.
  (setq rec (if name (tblobjname "BLOCK" name)))
  (if rec
    (progn
      (setq ent (entnext rec))
      (while (and ent (/= (cdr (assoc 0 (entget ent))) "ENDBLK"))
        (setq ed  (entget ent)
              typ (cdr (assoc 0 ed)))
        (if (member typ '("LINE" "LWPOLYLINE" "POLYLINE" "3DFACE"))
          (progn
            (setq pair (assoc 370 ed)
                  ed   (if pair
                         (subst (cons 370 30) pair ed)
                         (append ed (list (cons 370 30))))
                  layerPair (assoc 8 ed)
                  ed (if layerPair
                       (subst (cons 8 (DT--layer-linework)) layerPair ed)
                       (append ed (list (cons 8 (DT--layer-linework)))))
                  ed (vl-remove-if '(lambda (x) (= (car x) 62)) ed))
            (entmod ed)))
        (if (= typ "HATCH")
          (progn
            (setq layerPair (assoc 8 ed)
                   ed (if layerPair
                        (subst (cons 8 (DT--layer-fitting)) layerPair ed)
                        (append ed (list (cons 8 (DT--layer-fitting)))))
                   ed (vl-remove-if
                        '(lambda (x) (member (car x) '(62 420 430)))
                        ed))
            (entmod ed)))
        (if (= typ "INSERT")
          (progn
            (setq nestedName (cdr (assoc 2 ed)))
            (if (and nestedName
                     (wcmatch (strcase nestedName) "DT$SHELL$*")
                     (not (member (strcase nestedName) nestedNames)))
              (setq nestedNames (cons (strcase nestedName) nestedNames)))))
        (setq ent (entnext ent)))
      (foreach nestedName nestedNames
        (DT--set-block-linework-050 nestedName))
      T)
  )
)

(defun DT--block-poly-vla-at (blk pts closedp bulges elevation / pl i b)
  (if (and blk pts (> (length pts) 1))
    (progn
      (setq pl (vla-AddLightWeightPolyline blk (DT--2d-points-variant pts)))
      (vla-put-Layer pl (DT--layer-linework))
      (vla-put-Lineweight pl 30)
      (vla-put-Closed pl (if closedp :vlax-true :vlax-false))
      (if (numberp elevation) (vla-put-Elevation pl elevation))
      (setq i 0)
      (foreach p pts
        (setq b (if bulges (nth i bulges) 0.0))
        (if (and b (> (abs b) 1e-10))
          (vla-SetBulge pl i b)
        )
        (setq i (1+ i))
      )
      pl
    )
  )
)

(defun DT--block-poly-vla (blk pts closedp bulges)
  (DT--block-poly-vla-at blk pts closedp bulges 0.0)
)

(defun DT--block-raised-outline-vla (blk pts closedp bulges / height p lineObj)
  (setq height (DT--active-side-height))
  (if (and blk closedp pts (> height 0.0))
    (progn
      (DT--block-poly-vla-at blk pts T bulges height)
      (foreach p pts
        (setq lineObj
          (vla-AddLine
            blk
            (vlax-3d-point (list (car p) (cadr p) 0.0))
            (vlax-3d-point (list (car p) (cadr p) height))))
        (if lineObj
          (progn
            (vla-put-Layer lineObj (DT--layer-linework))
            (vla-put-Lineweight lineObj 30)))
      )
    )
  )
)


(defun DT--block-hatch-vla (blk boundaryObj / pattern color hatch sa var ok)
  (if (and blk boundaryObj)
    (progn
      (setq pattern (car (DT--hatch-pattern-info (DT--mode-hatch-pattern *DT_ACTIVE_MODE*)))
            color   (DT--mode-hatch-color *DT_ACTIVE_MODE*))
      (setq hatch (vl-catch-all-apply 'vla-AddHatch (list blk 1 pattern :vlax-true)))
      (if (not (vl-catch-all-error-p hatch))
        (progn
          (setq sa (vlax-make-safearray vlax-vbObject '(0 . 0)))
          (vlax-safearray-put-element sa 0 boundaryObj)
          (setq var (vlax-make-variant sa))
          (setq ok (vl-catch-all-apply 'vla-AppendOuterLoop (list hatch var)))
          (if (not (vl-catch-all-error-p ok))
            (progn
              (vl-catch-all-apply 'vla-put-Layer (list hatch (DT--layer-fitting)))
              (vl-catch-all-apply 'vla-put-Color (list hatch 256))
              (vl-catch-all-apply 'vla-put-PatternScale (list hatch (DT--hatch-scale)))
              (vl-catch-all-apply 'vla-Evaluate (list hatch))
              hatch
            )
            (vl-catch-all-apply 'vla-Delete (list hatch))
          )
        )
      )
    )
  )
)

(defun DT--block-shell-insert-vla (blk shellName / obj)
  (if (and blk shellName (tblsearch "BLOCK" shellName))
    (progn
      (setq obj
        (vl-catch-all-apply
          'vla-InsertBlock
          (list blk (vlax-3d-point '(0.0 0.0 0.0)) shellName 1.0 1.0 1.0 0.0)))
      (if (and obj (not (vl-catch-all-error-p obj)))
        (progn
          (vl-catch-all-apply 'vla-put-Layer (list obj (DT--layer-fitting)))
          obj)
      )
    )
  )
)

(defun DT--block-shell-insert-entmake (shellName)
  (if (and shellName (tblsearch "BLOCK" shellName))
    (entmake
      (list
        '(0 . "INSERT")
        (cons 2 shellName)
        (cons 8 (DT--layer-fitting))
        '(10 0.0 0.0 0.0)
        '(41 . 1.0)
        '(42 . 1.0)
        '(43 . 1.0)
        '(50 . 0.0)))
  )
)

(defun DT--block-references-block-p (name nestedName / rec ent found)
  (setq rec (if name (tblobjname "BLOCK" name)))
  (if rec
    (progn
      (setq ent (entnext rec))
      (while (and ent (/= (cdr (assoc 0 (entget ent))) "ENDBLK") (null found))
        (if (and (= (cdr (assoc 0 (entget ent))) "INSERT")
                 (= (strcase (cdr (assoc 2 (entget ent)))) (strcase nestedName)))
          (setq found T))
        (setq ent (entnext ent)))))
  found
)

(defun DT--populate-fitting-block-vla (blk shapes base ang yscale shellName / shape local bulges pl hatch ok)
  (if (and blk shapes)
    (progn
      (setq ok T)
      (foreach shape shapes
        (setq local
          (DT--local-pts-xform
            (car shape)
            base
            ang
            yscale
          )
        )
        (setq bulges (DT--local-bulges-xform (caddr shape) yscale))
        (setq pl (DT--block-poly-vla blk local (cadr shape) bulges))
        (if (not pl) (setq ok nil))
        (if (and (cadr shape) pl)
          (progn
            (setq hatch (DT--block-hatch-vla blk pl))
            (if (not hatch) (setq ok nil))
          )
        )
      )
      (if shellName
        (if (not (DT--block-shell-insert-vla blk shellName)) (setq ok nil)))
      ok
    )
  )
)
(defun DT--redefine-fitting-block (name shapes base ang yscale shellName / blk rec doc blks)
  (vl-load-com)
  (setq rec (tblobjname "BLOCK" name))
  (setq blk
    (cond
      (rec (vlax-ename->vla-object rec))
      (T
        (setq doc  (vla-get-ActiveDocument (vlax-get-acad-object))
              blks (vla-get-Blocks doc))
        (vl-catch-all-apply 'vla-Item (list blks name))
      )
    )
  )
  (if (and blk (not (vl-catch-all-error-p blk)))
    (progn
      (DT--clear-block-object blk)
      (DT--populate-fitting-block-vla blk shapes base ang yscale shellName)
      (DT--block-associate-hatches name)
    )
  )
)
(defun DT--mark-fitting-insert (ins kind width / app ed payload)
  (setq app "DT_FITTING")
  (if (not (tblsearch "APPID" app)) (regapp app))
  (if (and ins (entget ins))
    (progn
      (setq payload
        (list app
          (cons 1000 (if kind kind ""))
          (cons 1040 (if (numberp width) width 0.0))
        )
      )
      (setq ed (entget ins '("*")))
      (setq ed (DT--xdata-set-app ed app payload))
      (entmod ed)
      (entupd ins)
    )
  )
  (DT--cache-fitting-insert ins)
  ins
)

(defun DT--fitting-display-app () "DT_FITTING_DISPLAY")

(defun DT--fitting-display-data (ins / app ed xd rec item source enabled)
  (setq app (DT--fitting-display-app))
  (if (and ins (entget ins) (tblsearch "APPID" app))
    (progn
      (setq ed  (entget ins (list app))
            xd  (assoc -3 ed)
            rec (if xd (cadr xd) nil))
      (if (and rec (= (car rec) app))
        (foreach item (cdr rec)
          (cond
            ((= (car item) 1000) (setq source (cdr item)))
            ((= (car item) 1070) (setq enabled (/= (cdr item) 0))))))))
  (if source (list source enabled))
)

(defun DT--set-fitting-display-data (ins source enabled / app ed payload)
  (setq app (DT--fitting-display-app))
  (if (not (tblsearch "APPID" app)) (regapp app))
  (if (and ins source (setq ed (entget ins '("*"))))
    (progn
      (setq payload
        (list app
          (cons 1000 source)
          (cons 1070 (if enabled 1 0))))
      (setq ed (DT--xdata-set-app ed app payload))
      (entmod ed)
      (entupd ins)
      ins))
)

(defun DT--fitting-2d-block-name (source / limit)
  (setq limit (- 250 (strlen "$2D_LOCAL3")))
  (strcat
    (if (> (strlen source) limit) (substr source 1 limit) source)
    "$2D_LOCAL3")
)

(defun DT--fitting-shell-reference-object-p (obj / objectName blockName)
  (setq objectName
    (vl-catch-all-apply 'vla-get-ObjectName (list obj)))
  (if (and objectName
           (not (vl-catch-all-error-p objectName))
           (= objectName "AcDbBlockReference"))
    (progn
      (setq blockName (vl-catch-all-apply 'vla-get-Name (list obj)))
      (and blockName
           (not (vl-catch-all-error-p blockName))
           (wcmatch (strcase blockName) "DT$SHELL$*"))))
)

(defun DT--projected-face-shape-from-ent
  (ent / ed code pair pt pts clean first last area)
  (setq ed (if ent (entget ent)))
  (if (= (cdr (assoc 0 ed)) "3DFACE")
    (progn
      (foreach code '(10 11 12 13)
        (setq pair (assoc code ed))
        (if pair
          (progn
            (setq pt (list (car (cdr pair)) (cadr (cdr pair)) 0.0))
            (if (or (null pts)
                    (not (equal pt (g365_last pts) 0.0000001)))
              (setq pts (append pts (list pt)))))))
      (if (and (> (length pts) 2)
               (equal (car pts) (g365_last pts) 0.0000001))
        (setq pts (DT--hatch-drop-last pts)))
      (if (> (length pts) 2)
        (progn
          (setq first (car pts)
                clean (list first))
          (foreach pt (cdr pts)
            (if (not
                  (vl-some
                    '(lambda (known) (equal pt known 0.0000001))
                    clean))
              (setq clean (append clean (list pt)))))
          (setq area (abs (DT--polygon-area2 clean)))
          (if (and (> (length clean) 2) (> area 0.000001))
            (list clean T nil)))))
  )
)

(defun DT--face-plan-points-from-ent (ent / ed code pair p out)
  (setq ed (if ent (entget ent)))
  (if (= (cdr (assoc 0 ed)) "3DFACE")
    (foreach code '(10 11 12 13)
      (setq pair (assoc code ed))
      (if pair
        (progn
          (setq p (list (car (cdr pair)) (cadr (cdr pair)) 0.0))
          (if (not
                (vl-some
                  '(lambda (known) (equal p known 0.0000001))
                  out))
            (setq out (append out (list p))))))))
  out
)

(defun DT--plan-point-less-p (a b)
  (or
    (< (car a) (car b))
    (and (equal (car a) (car b) 0.0000001)
         (< (cadr a) (cadr b))))
)

(defun DT--unique-plan-points (pts / out p)
  (foreach p pts
    (if (not
          (vl-some
            '(lambda (known) (equal p known 0.0000001))
            out))
      (setq out (append out (list p)))))
  out
)

(defun DT--plan-turn-cross (a b c)
  (-
    (* (- (car b) (car a)) (- (cadr c) (cadr a)))
    (* (- (cadr b) (cadr a)) (- (car c) (car a))))
)

(defun DT--convex-hull-plan (pts / sorted lower upper p n)
  (setq sorted
    (vl-sort
      (DT--unique-plan-points pts)
      'DT--plan-point-less-p))
  (if (> (length sorted) 2)
    (progn
      (foreach p sorted
        (while
          (and
            (> (length lower) 1)
            (<=
              (DT--plan-turn-cross
                (nth (- (length lower) 2) lower)
                (g365_last lower)
                p)
              0.0000001))
          (setq lower (DT--hatch-drop-last lower)))
        (setq lower (append lower (list p))))
      (foreach p (reverse sorted)
        (while
          (and
            (> (length upper) 1)
            (<=
              (DT--plan-turn-cross
                (nth (- (length upper) 2) upper)
                (g365_last upper)
                p)
              0.0000001))
          (setq upper (DT--hatch-drop-last upper)))
        (setq upper (append upper (list p))))
      (setq lower (DT--hatch-drop-last lower)
            upper (DT--hatch-drop-last upper))
      (append lower upper))
  )
)

(defun DT--ensure-fitting-2d-block
  (source / target rec ent ed typ shape polyShapes facePts hull made)
  (setq target (DT--fitting-2d-block-name source))
  (if (tblsearch "BLOCK" target)
    target
    (if (and source (tblsearch "BLOCK" source))
      (progn
        (entmake
          (list
            '(0 . "BLOCK")
            (cons 2 target)
            '(70 . 0)
            '(10 0.0 0.0 0.0)))
        (setq rec (tblobjname "BLOCK" source)
              ent (if rec (entnext rec)))
        (while (and ent (/= (cdr (assoc 0 (entget ent))) "ENDBLK"))
          (setq ed  (entget ent)
                typ (cdr (assoc 0 ed)))
          (cond
            ((= typ "LWPOLYLINE")
              (setq shape (DT--closed-poly-shape-from-ent ent))
              (if shape
                (setq polyShapes (append polyShapes (list shape)))))
            ((= typ "3DFACE")
              (setq facePts
                (append facePts (DT--face-plan-points-from-ent ent)))))
          (setq ent (entnext ent)))
        (if polyShapes
          (foreach shape polyShapes
            (DT--block-poly-entmake
              (car shape) (cadr shape) (caddr shape))
            (DT--block-local-2d-hatch-entmake
              (car shape) (caddr shape))
            (setq made T))
          (progn
            ;; Yalniz 3DFACE kullanan elevation fittingleri cok sayida yuz
            ;; izdushumu yerine tek, sade bir ust-gorunus konturu alir.
            (setq hull (DT--convex-hull-plan facePts))
            (if (> (length hull) 2)
              (progn
                (DT--block-poly-entmake hull T nil)
                (DT--block-local-2d-hatch-entmake hull nil)
                (setq made T)))))
        (entmake '((0 . "ENDBLK")))
        (if made
          (progn
            (DT--set-block-linework-050 target)
            target)
          (setq target nil)))
      )
    )
  target
)

(defun DT--set-insert-block-name (ins name / ed pair)
  (if (and ins name (tblsearch "BLOCK" name) (setq ed (entget ins '("*"))))
    (progn
      (setq pair (assoc 2 ed))
      (if pair
        (setq ed (subst (cons 2 name) pair ed))
        (setq ed (append ed (list (cons 2 name)))))
      (if (entmod ed)
        (progn (entupd ins) ins))))
)

(defun DT--apply-fitting-3d-mode (ins enabled / ed current data source target)
  (if (and ins
           (setq ed (entget ins '("*")))
           (= (cdr (assoc 0 ed)) "INSERT"))
    (progn
      (setq current (cdr (assoc 2 ed))
            data    (DT--fitting-display-data ins)
            source  (if data (car data) nil))
      (if (null source)
        (setq source current))
      (if enabled
        (if (tblsearch "BLOCK" source)
          (DT--set-insert-block-name ins source))
        (progn
          (setq target (DT--ensure-fitting-2d-block source))
          (if target (DT--set-insert-block-name ins target))))
      (DT--set-fitting-display-data ins source enabled)))
  ins
)

(defun DT--fitting-3d-enabled-p (ins / data)
  (setq data (DT--fitting-display-data ins))
  (if data
    (if (cadr data) T nil)
    T)
)

(defun DT--fitting-name-p (name / u)
  (setq u (if name (strcase name) ""))
  (and
    (> (strlen u) 2)
    (= (substr u 1 2) "E_")
    (or
      (vl-string-search "_T_" u)
      (vl-string-search "_ART" u)
      (vl-string-search "_ESNEK" u)
      (vl-string-search "_ELEVATION_" u)
      (vl-string-search "_D" u)
    )
  )
)

(defun DT--fitting-insert-p (ent / ed name)
  (if (and ent (setq ed (entget ent '("DT_FITTING"))) (= (cdr (assoc 0 ed)) "INSERT"))
    (or
      (assoc -3 ed)
      (progn
        (setq name (cdr (assoc 2 ed)))
        (DT--fitting-name-p name)
      )
    )
  )
)

(defun DT--collect-fitting-inserts (/ ss i ent ed lay out)
  (setq ss
    (ssget "_X"
      (list (cons 0 "INSERT"))))
  (if ss
    (progn
      (setq i 0)
      (while (< i (sslength ss))
        (setq ent (ssname ss i)
              ed  (entget ent)
              lay (if ed (cdr (assoc 8 ed)) nil))
        (if (and (DT--entity-alive-p ent)
                 lay
                 (DT--tray-visible-layer-p lay)
                 (DT--fitting-insert-p ent))
          (setq out (cons ent out)))
        (setq i (1+ i)))))
  (reverse out)
)

(defun DT--fitting-inserts ()
  (if (and (boundp '*DT_FITTING_CACHE_ACTIVE*)
           *DT_FITTING_CACHE_ACTIVE*)
    *DT_FITTING_CACHE*
    (DT--collect-fitting-inserts))
)

(defun DT--cache-fitting-insert (ent)
  (if (and ent
           (DT--entity-alive-p ent)
           (boundp '*DT_FITTING_CACHE_ACTIVE*)
           *DT_FITTING_CACHE_ACTIVE*
           (not (member ent *DT_FITTING_CACHE*)))
    (setq *DT_FITTING_CACHE* (cons ent *DT_FITTING_CACHE*)))
  ent
)

(defun DT--replace-last-bulge (lst val / out i n x)
  (setq i 0
        n (length lst))
  (foreach x lst
    (setq out
      (append out
        (list
          (if (= i (1- n)) val x)
        )
      )
    )
    (setq i (1+ i))
  )
  out
)

(defun DT--closed-poly-shape-from-ent (ent / ed item flags pts bulges)
  (setq ed (entget ent))
  (setq flags (if (assoc 70 ed) (cdr (assoc 70 ed)) 0))
  (if (and (= (cdr (assoc 0 ed)) "LWPOLYLINE")
           (= (logand flags 1) 1))
    (progn
      (foreach item ed
        (cond
          ((= (car item) 10)
            (setq pts (append pts (list (list (car (cdr item)) (cadr (cdr item)) 0.0))))
            (setq bulges (append bulges (list 0.0)))
          )
          ((= (car item) 42)
            (if bulges
              (setq bulges (DT--replace-last-bulge bulges (cdr item)))
            )
          )
        )
      )
      (if (> (length pts) 1)
        (list pts T bulges)
      )
    )
  )
)
(defun DT--collapse-open-block-polyline (ent / ed item flags first out changed)
  (setq ed (entget ent)
        flags (if (assoc 70 ed) (cdr (assoc 70 ed)) 0))
  (foreach item ed
    (if (and (= (car item) 10) (null first))
      (setq first (cdr item))
    )
  )
  (if first
    (progn
      (foreach item ed
        (cond
          ((= (car item) 10)
            (setq out (append out (list (cons 10 first)))))
          ((= (car item) 70)
            (setq out (append out (list (cons 70 (logior flags 1))))))
          ((= (car item) 42)
            (setq out (append out (list (cons 42 0.0)))))
          (T
            (setq out (append out (list item))))
        )
      )
      (if (not (assoc 70 ed))
        (setq out (append out (list (cons 70 1))))
      )
      (if (entmod out)
        (progn
          (entupd ent)
          (setq changed T)
        )
      )
    )
  )
  changed
)
(defun DT--cleanup-fitting-block-inner-lines (/ rec name blk ent ed next flags cleaned)
  (setq rec (tblnext "BLOCK" T)
        cleaned 0)
  (while rec
    (setq name (cdr (assoc 2 rec)))
    (if (and name (DT--fitting-name-p name) (setq blk (tblobjname "BLOCK" name)))
      (progn
        (setq ent (entnext blk))
        (while (and ent (/= (cdr (assoc 0 (entget ent))) "ENDBLK"))
          (setq next (entnext ent)
                ed   (entget ent))
          (setq flags (if (assoc 70 ed) (cdr (assoc 70 ed)) 0))
          (if (and (= (cdr (assoc 0 ed)) "LWPOLYLINE")
                   (= (logand flags 1) 0))
            (if (DT--collapse-open-block-polyline ent)
              (setq cleaned (1+ cleaned))
            )
          )
          (setq ent next)
        )
      )
    )
    (setq rec (tblnext "BLOCK"))
  )
  cleaned
)
(defun DT--fitting-insert-width (ent fallback / ed xd rec x val)
  (setq val fallback)
  (if (and ent (entget ent))
    (progn
      (setq ed (entget ent '("DT_FITTING"))
            xd (assoc -3 ed))
      (if xd
        (progn
          (setq rec (cadr xd))
          (foreach x (cdr rec)
            (if (= (car x) 1040) (setq val (cdr x)))
          )
        )
      )
    )
  )
  (if (and (numberp val) (> val 0.0)) val fallback)
)

(defun DT--variant-list (v / vv out)
  (setq vv (vl-catch-all-apply 'vlax-variant-value (list v)))
  (if (vl-catch-all-error-p vv)
    (setq vv v)
  )
  (setq out (vl-catch-all-apply 'vlax-safearray->list (list vv)))
  (if (vl-catch-all-error-p out) nil out)
)

(defun DT--point-in-box-p (pt mn mx tol)
  (and pt mn mx
       (<= (- (car mn) tol) (car pt) (+ (car mx) tol))
       (<= (- (cadr mn) tol) (cadr pt) (+ (cadr mx) tol)))
)

(defun DT--point-in-fitting-box-p (pt ent tol / obj mn mx ok)
  (if (and pt ent (entget ent))
    (progn
      (setq obj (vl-catch-all-apply 'vlax-ename->vla-object (list ent)))
      (if (or (vl-catch-all-error-p obj) (null obj))
        nil
        (progn
          (setq ok (vl-catch-all-apply 'vla-getboundingbox (list obj 'mn 'mx)))
          (if (vl-catch-all-error-p ok)
            nil
            (DT--point-in-box-p pt (DT--variant-list mn) (DT--variant-list mx) tol)
          )
        )
      )
    )
  )
)

(defun DT--nearest-fitting-center-for-point
  (pt width / ent ed ip lay activeLayer fw tol d best bestD)
  (if (and pt (DT--layer-fitting))
    (progn
      (setq activeLayer (strcase (DT--layer-fitting)))
      (foreach ent (DT--fitting-inserts)
        (setq ed (entget ent)
              ip  (if ed (cdr (assoc 10 ed)) nil)
              lay (if ed (cdr (assoc 8 ed)) nil))
        (if (and ip
                 lay
                 (= (strcase lay) activeLayer)
                 (or (DT--same-active-elevation-p ent)
                     (DT--elevation-fitting-insert-p ent)))
          (progn
            (setq fw  (DT--fitting-insert-width ent width)
                  tol (max 1.0 (/ fw 20.0))
                  d   (distance
                        (list (car pt) (cadr pt) 0.0)
                        (list (car ip) (cadr ip) 0.0)))
            (if (and
                  (<= d (+ (* fw 4.0) tol))
                  (or
                    (<= d (+ (* fw 1.25) tol))
                    (DT--point-in-fitting-box-p pt ent tol)
                  )
                  (or (null bestD) (< d bestD))
                )
              (setq bestD d
                    best  (list (car ip) (cadr ip) 0.0))
            )
          )
        )
      )
    )
  )
  best
)

(defun DT--translate-pts (pts dx dy / out p)
  (foreach p pts
    (setq out
      (append out
        (list
          (list (+ (car p) dx) (+ (cadr p) dy) 0.0)
        )
      )
    )
  )
  out
)

(defun DT--snap-poly-ends-to-fitting-blocks (pts width / out p dx dy)
  (setq out pts)
  (if (and out (> (length out) 1))
    (progn
      (setq p (DT--nearest-fitting-center-for-point (car out) width))
      (if p
        (progn
          (setq dx (- (car p) (caar out))
                dy (- (cadr p) (cadar out)))
          (setq out (DT--translate-pts out dx dy))
        )
        (progn
          (setq p (DT--nearest-fitting-center-for-point (g365_last out) width))
          (if p
            (progn
              (setq dx (- (car p) (car (g365_last out)))
                    dy (- (cadr p) (cadr (g365_last out))))
              (setq out (DT--translate-pts out dx dy))
            )
          )
        )
      )
    )
  )
  out
)
(defun DT--delete-existing-fittings-at (pt lay tol / ent ed ip)
  (if (and pt lay (/= lay ""))
    (progn
      (foreach ent (DT--fitting-inserts)
        (setq ed (entget ent)
              ip (if ed (cdr (assoc 10 ed)) nil))
        (if (and ip
                 (= (strcase (cdr (assoc 8 ed))) (strcase lay))
                 (DT--same-active-elevation-p ent)
                 (<= (distance (list (car ip) (cadr ip) 0.0) pt) tol))
          (entdel ent)
        )
      )
    )
  )
)
(defun DT--shapes-need-bulge-p (shapes / hit shape b)
  (foreach shape shapes
    (foreach b (caddr shape)
      (if (and b (> (abs b) 1e-10)) (setq hit T))
    )
  )
  hit
)

(defun DT--block-has-nonzero-bulge-p (name / rec ent ed item hit)
  (setq rec (tblobjname "BLOCK" name))
  (if rec
    (progn
      (setq ent (entnext rec))
      (while (and ent (/= (cdr (assoc 0 (entget ent))) "ENDBLK"))
        (setq ed (entget ent))
        (foreach item ed
          (if (and (= (car item) 42) (> (abs (cdr item)) 1e-10))
            (setq hit T)
          )
        )
        (setq ent (entnext ent))
      )
    )
  )
  hit
)

(defun DT--block-has-hatch-p (name / rec ent hit)
  (setq rec (tblobjname "BLOCK" name))
  (if rec
    (progn
      (setq ent (entnext rec))
      (while (and ent (/= (cdr (assoc 0 (entget ent))) "ENDBLK"))
        (if (= (cdr (assoc 0 (entget ent))) "HATCH")
          (setq hit T)
        )
        (setq ent (entnext ent))
      )
    )
  )
  hit
)

(defun DT--fallback-fitting-block-name (name shapes / needs i candidate)
  (setq needs (DT--shapes-need-bulge-p shapes)
        i 1
        candidate (strcat name "_F"))
  (while
    (and
      (tblsearch "BLOCK" candidate)
      (or
        (not (DT--block-has-hatch-p candidate))
        (and needs (not (DT--block-has-nonzero-bulge-p candidate)))
      )
    )
    (setq i (1+ i)
          candidate (strcat name "_F" (itoa i)))
  )
  candidate
)

(defun DT--stable-fitting-kind-p (kind / value)
  ;; Flexible fittings may have the same angle and maximum width but
  ;; different arm widths. Fixed elbows, T and + fittings are reusable.
  (setq value (strcase (if kind kind "")))
  (not (wcmatch value "ESNEK*"))
)

(defun DT--fitting-definition-cache-key (name)
  (strcase
    (strcat
      (if name name "")
      "|"
      (if (and (> (DT--active-side-height) 0.0)
               (> (DT--plan-material-thickness) 0.0))
        (DT--shell-style-token)
        "NOSHELL")))
)

(defun DT--document-cache-key ()
  (strcase
    (strcat
      (if (getvar "DWGPREFIX") (getvar "DWGPREFIX") "")
      (if (getvar "DWGNAME") (getvar "DWGNAME") "")))
)

(defun DT--ensure-fitting-definition-session-cache (/ key)
  ;; Block definitions already live in the drawing. Keep their verified names
  ;; in session memory so every new DT command does not inspect them again.
  (setq key (DT--document-cache-key))
  (if (or
        (not (boundp '*DT_FITTING_DEFINITION_CACHE_DOCUMENT*))
        (/= *DT_FITTING_DEFINITION_CACHE_DOCUMENT* key))
    (setq *DT_FITTING_DEFINITION_CACHE_DOCUMENT* key
          *DT_FITTING_DEFINITION_CACHE* nil)
    (if (not (boundp '*DT_FITTING_DEFINITION_CACHE*))
      (setq *DT_FITTING_DEFINITION_CACHE* nil)))
  *DT_FITTING_DEFINITION_CACHE*
)

(defun DT--fitting-definition-cache-get (name / rec)
  (if (and name
           (boundp '*DT_FITTING_CACHE_ACTIVE*)
           *DT_FITTING_CACHE_ACTIVE*)
    (progn
      (setq rec
        (assoc
          (DT--fitting-definition-cache-key name)
          *DT_FITTING_DEFINITION_CACHE*))
      (if (and rec
               (tblsearch "BLOCK" (cadr rec))
               (or (null (caddr rec))
                   (tblsearch "BLOCK" (caddr rec))))
        rec)))
)

(defun DT--fitting-definition-cache-put
  (requestedName actualName shellName / key)
  (if (and requestedName
           actualName
           (tblsearch "BLOCK" actualName)
           (boundp '*DT_FITTING_CACHE_ACTIVE*)
           *DT_FITTING_CACHE_ACTIVE*)
    (progn
      (setq key (DT--fitting-definition-cache-key requestedName))
      (if (null (assoc key *DT_FITTING_DEFINITION_CACHE*))
        (setq *DT_FITTING_DEFINITION_CACHE*
          (cons
            (list key actualName shellName)
            *DT_FITTING_DEFINITION_CACHE*)))))
  actualName
)

(defun DT--create-fitting-block-def-vla (name shapes base ang yscale shellName / doc blks blk)
  (vl-load-com)
  (if (and name shapes)
    (progn
      (setq doc  (vla-get-ActiveDocument (vlax-get-acad-object))
            blks (vla-get-Blocks doc)
            blk  (vla-Add blks (vlax-3d-point (list 0.0 0.0 0.0)) name))
      (DT--populate-fitting-block-vla blk shapes base ang yscale shellName)
    )
  )
)

(defun DT--create-fitting-block-def (name shapes base ang yscale shellName / shape local bulges boundary)
  (if (and name shapes)
    (progn
      (entmake
        (list
          (cons 0 "BLOCK")
          (cons 2 name)
          (cons 70 0)
          (cons 10 (list 0.0 0.0 0.0))
        )
      )
      (foreach shape shapes
        (setq local
          (DT--local-pts-xform
            (car shape)
            base
            ang
            yscale
          )
        )
        (setq bulges (DT--local-bulges-xform (caddr shape) yscale))
        (DT--block-poly-entmake local (cadr shape) bulges)
        (setq boundary (entlast))
        (if (cadr shape)
          (DT--block-hatch-entmake local bulges boundary)
        )
      )
      (if shellName (DT--block-shell-insert-entmake shellName))
      (entmake '((0 . "ENDBLK")))
      (DT--block-associate-hatches name)
      T
    )
  )
)
(defun DT--make-fitting-block
  (kind width base shapes ang yscale
    / name requestedName shellName needs ok ins cached cacheRec)
  (setq name          (DT--fitting-block-name kind width)
        requestedName name)
  (if (and name base shapes)
    (progn
      (setq cacheRec
        (if (DT--stable-fitting-kind-p kind)
          (DT--fitting-definition-cache-get requestedName)))
      (if cacheRec
        (setq name      (cadr cacheRec)
              shellName (caddr cacheRec)
              ok        T
              cached    T)
        (progn
          (setq shellName
                  (DT--ensure-fitting-shell-block
                    name shapes base ang yscale)
                needs (DT--shapes-need-bulge-p shapes))
          (if (and shellName
                   (tblsearch "BLOCK" name)
                   (not (DT--block-references-block-p name shellName)))
            (setq name (strcat name "_O2")))
          (cond
            ((and
               (tblsearch "BLOCK" name)
               (DT--stable-fitting-kind-p kind)
               (DT--block-has-hatch-p name)
               (or (not needs) (DT--block-has-nonzero-bulge-p name))
               (or (not shellName)
                   (DT--block-references-block-p name shellName)))
              (setq ok T cached T))
            ((not (tblsearch "BLOCK" name))
              (DT--create-fitting-block-def
                name shapes base ang yscale shellName))
            (T
              (setq ok
                (vl-catch-all-apply
                  'DT--redefine-fitting-block
                  (list name shapes base ang yscale shellName)))
              (if
                (not
                  (and
                    (not (vl-catch-all-error-p ok))
                    ok
                    (DT--block-has-hatch-p name)
                    (or
                      (not needs)
                      (DT--block-has-nonzero-bulge-p name))))
                (progn
                  (setq name
                    (DT--fallback-fitting-block-name name shapes))
                  (if (not (tblsearch "BLOCK" name))
                    (DT--create-fitting-block-def
                      name shapes base ang yscale shellName)
                    (progn
                      (setq ok
                        (vl-catch-all-apply
                          'DT--redefine-fitting-block
                          (list
                            name shapes base ang yscale shellName)))
                      (if (or
                            (vl-catch-all-error-p ok)
                            (not ok))
                        nil)))
                ))
            ))
          (if (not cached)
            (progn
              (if shellName
                (DT--set-block-linework-050 shellName))
              (DT--block-associate-hatches name)
              (DT--set-block-linework-050 name)))
          (if (DT--stable-fitting-kind-p kind)
            (DT--fitting-definition-cache-put
              requestedName name shellName))
        )
      )
      (setq ins
        (entmakex
          (list
            (cons 0 "INSERT")
            (cons 2 name)
            (cons 8 (DT--layer-fitting))
             (cons 10 (DT--point-at-elevation base (DT--active-elevation)))
            (cons 41 1.0)
            (cons 42 yscale)
            (cons 43 1.0)
            (cons 50 ang)
          )
        )
      )
      (DT--mark-fitting-insert ins kind width)
      (DT--apply-fitting-3d-mode ins (DT--active-3d-enabled-p))
      ins
    )
  )
)

(defun DT--raise-pts (pts height / out p)
  (foreach p pts
    (setq out
      (append out
        (list
          (list
            (car p)
            (cadr p)
            (+ (if (caddr p) (caddr p) 0.0) height)))))
  )
  out
)

(defun DT--block-raised-outline3d (pts / height topPts p topP)
  (setq height (DT--active-side-height))
  (if (and pts (> height 0.0))
    (progn
      (setq topPts (DT--raise-pts pts height))
      (DT--make-poly3d (DT--layer-linework) topPts T)
      (while pts
        (setq p    (car pts)
              topP (car topPts))
        (DT--block-line-entmake p topP)
        (setq pts    (cdr pts)
              topPts (cdr topPts))
      )
    )
  )
)

(defun DT--elevation-arc-required-p (slope / limit)
  ;; Paletten girilen esik gecilince esnek govde ve dik ara tava kullanilir.
  (setq limit
    (* pi
       (/ (DT--active-elevation-angle) 180.0)))
  (> (abs (atan slope)) (+ limit 1e-9))
)

(defun DT--elevation-linear-profile-points (newWidth oldWidth span slope / oldHalf newHalf)
  (setq oldHalf (/ oldWidth 2.0)
        newHalf (/ newWidth 2.0))
  (list
    (list
      (list (- span) oldHalf (* (- span) slope))
      (list span newHalf (* span slope)))
    (list
      (list (- span) (- oldHalf) (* (- span) slope))
      (list span (- newHalf) (* span slope))))
)

(defun DT--elevation-profile-points (newWidth oldWidth span slope divisions / count i ratio run absSlope direction theta sinTheta radius rise startZ centerZ startAngle angle x half z upper lower)
  ;; Tek yonlu dairesel dusuy kurp: eski yatay tavaya ve yeni egimli
  ;; orta tavaya tegettir. Orta tavanin ucu, bu profilin +span ucuna
  ;; tasindigi icin egri geri donmez ve block altinda duz parca kalmaz.
  (setq count    (max 4 (fix divisions))
        run      (* 2.0 span)
        absSlope (abs slope)
        i        0)
  (if (< absSlope 1e-8)
    (DT--elevation-linear-profile-points newWidth oldWidth span slope)
    (progn
      (setq direction  (if (< slope 0.0) -1.0 1.0)
            theta      (atan absSlope)
            sinTheta   (sin theta)
            radius     (/ run sinTheta)
            rise       (* direction radius (- 1.0 (cos theta)))
            startZ     (/ (- rise) 2.0)
            centerZ    (+ startZ (* direction radius))
            startAngle (* (- direction) (/ pi 2.0)))
      (while (<= i count)
        (setq ratio (/ (float i) count)
              angle (+ startAngle (* direction theta ratio))
              x     (+ (- span) (* radius (cos angle)))
              z     (+ centerZ (* radius (sin angle)))
              half  (+ (/ oldWidth 2.0)
                       (* (- (/ newWidth 2.0) (/ oldWidth 2.0)) ratio))
              upper (append upper (list (list x half z)))
              lower (append lower (list (list x (- half) z)))
              i     (1+ i)))
      (list upper lower))
  )
)

(defun DT--profile-shift-y (pts amount / out p)
  (foreach p pts
    (setq out
      (append out
        (list (list (car p) (+ (cadr p) amount) (if (caddr p) (caddr p) 0.0))))))
  out
)

(defun DT--profile-offset-normal-xz (pts amount / count i p before after dx dz tangentLen nx nz out)
  ;; Elevation profilini her noktadaki yerel tegete dik tasir. Boylece
  ;; egri diklesse bile yanak yuksekligi ve malzeme kalinligi sabit kalir.
  (setq count (length pts)
        i 0)
  (while (< i count)
    (setq p (nth i pts)
          before (if (> i 0) (nth (1- i) pts) p)
          after  (if (< i (1- count)) (nth (1+ i) pts) p))
    (cond
      ((and (= i 0) (>= count 3))
        (setq dx (+ (* -3.0 (car p))
                    (*  4.0 (car (nth 1 pts)))
                    (- (car (nth 2 pts))))
              dz (+ (* -3.0 (if (caddr p) (caddr p) 0.0))
                    (*  4.0 (if (caddr (nth 1 pts)) (caddr (nth 1 pts)) 0.0))
                    (- (if (caddr (nth 2 pts)) (caddr (nth 2 pts)) 0.0)))))
      ((and (= i (1- count)) (>= count 3))
        (setq dx (+ (*  3.0 (car p))
                    (* -4.0 (car (nth (- count 2) pts)))
                    (car (nth (- count 3) pts)))
              dz (+ (*  3.0 (if (caddr p) (caddr p) 0.0))
                    (* -4.0 (if (caddr (nth (- count 2) pts))
                              (caddr (nth (- count 2) pts)) 0.0))
                    (if (caddr (nth (- count 3) pts))
                      (caddr (nth (- count 3) pts)) 0.0))))
      (T
        (setq dx (- (car after) (car before))
              dz (- (if (caddr after) (caddr after) 0.0)
                    (if (caddr before) (caddr before) 0.0)))))
    (setq tangentLen (sqrt (+ (* dx dx) (* dz dz))))
    (if (< tangentLen 1e-9)
      (setq nx 0.0 nz 1.0)
      (setq nx (/ (- dz) tangentLen)
            nz (/ dx tangentLen)))
    (if (< nz 0.0)
      (setq nx (- nx) nz (- nz)))
    (setq out
      (append
        out
        (list
          (list
            (+ (car p) (* amount nx))
            (cadr p)
            (+ (if (caddr p) (caddr p) 0.0) (* amount nz)))))
      i (1+ i)))
  out
)

(defun DT--block-elevation-curved-geometry (newWidth oldWidth span slope arcP / profile upper lower sideHeight thickness innerUpper innerLower floorUpper floorLower topUpper topLower innerTopUpper innerTopLower i n *DT_BLOCK_FACE_UNASSOC*)
  (setq *DT_BLOCK_FACE_UNASSOC* arcP
        profile    (if arcP
                     (DT--elevation-profile-points newWidth oldWidth span slope 8)
                     (DT--elevation-linear-profile-points newWidth oldWidth span slope))
        upper      (car profile)
        lower      (cadr profile)
        sideHeight (DT--active-side-height)
        thickness
          (min
            (DT--plan-material-thickness)
            (* sideHeight 0.45)
            (* newWidth 0.45)
            (* oldWidth 0.45)))
  (if (and upper lower)
    (progn
      (if (and (> sideHeight 0.0) (> thickness 0.0))
        (setq innerUpper   (DT--profile-shift-y upper (- thickness))
              innerLower   (DT--profile-shift-y lower thickness)
              floorUpper   (DT--profile-offset-normal-xz innerUpper thickness)
              floorLower   (DT--profile-offset-normal-xz innerLower thickness)
              topUpper     (DT--profile-offset-normal-xz upper sideHeight)
              topLower     (DT--profile-offset-normal-xz lower sideHeight)
              innerTopUpper (DT--profile-offset-normal-xz innerUpper sideHeight)
              innerTopLower (DT--profile-offset-normal-xz innerLower sideHeight)))
      (setq i 0
            n (length upper))
      (while (< i (1- n))
        ;; 10: enine parca sinirlarini gizler; iki baglanti ucu acik kalir.
        (DT--block-face-hatched-flags
          (list (nth i upper) (nth (1+ i) upper)
                (nth (1+ i) lower) (nth i lower)) 10)
        (if floorUpper
          (progn
            (DT--block-face-hatched-flags
              (list (nth i floorUpper) (nth (1+ i) floorUpper)
                    (nth (1+ i) floorLower) (nth i floorLower)) 10)
            (DT--block-face-hatched-flags
              (list (nth i upper) (nth (1+ i) upper)
                    (nth (1+ i) topUpper) (nth i topUpper)) 10)
            (DT--block-face-hatched-flags
              (list (nth i floorUpper) (nth (1+ i) floorUpper)
                    (nth (1+ i) innerTopUpper) (nth i innerTopUpper)) 10)
            (DT--block-face-hatched-flags
              (list (nth i topUpper) (nth (1+ i) topUpper)
                    (nth (1+ i) innerTopUpper) (nth i innerTopUpper)) 10)
            (DT--block-face-hatched-flags
              (list (nth i lower) (nth (1+ i) lower)
                    (nth (1+ i) topLower) (nth i topLower)) 10)
            (DT--block-face-hatched-flags
              (list (nth i floorLower) (nth (1+ i) floorLower)
                    (nth (1+ i) innerTopLower) (nth i innerTopLower)) 10)
            (DT--block-face-hatched-flags
              (list (nth i topLower) (nth (1+ i) topLower)
                    (nth (1+ i) innerTopLower) (nth i innerTopLower)) 10)))
        (setq i (1+ i)))
      T)
  )
)

(defun DT--create-elevation-fitting-block-def (name newWidth oldWidth span slope arcP)
  (if (and name
           (numberp newWidth)
           (numberp oldWidth)
           (numberp span)
           (> span 0.0)
           (numberp slope))
    (progn
      (entmake
        (list
          '(0 . "BLOCK")
          (cons 2 name)
          '(70 . 0)
          '(10 0.0 0.0 0.0)))
      (DT--block-elevation-curved-geometry newWidth oldWidth span slope arcP)
      (entmake '((0 . "ENDBLK")))
      (if (not arcP) (DT--block-associate-hatches name))
      T
    )
  )
)

(defun DT--make-elevation-fitting-block-span
  (kind newWidth oldWidth base dir slope spanOverride / span arcP slopeKind name ins)
  (setq span      (if (and (numberp spanOverride) (> spanOverride 0.001))
                    spanOverride
                    (max newWidth oldWidth))
        arcP      (DT--elevation-arc-required-p slope)
        slopeKind (strcat kind
                    (if arcP "_3D_ARC8_OPEN_TAN_C5N_S_H2" "_3D_LINEAR_OPEN_N_S")
                    (DT--width-name slope) (DT--shell-style-token))
        name       (DT--fitting-block-name slopeKind span))
  (if (and name base dir (> span 0.0))
    (progn
      (if (not (tblsearch "BLOCK" name))
        (DT--create-elevation-fitting-block-def name newWidth oldWidth span slope arcP))
      (if (not arcP) (DT--block-associate-hatches name))
      (DT--set-block-linework-050 name)
      (setq ins
        (entmakex
          (list
            '(0 . "INSERT")
            (cons 2 name)
            (cons 8 (DT--layer-fitting))
            (cons 10 (DT--point-at-elevation base (DT--active-elevation)))
            '(41 . 1.0)
            '(42 . 1.0)
            '(43 . 1.0)
            (cons 50 (DT--vec-angle dir)))))
      (DT--mark-fitting-insert ins kind span)
      (DT--apply-fitting-3d-mode ins (DT--active-3d-enabled-p))
      ins
    )
  )
)

(defun DT--make-elevation-fitting-block
  (kind newWidth oldWidth base dir slope)
  (DT--make-elevation-fitting-block-span
    kind newWidth oldWidth base dir slope nil)
)
(defun DT--simplify-pts (pts / out i a b c u1 u2 dotv)
  (if (< (length pts) 3)
    pts
    (progn
      (setq out (list (car pts)) i 1)
      (while (< i (1- (length pts)))
        (setq a (g365_last out)
              b (nth i pts)
              c (nth (1+ i) pts)
              u1 (DT--seg-unit a b)
              u2 (DT--seg-unit b c)
              dotv (g365_dot (car u1) (cadr u1) (car u2) (cadr u2)))
        (if (< dotv 0.9999)
          (setq out (append out (list b)))
        )
        (setq i (1+ i))
      )
      (append out (list (g365_last pts)))
    )
  )
)

(defun DT--corner-records (pts width / out i a b c u1 u2 dotv d)
  (setq i 1)
  (while (< i (1- (length pts)))
    (setq a (nth (1- i) pts)
          b (nth i pts)
          c (nth (1+ i) pts)
          u1 (DT--seg-unit a b)
          u2 (DT--seg-unit b c)
          dotv (g365_dot (car u1) (cadr u1) (car u2) (cadr u2)))
    (if (and (< dotv 0.999) (> dotv -0.999))
      (progn
        (setq d (min width (* 0.35 (distance a b)) (* 0.35 (distance b c))))
        (if (> d 0.01)
          (setq out (append out (list (list i b u1 u2 d))))
        )
      )
    )
    (setq i (1+ i))
  )
  out
)

(defun DT--corner-at (corners idx / found rec)
  (foreach rec corners
    (if (= (car rec) idx) (setq found rec))
  )
  found
)

(defun DT--face-data-flags (lay p1 p2 p3 p4 flags)
  (if (and p1 p2 p3 p4)
    (list
      '(0 . "3DFACE")
      '(100 . "AcDbEntity")
      (cons 8 lay)
      '(370 . 30)
      '(100 . "AcDbFace")
      (cons 10 p1)
      (cons 11 p2)
      (cons 12 p3)
      (cons 13 p4)
      (cons 70 (if (numberp flags) (fix flags) 0)))
  )
)

(defun DT--face-data (lay p1 p2 p3 p4)
  (DT--face-data-flags lay p1 p2 p3 p4 0)
)

(defun DT--make-3d-face (lay p1 p2 p3 p4 / data)
  (setq data (DT--face-data lay p1 p2 p3 p4))
  (if data (entmakex data))
)

(defun DT--make-plane-hatch (boundary lay pts / data hatch)
  (setq data
    (DT--hatch-data-plane-assoc
      lay
      pts
      (DT--mode-hatch-pattern *DT_ACTIVE_MODE*)
      (DT--mode-hatch-color *DT_ACTIVE_MODE*)
      boundary))
  (if data
    (progn
      ;; 3DFACE sinirli hatchler blok tanimi icinde ENTMAKEX ile sessizce
      ;; reddedilebiliyor. ENTMAKE mevcut BLOCK baglaminda hatchi korur.
      (if (entmake data) (setq hatch (entlast)))
      (if hatch (DT--hatch-set-source hatch boundary))))
)

(defun DT--quad-planar-p (pts / p0 p1 p2 p3 normal span deviation)
  (if (= (length pts) 4)
    (progn
      (setq p0     (nth 0 pts)
            p1     (nth 1 pts)
            p2     (nth 2 pts)
            p3     (nth 3 pts)
            normal (DT--unit3
                     (DT--cross3
                       (DT--vec3-sub p1 p0)
                       (DT--vec3-sub p3 p0)))
            span   (max (distance p0 p1)
                        (distance p1 p2)
                        (distance p2 p3)
                        (distance p3 p0)
                        1.0))
      (if normal
        (progn
          (setq deviation
            (abs
              (+ (* (car normal)   (- (car p2)   (car p0)))
                 (* (cadr normal)  (- (cadr p2)  (cadr p0)))
                 (* (caddr normal) (- (caddr p2) (caddr p0))))))
          (<= deviation (* span 1e-7)))
        nil))
    T)
)

(defun DT--mid3 (a b)
  (list
    (/ (+ (car a) (car b)) 2.0)
    (/ (+ (cadr a) (cadr b)) 2.0)
    (/ (+ (if (caddr a) (caddr a) 0.0)
          (if (caddr b) (caddr b) 0.0)) 2.0))
)

(defun DT--block-face-hatched-make (pts flags associativeP / data boundary p3 p4)
  (if (and pts (= (length pts) 4))
    (progn
      (setq p3 (nth 2 pts)
            p4 (nth 3 pts))
      (entmake
        (DT--face-data-flags
          (DT--layer-linework)
          (nth 0 pts) (nth 1 pts) p3 p4
          flags))
      (setq boundary (entlast)
            data
              (if associativeP
                (DT--hatch-data-plane-assoc
                  (DT--layer-fitting)
                  pts
                  (DT--mode-hatch-pattern *DT_ACTIVE_MODE*)
                  (DT--mode-hatch-color *DT_ACTIVE_MODE*)
                  boundary)
                (DT--hatch-data-plane
                  (DT--layer-fitting)
                  pts
                  (DT--mode-hatch-pattern *DT_ACTIVE_MODE*)
                  (DT--mode-hatch-color *DT_ACTIVE_MODE*))))
      (if data (entmake data)))
  )
)

(defun DT--make-plane-hatch-unassoc (lay pts / data hatch)
  (setq data
    (DT--hatch-data-plane
      lay
      pts
      (DT--mode-hatch-pattern *DT_ACTIVE_MODE*)
      (DT--mode-hatch-color *DT_ACTIVE_MODE*)))
  (if (and data
           (boundp '*DT_BLOCK_HATCH_ASSOC_MARKER*)
           *DT_BLOCK_HATCH_ASSOC_MARKER*
           (assoc 71 data))
    (setq data (subst '(71 . 1) (assoc 71 data) data)))
  ;; Keep the associative marker expected by tray tooling on horizontal visual
  ;; blocks without adding the 3DFACE source handle that crashes AutoCAD.
  ;; Controller STRETCH rebuilds inclined visuals, so their hatch still follows.
  (if (and data (entmake data)) (setq hatch (entlast)))
  hatch
)

(defun DT--block-face-hatched-flags (pts flags)
  (cond
    ;; Kavisli elevation yuzlerindeki dort kose ayni duzlemde olmayabilir.
    ;; AutoCAD bu dortgenlere HATCH olusturmaz; iki duzlemsel ucgene bol.
    ((and pts (= (length pts) 4) (not (DT--quad-planar-p pts)))
      (DT--block-face-hatched-make
        (list
          (nth 0 pts) (nth 1 pts) (nth 2 pts)
          (DT--mid3 (nth 2 pts) (nth 0 pts)))
        flags nil)
      (DT--block-face-hatched-make
        (list
          (nth 0 pts) (nth 2 pts) (nth 3 pts)
          (DT--mid3 (nth 3 pts) (nth 0 pts)))
        flags nil))
    ((and pts (= (length pts) 4))
      (DT--block-face-hatched-make
        pts flags
        (not
          (and (boundp '*DT_BLOCK_FACE_UNASSOC*)
               *DT_BLOCK_FACE_UNASSOC*))))
  )
)

(defun DT--block-face-hatched (pts)
  (DT--block-face-hatched-flags pts 0)
)

(defun DT--polygon-area2 (pts / out i a b n)
  (setq out 0.0
        i   0
        n   (length pts))
  (while (< i n)
    (setq a (nth i pts)
          b (nth (rem (1+ i) n) pts)
          out (+ out (- (* (car a) (cadr b)) (* (car b) (cadr a))))
          i (1+ i)))
  out
)

(defun DT--inset-closed-pts (pts amount / side n i prev cur next u1 u2 n1 n2 a1 b1 a2 b2 ip avg out)
  (if (and pts (>= (length pts) 3) (numberp amount) (> amount 0.0))
    (progn
      (setq side (if (> (DT--polygon-area2 pts) 0.0) 1.0 -1.0)
            n    (length pts)
            i    0)
      (while (< i n)
        (setq prev (nth (rem (+ i n -1) n) pts)
              cur  (nth i pts)
              next (nth (rem (1+ i) n) pts)
              u1   (DT--seg-unit prev cur)
              u2   (DT--seg-unit cur next)
              n1   (DT--perp u1)
              n2   (DT--perp u2)
              a1   (DT--pt+ prev n1 (* side amount))
              b1   (DT--pt+ cur  n1 (* side amount))
              a2   (DT--pt+ cur  n2 (* side amount))
              b2   (DT--pt+ next n2 (* side amount))
              ip   (g365_line_inter a1 b1 a2 b2))
        (if (or (null ip) (> (distance cur ip) (* amount 8.0)))
          (progn
            (setq avg (g365_unit
                        (+ (* side (car n1)) (* side (car n2)))
                        (+ (* side (cadr n1)) (* side (cadr n2)))))
            (setq ip (if avg (DT--pt+ cur avg amount) b1)))
        )
        (setq out (append out (list ip))
              i   (1+ i))
      )
      out
    )
  )
)

(defun DT--plane-z-at (pt planePts / normal p0 nz)
  (setq normal (DT--plane-normal planePts)
        p0     (car planePts)
        nz     (if normal (caddr normal) 0.0))
  (if (and normal p0 (> (abs nz) 1e-9))
    (- (if (caddr p0) (caddr p0) 0.0)
       (/ (+ (* (car normal) (- (car pt) (car p0)))
             (* (cadr normal) (- (cadr pt) (cadr p0))))
          nz))
    (if (and p0 (caddr p0)) (caddr p0) 0.0)
  )
)

(defun DT--pts-on-plane (xyPts planePts / out p)
  (foreach p xyPts
    (setq out
      (append out
        (list (list (car p) (cadr p) (DT--plane-z-at p planePts))))))
  out
)

(defun DT--pt-shift-xy (p u d)
  (list
    (+ (car p) (* (car u) d))
    (+ (cadr p) (* (cadr u) d))
    (if (caddr p) (caddr p) 0.0))
)

(defun DT--pt-shift-3d (p u d)
  (list
    (+ (car p) (* (car u) d))
    (+ (cadr p) (* (cadr u) d))
    (+ (if (caddr p) (caddr p) 0.0) (* (caddr u) d)))
)

(defun DT--set-list-item (lst idx value / out i item)
  (setq i 0)
  (foreach item lst
    (setq out (append out (list (if (= i idx) value item)))
          i (1+ i))
  )
  out
)

(defun DT--floor-points-at-open-ports (innerPts outerPts openEdges / out n edge next)
  ;; Hacim tabani kapali kenarlarda iceride kalir, acik portta tava ucuna kadar uzar.
  (setq out innerPts
        n   (min (length innerPts) (length outerPts)))
  (foreach edge openEdges
    (if (and (numberp edge) (>= edge 0) (< edge n))
      (progn
        (setq next (rem (1+ edge) n)
              out  (DT--set-list-item out edge (nth edge outerPts))
              out  (DT--set-list-item out next (nth next outerPts)))
      )
    )
  )
  out
)

(defun DT--side-inner-points-at-open-ports (innerPts outerPts openEdges / out n edge next a b rec)
  ;; Ic yanak uclari port duzlemine gelir; port kesiti acik kalmaya devam eder.
  (setq out innerPts
        n   (min (length innerPts) (length outerPts)))
  (foreach edge openEdges
    (if (and (numberp edge) (>= edge 0) (< edge n))
      (progn
        (setq next (rem (1+ edge) n)
              a    (nth edge outerPts)
              b    (nth next outerPts)
              rec  (g365_closest_on_seg (nth edge out) a b))
        (if rec (setq out (DT--set-list-item out edge (car rec))))
        (setq rec (g365_closest_on_seg (nth next out) a b))
        (if rec (setq out (DT--set-list-item out next (car rec))))
      )
    )
  )
  out
)

(defun DT--block-shell-geometry-open (outerPts skipEdges / sideHeight thickness xy insetXY rawInnerPts innerPts floorPts floorTop innerFloorTop outerTop innerTop floorBoundary floorHatch i n a b ia ib)
  (setq sideHeight (DT--active-side-height)
        thickness  (min (DT--plan-material-thickness) (* sideHeight 0.45)))
  (if (and outerPts (>= (length outerPts) 3) (> sideHeight 0.0) (> thickness 0.0))
    (progn
      (setq xy      (mapcar '(lambda (p) (list (car p) (cadr p) 0.0)) outerPts)
            insetXY (DT--inset-closed-pts xy thickness)
            rawInnerPts (if insetXY (DT--pts-on-plane insetXY outerPts) nil)
            innerPts (if rawInnerPts
                       (DT--side-inner-points-at-open-ports
                         rawInnerPts outerPts skipEdges)
                       nil)
            floorPts (if innerPts
                       (DT--floor-points-at-open-ports innerPts outerPts skipEdges)
                       nil)
            floorTop (if floorPts (DT--raise-pts floorPts thickness) nil)
            innerFloorTop (if innerPts (DT--raise-pts innerPts thickness) nil)
            outerTop (DT--raise-pts outerPts sideHeight)
            innerTop (if innerPts (DT--raise-pts innerPts sideHeight) nil))
      (if (and floorTop (>= (length floorTop) 3))
        (progn
          (setq floorBoundary (DT--make-poly3d (DT--layer-linework) floorTop T)
                floorHatch
                  (DT--hatch-data-plane-assoc
                    (DT--layer-fitting)
                    floorTop
                    (DT--mode-hatch-pattern *DT_ACTIVE_MODE*)
                    (DT--mode-hatch-color *DT_ACTIVE_MODE*)
                    floorBoundary))
          (if floorHatch (entmake floorHatch))
        )
      )
      (if (and innerPts innerTop (= (length outerPts) (length innerPts)))
        (progn
          (setq i 0 n (length outerPts))
          (while (< i n)
            (setq a  (nth i outerPts)
                  b  (nth (rem (1+ i) n) outerPts)
                  ia (nth i innerPts)
                  ib (nth (rem (1+ i) n) innerPts))
            (if (not (member i skipEdges))
              (progn
                (DT--block-face-hatched
                  (list a b (nth (rem (1+ i) n) outerTop) (nth i outerTop)))
                (DT--block-face-hatched
                  (list (nth i innerFloorTop)
                        (nth (rem (1+ i) n) innerFloorTop)
                        (nth (rem (1+ i) n) innerTop)
                        (nth i innerTop)))
                (DT--block-face-hatched
                  (list (nth i outerTop)
                        (nth (rem (1+ i) n) outerTop)
                        (nth (rem (1+ i) n) innerTop)
                        (nth i innerTop)))))
            (setq i (1+ i))
          )
        )
      )
      T
    )
  )
)

(defun DT--block-shell-geometry (outerPts)
  (DT--block-shell-geometry-open outerPts nil)
)

(defun DT--shell-style-token (/ pattern color scale thickness)
  (setq pattern   (car (DT--hatch-pattern-info (DT--mode-hatch-pattern *DT_ACTIVE_MODE*)))
        color     (DT--mode-hatch-color *DT_ACTIVE_MODE*)
        scale     (DT--hatch-scale)
        thickness (DT--plan-material-thickness))
  (strcat
    "$T" (DT--width-name thickness)
    "$P" (DT--name-safe pattern)
    "$C" (itoa color)
    "$S" (DT--width-name scale))
)

(defun DT--fitting-shell-block-name (fittingName)
  (strcat "DT$SHELL$" (DT--name-safe fittingName) (DT--shell-style-token) "$OPEN4")
)

(defun DT--create-fitting-shell-block (shellName shapes base ang yscale / shape local bulges flat ports localPorts openEdges made)
  (if (and shellName shapes)
    (progn
      (entmake
        (list
          '(0 . "BLOCK")
          (cons 2 shellName)
          '(70 . 0)
          '(10 0.0 0.0 0.0)))
      (foreach shape shapes
        (if (cadr shape)
          (progn
            (setq local
              (DT--local-pts-xform (car shape) base ang yscale)
                  bulges (DT--local-bulges-xform (caddr shape) yscale)
                  flat   (if bulges (DT--flatten-bulged-pts local bulges) local)
                  ports  (nth 3 shape)
                  localPorts (if ports (DT--local-pts-xform ports base ang yscale) nil)
                  openEdges (if localPorts
                              (DT--fitting-port-open-edges flat localPorts)
                              (DT--fitting-flat-open-edges local bulges flat)))
            (if (DT--block-shell-geometry-open flat openEdges) (setq made T))
          )
        )
      )
      (entmake '((0 . "ENDBLK")))
      (DT--block-associate-hatches shellName)
      made
    )
  )
)

(defun DT--ensure-fitting-shell-block (fittingName shapes base ang yscale / shellName created)
  (if (and (> (DT--active-side-height) 0.0)
           (> (DT--plan-material-thickness) 0.0))
    (progn
      (setq shellName (DT--fitting-shell-block-name fittingName))
      (if (not (tblsearch "BLOCK" shellName))
        (if (DT--create-fitting-shell-block shellName shapes base ang yscale)
          (setq created T)
          (setq shellName nil)))
      (if (and shellName created)
        (progn
          (DT--block-associate-hatches shellName)
          (DT--set-block-linework-050 shellName)))
      shellName
    )
  )
)

(defun DT--make-model-face-hatched (lay pts / data face hatch)
  (if (and pts (= (length pts) 4))
    (progn
      ;; Yuz ve hatch ayni BLOCK/model baglaminda ardisik olusmali.
      ;; ENTMAKEX ile uretilen 3DFACE blokta gorunse de associative hatch
      ;; kaynak siniri olarak kabul edilmeyebiliyor.
      (setq data
        (DT--face-data
          (DT--line-layer-name lay)
          (nth 0 pts) (nth 1 pts) (nth 2 pts) (nth 3 pts)))
      (if (and data (entmake data)) (setq face (entlast)))
      (setq hatch
        (if (and (boundp '*DT_BLOCK_FACE_UNASSOC*)
                 *DT_BLOCK_FACE_UNASSOC*)
          (DT--make-plane-hatch-unassoc lay pts)
          (DT--make-plane-hatch face lay pts)))
      (list face hatch)
    )
  )
)

(defun DT--make-tray-sidewalls (tray p1 p2 p3 p4 / height thickness width inwardL inwardR floorNormal inner1 inner2 inner3 inner4 fp1 fp2 fp3 fp4 op1 op2 op3 op4 il1 il2 il3 il4 it1 it2 it3 it4 faces rec face hatch walls hatches)
  (setq height    (DT--active-side-height)
        width     (distance p1 p4)
        thickness (min (DT--plan-material-thickness) (* height 0.45) (* width 0.45)))
  (if (and tray (> height 0.0) (> thickness 0.0))
    (progn
      (setq inwardL (DT--seg-unit p1 p4)
            inwardR (DT--seg-unit p4 p1)
            floorNormal (DT--plane-normal (list p1 p4 p2))
            floorNormal (if floorNormal floorNormal '(0.0 0.0 1.0))
            inner1 (DT--pt-shift-xy p1 inwardL thickness)
            inner2 (DT--pt-shift-xy p2 inwardL thickness)
            inner3 (DT--pt-shift-xy p3 inwardR thickness)
            inner4 (DT--pt-shift-xy p4 inwardR thickness)
            fp1 (DT--pt-shift-3d p1 floorNormal thickness)
            fp2 (DT--pt-shift-3d p2 floorNormal thickness)
            fp3 (DT--pt-shift-3d p3 floorNormal thickness)
            fp4 (DT--pt-shift-3d p4 floorNormal thickness)
            op1 (DT--pt-shift-3d p1 floorNormal height)
            op2 (DT--pt-shift-3d p2 floorNormal height)
            op3 (DT--pt-shift-3d p3 floorNormal height)
            op4 (DT--pt-shift-3d p4 floorNormal height)
            il1 (DT--pt-shift-3d inner1 floorNormal thickness)
            il2 (DT--pt-shift-3d inner2 floorNormal thickness)
            il3 (DT--pt-shift-3d inner3 floorNormal thickness)
            il4 (DT--pt-shift-3d inner4 floorNormal thickness)
            it1 (DT--pt-shift-3d inner1 floorNormal height)
            it2 (DT--pt-shift-3d inner2 floorNormal height)
            it3 (DT--pt-shift-3d inner3 floorNormal height)
            it4 (DT--pt-shift-3d inner4 floorNormal height)
            faces
              (list
                (list fp1 fp2 fp3 fp4)
                (list p1 p4 fp4 fp1)
                (list p2 p3 fp3 fp2)
                (list p1 p2 op2 op1)
                (list p4 p3 op3 op4)
                (list il1 il2 it2 it1)
                (list il4 il3 it3 it4)
                (list op1 op2 it2 it1)
                (list op4 op3 it3 it4)
                ;; Tava ucundaki iki yanak kesitini de kapat.
                (list p1 op1 it1 il1)
                (list p4 op4 it4 il4)
                (list p2 op2 it2 il2)
                (list p3 op3 it3 il3)))
      (foreach rec faces
        (setq rec   (DT--make-model-face-hatched (DT--layer-visible) rec)
              face  (car rec)
              hatch (cadr rec))
        (if face  (setq walls   (append walls (list face))))
        (if hatch (setq hatches (append hatches (list hatch)))))
      (if walls (DT--xdata-link-sidewalls tray walls))
      (foreach hatch hatches (DT--xdata-link-hatch tray hatch))
      walls
    )
  )
)

(defun DT--make-straight-piece (a b width / u n h p1 p2 p3 p4 ent hatch pts zA zB oldElevation)
  (if (> (distance a b) 0.001)
    (progn
      (setq u (DT--seg-unit a b)
            n (DT--perp u)
            h (/ width 2.0)
            zA (DT--build-elevation-at-point a)
            zB (DT--build-elevation-at-point b)
            p1 (DT--point-at-elevation (DT--pt+ a n h) zA)
            p2 (DT--point-at-elevation (DT--pt+ b n h) zB)
            p3 (DT--point-at-elevation (DT--pt+ b n (- h)) zB)
            p4 (DT--point-at-elevation (DT--pt+ a n (- h)) zA)
            pts (list p1 p2 p3 p4))
      (if (and (boundp '*DT_LIVE_PREVIEW_LIGHTWEIGHT*)
               *DT_LIVE_PREVIEW_LIGHTWEIGHT*)
        ;; Canli cizimde yalniz kontur yeterlidir. Hatch, yanak ve grup her
        ;; tiklamada silinip yeniden uretilirse AutoCAD undo/veritabani sisiyordu.
        (setq ent
          (if (equal zA zB 0.000001)
            (progn
              (setq oldElevation (DT--active-elevation)
                    *DT_ACTIVE_ELEVATION* zA
                    ent (DT--make-poly (DT--layer-linework) pts T)
                    *DT_ACTIVE_ELEVATION* oldElevation)
              ent)
            (DT--make-poly3d (DT--layer-linework) pts T)))
        (if (equal zA zB 0.000001)
          (progn
            (setq oldElevation (DT--active-elevation)
                  *DT_ACTIVE_ELEVATION* zA
                  ent (DT--make-poly (DT--layer-linework) pts T))
            (if ent
              (setq hatch
                (DT--make-assoc-hatch
                  ent
                  (DT--layer-visible)
                  pts
                  (DT--mode-hatch-pattern *DT_ACTIVE_MODE*)
                  (DT--mode-hatch-color *DT_ACTIVE_MODE*)))
            )
            (setq *DT_ACTIVE_ELEVATION* oldElevation)
          )
          (progn
            (setq ent (DT--make-poly3d (DT--layer-linework) pts T))
            (if ent
              (setq hatch
                (DT--make-assoc-hatch-plane
                  ent
                  (DT--layer-visible)
                  pts
                  (DT--mode-hatch-pattern *DT_ACTIVE_MODE*)
                  (DT--mode-hatch-color *DT_ACTIVE_MODE*)))
            )
          )
        )
      )
      (if (and ent hatch)
        (DT--xdata-link-hatch ent hatch)
      )
      (if (and ent
               (not
                 (and (boundp '*DT_LIVE_PREVIEW_LIGHTWEIGHT*)
                      *DT_LIVE_PREVIEW_LIGHTWEIGHT*)))
        (progn
          (DT--make-tray-sidewalls ent p1 p2 p3 p4)
          (DT--refresh-tray-group ent)))
      ent
    )
  )
)
(defun DT--turn-kind (u1 u2 / radians degrees rounded baseName)
  (setq radians (atan (abs (DT--cross2 u1 u2)) (g365_dot (car u1) (cadr u1) (car u2) (cadr u2))))
  (setq degrees (* 180.0 (/ radians pi)))
  (setq rounded (fix (+ degrees 0.5)))
  (setq baseName (strcat "d" (chr 246) "n" (chr 252) (chr 254)))
  (if (<= (abs (- degrees 90.0)) 0.1) baseName
    (strcat baseName "_A" (itoa rounded))
  )
)

(defun DT--90-turn-p (u1 u2)
  (<= (abs (g365_dot (car u1) (cadr u1) (car u2) (cadr u2))) 0.001)
)

(defun DT--rounded-turn-shape (b u1 u2 radius width / h s n1 n2 q1 q2 p1 p2 p3 p4 k)
  (setq h  (/ width 2.0)
        s  (if (< (DT--cross2 u1 u2) 0.0) -1.0 1.0)
        n1 (DT--perp u1)
        n2 (DT--perp u2)
        q1 (DT--pt+ b u1 (- radius))
        q2 (DT--pt+ b u2 radius)
        p1 (DT--pt+ q1 n1 (* s h))
        p2 (DT--pt+ q2 n2 (* s h))
        p3 (DT--pt+ q2 n2 (* (- s) h))
        p4 (DT--pt+ q1 n1 (* (- s) h))
        k  0.414213562373095)
  (list
    (list p1 p2 p3 p4)
    (list (* s k) 0.0 (* (- s) k) 0.0)
    (list q1 q2)
  )
)

(defun DT--make-turn-block (rec width / b u1 u2 d q1 q2 left right path rounded ang yscale result oldElevation)
  (setq b  (nth 1 rec)
        u1 (nth 2 rec)
        u2 (nth 3 rec)
        d  (nth 4 rec)
        q1 (DT--pt+ b u1 (- d))
        q2 (DT--pt+ b u2 d)
        ang (DT--vec-angle u1)
        yscale (DT--mirror-for u1 u2)
        oldElevation (DT--active-elevation)
        *DT_ACTIVE_ELEVATION* (DT--build-elevation-at-point b))
  (if (DT--90-turn-p u1 u2)
    (progn
      (setq rounded (DT--rounded-turn-shape b u1 u2 d width))
      (setq result
        (DT--make-fitting-block
          (DT--turn-kind u1 u2)
          width
          b
          (list (list (car rounded) T (cadr rounded) (caddr rounded)))
          ang
          yscale))
    )
    (progn
      (setq left  (g365_offset_open_pts (list q1 b q2) (/ width 2.0) 1))
      (setq right (g365_offset_open_pts (list q1 b q2) (/ width 2.0) -1))
      (if (and left right)
        (progn
          (setq path (append left (reverse right)))
          (setq result
            (DT--make-fitting-block
              (DT--turn-kind u1 u2) width b
              (list (list path T nil (list q1 q2))) ang yscale))
        )
      )
    )
  )
  (setq *DT_ACTIVE_ELEVATION* oldElevation)
  result
)

(defun DT--range-sort (ranges)
  (vl-sort ranges '(lambda (a b) (< (car a) (car b))))
)

(defun DT--merge-ranges (ranges / out rec lastRec)
  (foreach rec (DT--range-sort ranges)
    (if (null out)
      (setq out (list rec))
      (progn
        (setq lastRec (g365_last out))
        (if (<= (car rec) (+ (cadr lastRec) 0.0001))
          (setq out
            (append
              (reverse (cdr (reverse out)))
              (list (list (car lastRec) (max (cadr lastRec) (cadr rec))))
            )
          )
          (setq out (append out (list rec)))
        )
      )
    )
  )
  out
)

(defun DT--segment-cut-ranges (a b cutPts gap startD endD / ranges cp rec d lo hi cut pt useGap)
  (foreach cut cutPts
    (setq pt (DT--cut-point cut))
    (setq useGap (DT--cut-gap cut gap))
    (setq rec (g365_closest_on_seg pt a b))
    (if (and rec (<= (nth 2 rec) 0.001))
      (progn
        (setq cp (car rec))
        (setq d (distance a cp))
        (setq lo (max startD (- d useGap)))
        (setq hi (min endD (+ d useGap)))
        (if (> hi (+ lo 0.001))
          (setq ranges (append ranges (list (list lo hi))))
        )
      )
    )
  )
  (DT--merge-ranges ranges)
)

(defun DT--make-segment-pieces (a b width startD endD cutPts gap / u ranges cursor rec p1 p2 ent out)
  (setq u (DT--seg-unit a b))
  (setq ranges (DT--segment-cut-ranges a b cutPts gap startD endD))
  (setq cursor startD)
  (foreach rec ranges
    (if (> (car rec) (+ cursor 0.001))
      (progn
        (setq p1 (DT--pt+ a u cursor)
              p2 (DT--pt+ a u (car rec))
              ent (DT--make-straight-piece p1 p2 width))
        (if ent (setq out (append out (list ent))))
      )
    )
    (setq cursor (max cursor (cadr rec)))
  )
  (if (> endD (+ cursor 0.001))
    (progn
      (setq p1 (DT--pt+ a u cursor)
            p2 (DT--pt+ a u endD)
            ent (DT--make-straight-piece p1 p2 width))
      (if ent (setq out (append out (list ent))))
    )
  )
  out
)

(defun DT--build-straight-pieces (rawPts width cutPts / pts corners pieces i a b cStart cEnd startD endD segPieces)
  (setq pts (DT--simplify-pts rawPts))
  (setq corners (DT--corner-records pts width))
  (setq i 0)
  (while (< i (1- (length pts)))
    (setq a (nth i pts)
          b (nth (1+ i) pts)
          cStart (DT--corner-at corners i)
          cEnd   (DT--corner-at corners (1+ i))
          startD (if cStart (nth 4 cStart) 0.0)
          endD   (- (distance a b) (if cEnd (nth 4 cEnd) 0.0)))
    (if (> endD (+ startD 0.001))
      (progn
        (setq segPieces (DT--make-segment-pieces a b width startD endD cutPts width))
        (if segPieces (setq pieces (append pieces segPieces)))
      )
    )
    (setq i (1+ i))
  )
  pieces
)
(defun DT--build-piecewise-tray (rawPts width / pts corners pieces blocks blk rec)
  (setq pts (DT--simplify-pts rawPts))
  (setq corners (DT--corner-records pts width))
  (setq pieces (DT--build-straight-pieces pts width nil))
  (foreach rec corners
    (setq blk (DT--make-turn-block rec width))
    (if blk (setq blocks (append blocks (list blk))))
  )
  (list pieces blocks (length blocks) pts)
)
(defun DT--same-tray-layer-p (a b)
  (and a b (= (strcase a) (strcase b)))
)

(defun DT--collect-center-entities-raw (/ ss i ent out)
  (setq ss (ssget "_X" (list (cons 0 "LWPOLYLINE,POLYLINE") (cons 8 (DT--layer-center)))))
  (if ss
    (progn
      (setq i 0)
      (while (< i (sslength ss))
        (setq ent (ssname ss i))
        (if (and (DT--entity-alive-p ent)
                 (DT--active-center-p ent))
          (setq out (cons ent out))
        )
        (setq i (1+ i))
      )
    )
  )
  (reverse out)
)

(defun DT--center-cache-source (/ out ent)
  (if (and (boundp '*DT_CENTER_CACHE_ACTIVE*)
           *DT_CENTER_CACHE_ACTIVE*)
    (progn
      (foreach ent *DT_CENTER_CACHE*
        (if (and (DT--entity-alive-p ent)
                 (DT--active-center-p ent))
          (setq out (cons ent out))))
      (setq *DT_CENTER_CACHE* (reverse out)))
    (setq *DT_CENTER_CACHE* (DT--collect-center-entities-raw)))
  *DT_CENTER_CACHE*
)

(defun DT--cache-center-entity (ent)
  (if (and ent
           (DT--entity-alive-p ent)
           (boundp '*DT_CENTER_CACHE_ACTIVE*)
           *DT_CENTER_CACHE_ACTIVE*
           (not (member ent *DT_CENTER_CACHE*)))
    (setq *DT_CENTER_CACHE* (cons ent *DT_CENTER_CACHE*)))
  ent
)

(defun DT--center-entities (skip targetLayer / ent entLayer out)
  (foreach ent (DT--center-cache-source)
    (if (and (not (eq ent skip))
             (DT--same-active-elevation-p ent))
      (progn
        (setq entLayer (DT--center-layer ent nil))
        (if (DT--same-tray-layer-p entLayer targetLayer)
          (setq out (cons ent out))))))
  (reverse out)
)

(defun DT--all-layer-center-entities (skip targetLayer / ent entLayer out)
  ;; Kot gecisi icin ayni tava layer'indaki canli merkezleri kot ayirmadan getirir.
  (foreach ent (DT--center-cache-source)
    (if (not (eq ent skip))
      (progn
        (setq entLayer (DT--center-layer ent nil))
        (if (DT--same-tray-layer-p entLayer targetLayer)
          (setq out (cons ent out))))))
  (reverse out)
)

(defun DT--center-route-bounds (pts / p minX minY maxX maxY)
  (foreach p pts
    (if (null minX)
      (setq minX (car p) maxX (car p)
            minY (cadr p) maxY (cadr p))
      (setq minX (min minX (car p))
            maxX (max maxX (car p))
            minY (min minY (cadr p))
            maxY (max maxY (cadr p)))))
  (if minX (list minX minY maxX maxY))
)

(defun DT--center-near-route-p (center routeBounds newWidth / pts bounds oldWidth margin)
  (if (and center routeBounds)
    (progn
      (setq pts (g365_get_pts center)
            bounds (DT--center-route-bounds pts)
            oldWidth (DT--center-width center newWidth)
            margin (+ (/ newWidth 2.0) (/ oldWidth 2.0) 2.0))
      (and bounds
           (<= (- (car bounds) margin) (nth 2 routeBounds))
           (>= (+ (nth 2 bounds) margin) (car routeBounds))
           (<= (- (cadr bounds) margin) (nth 3 routeBounds))
           (>= (+ (nth 3 bounds) margin) (cadr routeBounds)))))
)

(defun DT--filter-centers-near-route (centers pts width / bounds center out)
  (setq bounds (DT--center-route-bounds pts))
  (foreach center centers
    (if (DT--center-near-route-p center bounds width)
      (setq out (cons center out))))
  (reverse out)
)

(defun DT--center-cache-reset ()
  (setq *DT_CENTER_CACHE*
    (DT--collect-center-entities-raw))
  *DT_CENTER_CACHE*
)

(defun DT--center-cache-count ()
  (length (DT--center-cache-source))
)

(defun DT--center-cache-active-p ()
  (and (boundp '*DT_CENTER_CACHE_ACTIVE*)
       *DT_CENTER_CACHE_ACTIVE*)
)

(defun DT--center-cache-disable ()
  (setq *DT_CENTER_CACHE_ACTIVE* nil
        *DT_CENTER_CACHE* nil)
  nil
)

(defun DT--center-cache-enable ()
  (setq *DT_CENTER_CACHE_ACTIVE* T)
  (DT--center-cache-reset)
)

(defun DT--center-cache-remove (ent)
  (if (and ent (boundp '*DT_CENTER_CACHE*))
    (setq *DT_CENTER_CACHE* (vl-remove ent *DT_CENTER_CACHE*)))
  ent
)

(defun DT--center-cache-refresh ()
  (if (DT--center-cache-active-p)
    (DT--center-cache-reset)
  )
  *DT_CENTER_CACHE*
)

(defun DT--nearest-center-end-contact (pt centers width / center pts oldWidth oldElevation activeZ sameActive bestSame tol p d best bestD i rec oldActive)
  ;; Tavanin gorunen ucundaki merkez/kose tiklamalarini ayni merkez ucuna toplar.
  (setq activeZ (DT--active-elevation))
  (foreach center centers
    (setq pts (g365_get_pts center))
    (if (and pts (> (length pts) 1))
      (progn
        (setq oldWidth (DT--center-width center width)
              tol      (+ (/ width 2.0) (/ oldWidth 2.0) 1.0))
        (setq i 0)
        (while (< i (1- (length pts)))
          (setq rec (g365_closest_on_seg pt (nth i pts) (nth (1+ i) pts))
                p   (if rec (car rec) nil)
                d   (if p (DT--distance-xy pt p) nil))
          (if (and p (<= d tol))
            (progn
              (setq oldElevation (DT--center-elevation-at-point center p)
                    sameActive   (equal oldElevation activeZ 0.000001)
                    oldActive    (DT--active-elevation)
                    *DT_ACTIVE_ELEVATION* oldElevation)
              (if (and
                    (DT--center-visible-at-point-p center p oldWidth)
                    (or
                      (null bestD)
                      (< d (- bestD 0.000001))
                      (and
                        (equal d bestD 0.000001)
                        sameActive
                        (not bestSame))))
                (setq bestD d
                      bestSame sameActive
                      best (list (list (car p) (cadr p) 0.0)
                                 center pts oldWidth oldElevation))
              )
              (setq *DT_ACTIVE_ELEVATION* oldActive)
            )
          )
          (setq i (1+ i))
        )
      )
    )
  )
  best
)

(defun DT--elevation-end-contacts (pts centers width / out firstRec lastRec pairDiff activeZ contacts transitionCenters firstZ lastZ)
  ;; Kayit: (temas oldCenter oldPts oldWidth oldZ yeniUcIndex digerZ)
  (setq out pts
        activeZ (DT--active-elevation))
  (if (and out (> (length out) 1))
    (progn
      (setq firstRec (DT--nearest-center-end-contact (car out) centers width)
            lastRec  (DT--nearest-center-end-contact (g365_last out) centers width)
            firstZ   (if firstRec (nth 4 firstRec) activeZ)
            lastZ    (if lastRec (nth 4 lastRec) activeZ)
            pairDiff (not (equal firstZ lastZ 0.000001)))
      (if (and firstRec pairDiff)
        (progn
          (setq out (DT--replace-first-point out (car firstRec)))
          (setq contacts
            (append contacts
              (list
                (append firstRec
                  (list 0 (if pairDiff lastZ activeZ))))))
          (setq transitionCenters
            (DT--add-ent-unique (cadr firstRec) transitionCenters))
        )
      )
      (if (and lastRec pairDiff)
        (progn
          (setq out (DT--replace-last-point out (car lastRec)))
          (setq contacts
            (append contacts
              (list
                (append lastRec
                  (list 1 (if pairDiff firstZ activeZ))))))
          (setq transitionCenters
            (DT--add-ent-unique (cadr lastRec) transitionCenters))
        )
      )
    )
  )
  (if (null firstZ) (setq firstZ activeZ))
  (if (null lastZ) (setq lastZ activeZ))
  (list out contacts transitionCenters (list firstZ lastZ))
)

(defun DT--elevation-scan-needs-fresh-retry-p (scan / contacts elevations)
  ;; Tek farkli-kot temasi, diger uc merkez cache'inde eksik kalinca olusur.
  (setq contacts   (cadr scan)
        elevations (nth 3 scan))
  (and (= (length contacts) 1)
       elevations
       (not (equal (car elevations) (cadr elevations) 0.000001)))
)

(defun DT--elevation-scan-for-center (newCenter pts width targetLayer / allCenters scan)
  (setq allCenters
          (DT--filter-centers-near-route
            (DT--all-layer-center-entities newCenter targetLayer)
            pts width)
        scan (DT--elevation-end-contacts pts allCenters width))
  (if (DT--elevation-scan-needs-fresh-retry-p scan)
    (progn
      (DT--center-cache-refresh)
      (setq allCenters
              (DT--filter-centers-near-route
                (DT--all-layer-center-entities newCenter targetLayer)
                pts width)
            scan (DT--elevation-end-contacts pts allCenters width))))
  (list scan allCenters)
)

(defun DT--point-known-p (pt pts tol / hit p)
  (foreach p pts
    (if (<= (distance pt p) tol) (setq hit T))
  )
  hit
)

(defun DT--vec-from-to (a b / dx dy)
  (setq dx (- (car b) (car a))
        dy (- (cadr b) (cadr a)))
  (g365_unit dx dy)
)

(defun DT--same-ray-p (u v)
  (and u v (> (g365_dot (car u) (cadr u) (car v) (cadr v)) 0.995))
)

(defun DT--add-ray-unique (ray rays / hit r)
  (if (and ray (> (distance '(0.0 0.0 0.0) (list (car ray) (cadr ray) 0.0)) 0.5))
    (progn
      (foreach r rays
        (if (DT--same-ray-p ray r) (setq hit T))
      )
      (if (not hit) (setq rays (append rays (list ray))))
    )
  )
  rays
)

(defun DT--point-on-seg-p (pt a b tol / rec)
  (setq rec (g365_closest_on_seg pt a b))
  (and rec (<= (nth 2 rec) tol))
)

(defun DT--arms-at-point (pts pt tol / arms i a b)
  (setq arms nil i 0)
  (while (< i (1- (length pts)))
    (setq a (nth i pts) b (nth (1+ i) pts))
    (if (DT--point-on-seg-p pt a b tol)
      (progn
        (if (> (distance pt a) tol)
          (setq arms (DT--add-ray-unique (DT--vec-from-to pt a) arms))
        )
        (if (> (distance pt b) tol)
          (setq arms (DT--add-ray-unique (DT--vec-from-to pt b) arms))
        )
      )
    )
    (setq i (1+ i))
  )
  arms
)

(defun DT--opposite-p (u v)
  (and u v (< (g365_dot (car u) (cadr u) (car v) (cadr v)) -0.995))
)

(defun DT--straight-axis (arms / a b)
  (if (= (length arms) 2)
    (progn
      (setq a (car arms) b (cadr arms))
      (if (DT--opposite-p a b) a nil)
    )
    nil
  )
)

(defun DT--perpendicular-p (u v)
  (and u v (<= (abs (g365_dot (car u) (cadr u) (car v) (cadr v))) 0.05))
)

(defun DT--opposite-exists-p (u arms / hit v)
  (foreach v arms
    (if (DT--opposite-p u v) (setq hit T))
  )
  hit
)

(defun DT--four-way-axes (arms / u v axes)
  (if (= (length arms) 4)
    (progn
      (setq u (car arms))
      (if (DT--opposite-exists-p u arms)
        (progn
          (foreach v (cdr arms)
            (if (and (not (DT--opposite-p u v))
                     (DT--perpendicular-p u v)
                     (DT--opposite-exists-p v arms)
                     (null axes))
              (setq axes (list u v))
            )
          )
        )
      )
    )
  )
  axes
)

(defun DT--xdata-set-app (ed app payload / out records item rec)
  (foreach item ed
    (if (= (car item) -3)
      (foreach rec (cdr item)
        (if (/= (car rec) app)
          (setq records (append records (list rec)))
        )
      )
      (setq out (append out (list item)))
    )
  )
  (if payload (setq records (append records (list payload))))
  (if records (setq out (append out (list (cons -3 records)))))
  out
)

(defun DT--xdata-remove-app (ed app)
  (DT--xdata-set-app ed app nil)
)

(defun DT--remove-center-display-copies (/ app ss i ent)
  ;; Onceki surumun hatch ustu gorunen merkez kopyalarini tamamen temizle.
  (setq app "DT_CENTER_DISPLAY")
  (if (tblsearch "APPID" app)
    (setq ss
      (ssget "_X"
        (list
          (cons 0 "LWPOLYLINE,POLYLINE")
          (list -3 (list app))
        )
      )
    )
  )
  (if ss
    (progn
      (setq i 0)
      (while (< i (sslength ss))
        (setq ent (ssname ss i))
        (if (entget ent) (entdel ent))
        (setq i (1+ i))
      )
      (sslength ss)
    )
    0
  )
)
(defun DT--xdata-link-tray (center trays / app ed lst payload tray h)
  (setq app "DT_TRAY_LINK")
  (if (not (tblsearch "APPID" app)) (regapp app))
  (setq lst
    (cond
      ((= (type trays) 'ENAME) (list trays))
      ((listp trays) trays)
      (T nil)
    )
  )
  (if (and center (entget center) lst)
    (progn
      (setq payload (list app))
      (foreach tray lst
        (if (and tray (entget tray))
          (progn
            (setq h (cdr (assoc 5 (entget tray))))
            (if h (setq payload (append payload (list (cons 1005 h)))))
          )
        )
      )
      (setq ed (entget center '("*")))
      (setq ed (DT--xdata-set-app ed app payload))
      (entmod ed)
      (entupd center)
    )
  )
  center
)

(defun DT--set-center-width (center width / app ed payload)
  (setq app "DT_TRAY_WIDTH")
  (if (not (tblsearch "APPID" app)) (regapp app))
  (if (and center (entget center) (numberp width) (> width 0.0))
    (progn
      (setq payload (list app (cons 1000 (rtos width 2 12))))
      (setq ed (entget center '("*")))
      (setq ed (DT--xdata-set-app ed app payload))
      (entmod ed)
      (entupd center)
    )
  )
  center
)

(defun DT--center-width (center fallback / app ed xd rec x val)
  (setq app "DT_TRAY_WIDTH")
  (setq val fallback)
  (if (and center (entget center))
    (progn
      (setq ed (entget center (list app)))
      (setq xd (assoc -3 ed))
      (if xd
        (progn
          (setq rec (cadr xd))
          (foreach x (cdr rec)
            (if (= (car x) 1000) (setq val (atof (cdr x))))
          )
        )
      )
    )
  )
  (if (and (numberp val) (> val 0.0)) val fallback)
)
(defun DT--set-center-layer (center lay / app ed payload)
  (setq app "DT_TRAY_LAYER")
  (if (not (tblsearch "APPID" app)) (regapp app))
  (if (and center (entget center) lay (/= lay ""))
    (progn
      (setq payload (list app (cons 1000 lay)))
      (setq ed (entget center '("*")))
      (setq ed (DT--xdata-set-app ed app payload))
      (entmod ed)
      (entupd center)
    )
  )
  center
)

(defun DT--center-layer (center fallback / app ed xd rec x lay trays tray)
  (setq app "DT_TRAY_LAYER" lay nil)
  (if (and center (entget center))
    (progn
      (setq ed (entget center (list app)))
      (setq xd (assoc -3 ed))
      (if xd
        (progn
          (setq rec (cadr xd))
          (foreach x (cdr rec)
            (if (= (car x) 1000) (setq lay (cdr x)))
          )
        )
      )
      (if (not (DT--tray-visible-layer-p lay))
        (progn
          (setq lay nil)
          (setq trays (DT--linked-trays center))
          (foreach tray trays
            (if (and (null lay) (entget tray)
                     (DT--tray-visible-layer-p (cdr (assoc 8 (entget tray)))))
              (setq lay (cdr (assoc 8 (entget tray))))
            )
          )
        )
      )
    )
  )
  (if (DT--tray-visible-layer-p lay) (DT--base-layer-name lay) fallback)
)

(setq *DT_DELETED_HANDLES* nil
      *DT_SUPPRESS_DELETE_HISTORY* nil)

(defun DT--ent-handle (ent / ed)
  (if (and ent (setq ed (entget ent)))
    (cdr (assoc 5 ed))
  )
)

(defun DT--entity-current-p (ent / ed h)
  ;; ENTGET silinmis entity icin nil verir; HANDENT'in eski handle'i geri
  ;; dondurmesi bu sabit-zamanli kontrolu etkilemez. Her sorguda tum layer'i
  ;; SSGET ile taramak buyuk planlarda DT'yi katlanarak yavaslatiyordu.
  (and ent
       (setq ed (entget ent))
       (setq h (cdr (assoc 5 ed)))
       (not (DT--deleted-handle-p h)))
)
(defun DT--deleted-handle-p (h)
  (and h (member h *DT_DELETED_HANDLES*))
)

(defun DT--remember-deleted-handle (h)
  (if (and h
           (not
             (and (boundp '*DT_SUPPRESS_DELETE_HISTORY*)
                  *DT_SUPPRESS_DELETE_HISTORY*))
           (not (DT--deleted-handle-p h)))
    (setq *DT_DELETED_HANDLES* (cons h *DT_DELETED_HANDLES*))
  )
  h
)

(defun DT--vla-object-for-ent (ent / obj ed h acad doc)
  (if (and ent (entget ent))
    (progn
      (setq obj (vl-catch-all-apply 'vlax-ename->vla-object (list ent)))
      (if (or (vl-catch-all-error-p obj) (null obj))
        (progn
          (setq ed (entget ent)
                h  (cdr (assoc 5 ed)))
          (if h
            (progn
              (setq acad (vl-catch-all-apply 'vlax-get-acad-object nil))
              (if (not (vl-catch-all-error-p acad))
                (progn
                  (setq doc (vl-catch-all-apply 'vla-get-ActiveDocument (list acad)))
                  (if (not (vl-catch-all-error-p doc))
                    (setq obj (vl-catch-all-apply 'vla-HandleToObject (list doc h)))
                  )
                )
              )
            )
          )
        )
      )
      (if (or (vl-catch-all-error-p obj) (null obj)) nil obj)
    )
  )
)

(defun DT--entity-erased-p (ent / obj r)
  (cond
    ((null ent) T)
    ((null (entget ent)) T)
    ((DT--deleted-handle-p (DT--ent-handle ent)) T)
    (T
      (setq obj (DT--vla-object-for-ent ent))
      (if (null obj)
        nil
        (progn
          (setq r (vl-catch-all-apply 'vlax-erased-p (list obj)))
          (cond
            ((vl-catch-all-error-p r) nil)
            ((eq r T) T)
            ((and (numberp r) (/= r 0)) T)
            (T nil)
          )
        )
      )
    )
  )
)

(defun DT--entity-alive-p (ent)
  (DT--entity-current-p ent)
)
(defun DT--xdata-link-hatch (tray hatch / app ed h payload oldHatch oldHandle found)
  (setq app "DT_TRAY_HATCH")
  (if (not (tblsearch "APPID" app)) (regapp app))
  (if (and tray hatch (entget tray) (entget hatch))
    (progn
      (setq h (cdr (assoc 5 (entget hatch))))
      (if h
        (progn
          (setq payload (list app))
          (foreach oldHatch (DT--linked-hatches tray)
            (setq oldHandle (cdr (assoc 5 (entget oldHatch))))
            (if oldHandle
              (progn
                (if (= (strcase oldHandle) (strcase h)) (setq found T))
                (setq payload (append payload (list (cons 1005 oldHandle))))
              )
            )
          )
          (if (not found)
            (setq payload (append payload (list (cons 1005 h)))))
          (setq ed (entget tray '("*")))
          (setq ed (DT--xdata-set-app ed app payload))
          (entmod ed)
          (entupd tray)
        )
      )
    )
  )
  tray
)

(defun DT--linked-hatches (ent / app ed xd rec h hatch out x)
  (setq app "DT_TRAY_HATCH")
  (if (and ent (entget ent))
    (progn
      (setq ed (entget ent (list app)))
      (setq xd (assoc -3 ed))
      (if xd
        (progn
          (setq rec (cadr xd))
          (foreach x (cdr rec)
            (if (= (car x) 1005)
              (progn
                (setq h (cdr x))
                (setq hatch (handent h))
                (if (DT--entity-alive-p hatch)
                  (setq out (append out (list hatch)))
                )
              )
            )
          )
        )
      )
    )
  )
  out
)

(defun DT--xdata-link-sidewalls (tray walls / app ed payload wall h)
  (setq app "DT_TRAY_SIDEWALL")
  (if (not (tblsearch "APPID" app)) (regapp app))
  (if (and tray (entget tray) walls)
    (progn
      (setq payload (list app))
      (foreach wall walls
        (if (and wall (entget wall))
          (progn
            (setq h (cdr (assoc 5 (entget wall))))
            (if h (setq payload (append payload (list (cons 1005 h)))))
          )
        )
      )
      (setq ed (entget tray '("*")))
      (setq ed (DT--xdata-set-app ed app payload))
      (entmod ed)
      (entupd tray)
    )
  )
  tray
)

(defun DT--linked-sidewalls (tray / app ed xd rec item wall out)
  (setq app "DT_TRAY_SIDEWALL")
  (if (and tray (entget tray))
    (progn
      (setq ed  (entget tray (list app))
            xd  (assoc -3 ed)
            rec (if xd (cadr xd) nil))
      (if (and rec (= (car rec) app))
        (foreach item (cdr rec)
          (if (= (car item) 1005)
            (progn
              (setq wall (handent (cdr item)))
              (if (DT--entity-alive-p wall)
                (setq out (append out (list wall))))
            )
          )
        )
      )
    )
  )
  out
)

(defun DT--ensure-composite-pickstyle (/ value)
  (setq value (getvar "PICKSTYLE"))
  ;; Bit 1 secilebilir gruplari, bit 2 associative hatch secimini etkinlestirir.
  (if (= 0 (logand value 1))
    (setq value (+ value 1)))
  (if (= 0 (logand value 2))
    (setq value (+ value 2)))
  (setvar "PICKSTYLE" value)
  ;; Grup secimi kalsin, grubun etrafindaki dikdortgen sinir kutusu gorunmesin.
  (vl-catch-all-apply 'setvar (list "GROUPDISPLAYMODE" 0))
  (getvar "PICKSTYLE")
)

(defun DT--existing-group-dictionary (/ record)
  (setq record (dictsearch (namedobjdict) "ACAD_GROUP"))
  (if record (cdr (assoc -1 record)))
)

(defun DT--group-dictionary (/ dictionary)
  (setq dictionary (DT--existing-group-dictionary))
  (if (null dictionary)
    (progn
      (setq dictionary
        (entmakex
          '((0 . "DICTIONARY")
            (100 . "AcDbDictionary")
            (280 . 0)
            (281 . 1))))
      (if dictionary
        (dictadd (namedobjdict) "ACAD_GROUP" dictionary))))
  dictionary
)

(defun DT--tray-group-name (tray / handle)
  (setq handle (if tray (DT--ent-handle tray)))
  (if handle (strcat "DT$TAVA$" (strcase handle)))
)

(defun DT--dictionary-record-entity (record / item)
  (cond
    ((setq item (assoc -1 record)) (cdr item))
    ((setq item (assoc 350 record)) (cdr item))
    ((setq item (assoc 360 record)) (cdr item)))
)

(defun DT--group-by-name (name / dictionary record)
  (setq dictionary (DT--existing-group-dictionary))
  (if (and dictionary name
           (setq record (dictsearch dictionary name)))
    (DT--dictionary-record-entity record))
)

(defun DT--delete-group-by-name (name / dictionary group removed object)
  (setq dictionary (DT--existing-group-dictionary)
        group      (if name (DT--group-by-name name)))
  (if (and dictionary name group)
    (progn
      (setq removed (dictremove dictionary name))
      (setq object (if (and removed (not (eq removed T))) removed group))
      (if (and object (not (eq object T)) (entget object))
        (vl-catch-all-apply 'entdel (list object)))
      T))
)

(defun DT--delete-tray-group (tray / name)
  (setq name (DT--tray-group-name tray))
  (if name (DT--delete-group-by-name name))
)

(defun DT--unique-alive-entities (entities / ent handle seen out)
  (foreach ent entities
    (if (and ent (DT--entity-alive-p ent)
             (setq handle (DT--ent-handle ent))
             (not (member handle seen)))
      (setq seen (cons handle seen)
            out  (append out (list ent)))))
  out
)

(defun DT--tray-group-entities (tray)
  (DT--unique-alive-entities
    (append (list tray)
            (DT--linked-hatches tray)
            (DT--linked-sidewalls tray)))
)

(defun DT--make-group-object (name entities / dictionary data group)
  (setq dictionary (DT--group-dictionary))
  (if (and dictionary name entities)
    (progn
      (setq data
        '((0 . "GROUP")
          (100 . "AcDbGroup")
          (300 . "DT tava secim kabugu")
          (70 . 0)
          (71 . 1)))
      (foreach entity entities
        (setq data (append data (list (cons 340 entity)))))
      (setq group (entmakex data))
      (if (and group (null (dictadd dictionary name group)))
        (progn
          (vl-catch-all-apply 'entdel (list group))
          (setq group nil)))
      group))
)

(defun DT--refresh-tray-group (tray / name entities group)
  (if (and tray (DT--visible-tray-p tray))
    (progn
      (setq name (DT--tray-group-name tray))
      (DT--delete-tray-group tray)
      (setq entities (DT--tray-group-entities tray))
      (if (and name (> (length entities) 1))
        (setq group (DT--make-group-object name entities)))
      group))
)

(defun DT--repair-existing-tray-groups (/ ss i tray count)
  (setq ss (ssget "_X" '((-3 ("DT_TRAY_HATCH"))))
        i 0
        count 0)
  (if ss
    (while (< i (sslength ss))
      (setq tray (ssname ss i))
      (if (and tray (DT--visible-tray-p tray)
               (DT--refresh-tray-group tray))
        (setq count (1+ count)))
      (setq i (1+ i))))
  count
)

(defun DT--remove-generated-tray-groups (/ dictionary record item name entries entry removed object)
  (setq dictionary (DT--existing-group-dictionary))
  (if dictionary
    (progn
      ;; Dictionary DXF kaydindaki 3/350 ciftleri grup adi ve nesnesidir.
      (setq record (entget dictionary)
            name nil)
      (foreach item record
        (cond
          ((= (car item) 3)
            (setq name (cdr item)))
          ((and name (member (car item) '(350 360)))
            (if (wcmatch (strcase name) "DT$TAVA$*")
              (setq entries (cons (cons name (cdr item)) entries)))
            (setq name nil))))
      (foreach entry entries
        (setq removed (dictremove dictionary (car entry)))
        (setq object (if (and removed (not (eq removed T))) removed (cdr entry)))
        (if (and object (not (eq object T)) (entget object))
          (vl-catch-all-apply 'entdel (list object))))
      (length entries))
    0)
)

(defun DT--tray-corner-points-3d (tray / ed typ z item ent vd p out)
  (if (and tray (setq ed (entget tray)))
    (progn
      (setq typ (cdr (assoc 0 ed)))
      (cond
        ((= typ "LWPOLYLINE")
          (setq z (if (assoc 38 ed) (cdr (assoc 38 ed)) 0.0))
          (foreach item ed
            (if (= (car item) 10)
              (setq p (cdr item)
                    out (append out (list (list (car p) (cadr p) z)))))))
        ((= typ "POLYLINE")
          (setq ent (entnext tray))
          (while (and ent (/= (cdr (assoc 0 (entget ent))) "SEQEND"))
            (setq vd (entget ent))
            (if (= (cdr (assoc 0 vd)) "VERTEX")
              (progn
                (setq p (cdr (assoc 10 vd)))
                (if p
                  (setq out
                    (append out
                      (list (list (car p) (cadr p) (if (caddr p) (caddr p) 0.0))))))))
            (setq ent (entnext ent))))))
  )
  out
)

(defun DT--tray-geometry-signature (tray / ed typ pts)
  (if (and tray (setq ed (entget tray)))
    (progn
      (setq typ (cdr (assoc 0 ed))
            pts (DT--tray-corner-points-3d tray))
      (if pts (cons typ pts)))
  )
)

(defun DT--tray-signature-map (/ ss i tray h sig out)
  (setq ss (ssget "_X" '((-3 ("DT_TRAY_HATCH"))))
        i 0)
  (if ss
    (while (< i (sslength ss))
      (setq tray (ssname ss i)
            h    (if tray (DT--ent-handle tray))
            sig  (if (and tray (DT--visible-tray-p tray))
                   (DT--tray-geometry-signature tray)))
      (if (and h sig) (setq out (cons (cons h sig) out)))
      (setq i (1+ i))))
  out
)

(defun DT--face-normal-edge-height (face normal / ed pts p0 p1 p2 p3 pairs pair vec unit align len best)
  (if (and face normal (setq ed (entget face)))
    (progn
      (setq p0 (cdr (assoc 10 ed))
            p1 (cdr (assoc 11 ed))
            p2 (cdr (assoc 12 ed))
            p3 (cdr (assoc 13 ed))
            pts (list p0 p1 p2 p3))
      (if (vl-every 'listp pts)
        (progn
          (setq pairs
            (list
              (list p0 p1)
              (list p1 p2)
              (list p2 p3)
              (list p3 p0)))
          (foreach pair pairs
            (setq vec  (DT--vec3-sub (cadr pair) (car pair))
                  unit (DT--unit3 vec))
            (if unit
              (progn
                (setq align (abs (DT--dot3 unit normal))
                      len   (distance (car pair) (cadr pair)))
                (if (and (> align 0.999)
                         (> len 0.000001)
                         (or (null best) (> len best)))
                  (setq best len)))))))))
  (if best best 0.0)
)

(defun DT--faces-normal-edge-height (faces normal / face value best)
  (foreach face faces
    (setq value (DT--face-normal-edge-height face normal))
    (if (and (> value 0.0) (or (null best) (> value best)))
      (setq best value)))
  (if best best 0.0)
)

(defun DT--block-normal-edge-height (name normal / blockEnt ent ed faces)
  (if (and name normal (setq blockEnt (tblobjname "BLOCK" name)))
    (progn
      (setq ent (entnext blockEnt))
      (while (and ent
                  (setq ed (entget ent))
                  (/= (cdr (assoc 0 ed)) "ENDBLK"))
        (if (= (cdr (assoc 0 ed)) "3DFACE")
          (setq faces (cons ent faces)))
        (setq ent (entnext ent)))))
  (DT--faces-normal-edge-height faces normal)
)

(defun DT--linked-sidewall-height
  (tray / corners normal walls height)
  ;; Global min/max Z includes the complete elevation change on a sloped tray.
  ;; Measure only edges parallel to the tray plane normal; those are the real
  ;; sidewall-height edges, independent of route slope and world orientation.
  (setq corners (DT--tray-corner-points-3d tray))
  (if (= (length corners) 4)
    (setq normal
      (DT--plane-normal
        (list (nth 0 corners) (nth 3 corners) (nth 1 corners)))))
  (if normal
    (progn
      (setq walls  (DT--linked-sidewalls tray)
            height (DT--faces-normal-edge-height walls normal))))
  (if height height 0.0)
)

(defun DT--hatch-source-is-p (hatch source / ed item after97 found)
  (if (and hatch source (setq ed (entget hatch)))
    (foreach item ed
      (cond
        ((= (car item) 97) (setq after97 (> (cdr item) 0)))
        ((and after97 (= (car item) 330))
          (if (eq (cdr item) source) (setq found T))
          (setq after97 nil)))))
  found
)

(defun DT--delete-linked-sidewall-geometry (tray / hatches walls keepTop hatch wall h)
  (setq hatches (DT--linked-hatches tray)
        walls   (DT--linked-sidewalls tray))
  (foreach hatch hatches
    (if (DT--hatch-source-is-p hatch tray) (setq keepTop hatch)))
  (if (and (null keepTop) hatches) (setq keepTop (car hatches)))
  (foreach hatch hatches
    (if (and hatch (not (eq hatch keepTop)) (entget hatch))
      (progn
        (setq h (DT--ent-handle hatch))
        (vl-catch-all-apply 'entdel (list hatch))
        (if h (DT--remember-deleted-handle h)))))
  (foreach wall walls
    (if (and wall (entget wall))
      (progn
        (setq h (DT--ent-handle wall))
        (vl-catch-all-apply 'entdel (list wall))
        (if h (DT--remember-deleted-handle h)))))
  keepTop
)

(defun DT--rebuild-tray-sidewall-geometry
  (tray / pts meta lay mode sideMm sidePlan inferredHeight
          *DT_ACTIVE_MODE* *DT_ACTIVE_LAYER* *DT_ACTIVE_ELEVATION*
          *DT_ACTIVE_SIDE_HEIGHT* *DT_ACTIVE_SIDE_HEIGHT_MM*)
  (if (and tray (DT--visible-tray-p tray))
    (progn
      (setq pts (DT--tray-corner-points-3d tray))
      (if (= (length pts) 4)
        (progn
          (setq meta           (DT--tray-meta-effective tray)
                lay            (DT--base-layer-name (cdr (assoc 8 (entget tray))))
                mode           (DT--normalize-mode
                                 (if (and meta (car meta))
                                   (car meta)
                                   (DT--mode-from-layer lay)))
                inferredHeight (DT--linked-sidewall-height tray)
                sideMm         (if (and meta (numberp (caddr meta)) (> (caddr meta) 0.0))
                                 (caddr meta)
                                 (/ (* inferredHeight 10.0)
                                    (max 0.000000001 (DEG:PLAN-UNIT-SCALE))))
                sidePlan       (if (> sideMm 0.0) (DT--plan-side-height sideMm) inferredHeight)
                *DT_ACTIVE_MODE* mode
                *DT_ACTIVE_LAYER* lay
                *DT_ACTIVE_ELEVATION* (if (caddr (car pts)) (caddr (car pts)) 0.0)
                *DT_ACTIVE_SIDE_HEIGHT_MM* sideMm
                *DT_ACTIVE_SIDE_HEIGHT* sidePlan)
          (DT--delete-tray-group tray)
          (DT--delete-linked-sidewall-geometry tray)
          (if (> sidePlan 0.0)
            (DT--make-tray-sidewalls
              tray (nth 0 pts) (nth 1 pts) (nth 2 pts) (nth 3 pts)))
          (DT--repair-tray-hatch-associations tray)
          (DT--refresh-tray-group tray)
          T)))
  )
)

(defun DT--tray-sidewall-local-normal-p (tray walls / pts expected wall ed base top actual)
  (setq pts (DT--tray-corner-points-3d tray))
  (if (and (= (length pts) 4) (>= (length walls) 4))
    (progn
      (setq expected (DT--plane-normal (list (nth 0 pts) (nth 3 pts) (nth 1 pts)))
            wall     (nth 3 walls)
            ed       (if wall (entget wall))
            base     (if ed (cdr (assoc 10 ed)))
            top      (if ed (cdr (assoc 13 ed)))
            actual   (if (and base top)
                       (DT--unit3 (DT--vec3-sub top base))))
      (and expected actual (> (DT--dot3 expected actual) 0.9999)))
  )
)

(defun DT--repair-existing-tray-sidewalls (/ ss i tray meta walls hatches sideMm count)
  (setq ss (ssget "_X" '((-3 ("DT_TRAY_HATCH"))))
        i 0
        count 0)
  (if ss
    (while (< i (sslength ss))
      (setq tray (ssname ss i))
      (if (and tray (DT--visible-tray-p tray))
        (progn
          (setq meta    (DT--tray-meta-effective tray)
                walls   (DT--linked-sidewalls tray)
                hatches (DT--linked-hatches tray)
                sideMm  (if (and meta (numberp (caddr meta))) (caddr meta) 0.0))
          (if (and (or (> sideMm 0.0) walls)
                   (or (/= (length walls) 13)
                       (/= (length hatches) 14)
                       (not (DT--tray-sidewall-local-normal-p tray walls))))
            (if (DT--rebuild-tray-sidewall-geometry tray)
              (setq count (1+ count))))))
      (setq i (1+ i))))
  count
)

(defun DT--repair-existing-model-hatch-colors (/ ss i hatch ed lay base count)
  (setq ss (ssget "_X" '((0 . "HATCH")))
        i 0
        count 0)
  (if ss
    (while (< i (sslength ss))
      (setq hatch (ssname ss i)
            ed    (if hatch (entget hatch))
            lay   (if ed (cdr (assoc 8 ed)))
            base  (if lay (DT--base-layer-name lay)))
      (if (and hatch base (DT--tray-visible-layer-p base))
        (progn
          (DT--set-layer-bylayer hatch base)
          (setq count (1+ count))))
      (setq i (1+ i))))
  count
)

(defun DT--repair-existing-tray-line-layers (/ ss i tray base line wall hatch count)
  (DT--ensure-type-layers)
  (DT--ensure-layer "e_tava" 7 nil)
  (DT--ensure-layer "e_tava_çizgi" 7 nil)
  (setq ss (ssget "_X" '((-3 ("DT_TRAY_HATCH"))))
        i 0
        count 0)
  (if ss
    (while (< i (sslength ss))
      (setq tray (ssname ss i))
      (if (and tray (DT--visible-tray-p tray))
        (progn
          (setq base (DT--base-layer-name (cdr (assoc 8 (entget tray))))
                line (DT--line-layer-name base))
          (DT--ensure-layer line (DT--layer-color-for-name base) nil)
          (DT--set-layer-bylayer tray line)
          (foreach wall (DT--linked-sidewalls tray)
            (if (entget wall) (DT--set-layer-bylayer wall line)))
          (foreach hatch (DT--linked-hatches tray)
            (if (entget hatch) (DT--set-layer-bylayer hatch base)))
          (DT--refresh-tray-group tray)
          (setq count (1+ count))))
      (setq i (1+ i))))
  (DT--repair-existing-model-hatch-colors)
  count
)

(defun DT--repair-existing-fitting-line-layers
  (/ ss i ins ed base mode name done count
     *DT_ACTIVE_MODE* *DT_ACTIVE_LAYER*)
  (setq ss (ssget "_X" '((0 . "INSERT") (-3 ("DT_FITTING"))))
        i 0
        count 0)
  (if ss
    (while (< i (sslength ss))
      (setq ins  (ssname ss i)
            ed   (entget ins)
            base (DT--base-layer-name (cdr (assoc 8 ed)))
            mode (DT--mode-from-layer base)
            name (cdr (assoc 2 ed)))
      (if (and name (not (member (strcase name) done)))
        (progn
          (setq *DT_ACTIVE_MODE* mode
                *DT_ACTIVE_LAYER* base)
          (DT--ensure-layer (DT--line-layer-name base)
                            (DT--layer-color-for-name base) nil)
          (DT--set-block-linework-050 name)
          (setq done  (cons (strcase name) done)
                count (1+ count))))
      (if (and ins base (/= base ""))
        (DT--set-entity-layer-only ins base))
      (setq i (1+ i))))
  count
)

(defun DT--sidewall-sync-command-name (info / cmd)
  (setq cmd (if (and (listp info) (car info)) (strcase (car info)) ""))
  cmd
)

(defun DT--composite-undo-command-p (cmd)
  (member cmd '("U" "UNDO" "REDO" "MREDO"))
)

(defun DT--sidewall-sync-watched-command-p (cmd)
  (and cmd
       (or (= cmd "STRETCH")
           (= cmd "GRIP_STRETCH")
           (= cmd "MOVE")
           (= cmd "GRIP_MOVE")
           (= cmd "ROTATE")
           (= cmd "GRIP_ROTATE")
           (= cmd "SCALE")
           (= cmd "GRIP_SCALE")
           (= cmd "MIRROR")
           (= cmd "ALIGN")))
)

(defun DT--composite-stretch-command-p (cmd)
  (member cmd '("STRETCH" "GRIP_STRETCH"))
)

(defun DT--composite-stretch-selection-begin (cmd / value)
  (if (DT--composite-stretch-command-p cmd)
    (progn
      (setq value (getvar "PICKSTYLE")
            *DT_COMPOSITE_PICKSTYLE_BEFORE* value)
      ;; STRETCH geometriyi ana sinirdan yonetsin; grup ve hatch secimi gecici kapanir.
      (setvar "PICKSTYLE" 0)))
)

(defun DT--composite-stretch-selection-end ()
  (if (and (boundp '*DT_COMPOSITE_PICKSTYLE_BEFORE*)
           (numberp *DT_COMPOSITE_PICKSTYLE_BEFORE*))
    (setvar "PICKSTYLE" *DT_COMPOSITE_PICKSTYLE_BEFORE*))
  (setq *DT_COMPOSITE_PICKSTYLE_BEFORE* nil)
)

(defun DT--composite-erase-map (/ ss i tray trayHandle entities ent handle handles out)
  (setq ss (ssget "_X" '((-3 ("DT_TRAY_HATCH"))))
        i 0)
  (if ss
    (while (< i (sslength ss))
      (setq tray       (ssname ss i)
            trayHandle (if tray (DT--ent-handle tray))
            entities   (if tray
                         (append (DT--linked-hatches tray) (DT--linked-sidewalls tray)))
            handles    nil)
      (foreach ent entities
        (setq handle (DT--ent-handle ent))
        (if handle (setq handles (cons handle handles))))
      (if (and trayHandle handles)
        (setq out (cons (cons trayHandle handles) out)))
      (setq i (1+ i))))
  out
)

(defun DT--handle-alive-p (handle / ent)
  (setq ent (if handle (handent handle)))
  (and ent (DT--entity-alive-p ent))
)

(defun DT--composite-erase-finish (/ record trayHandle tray affected handle ent)
  (if (and (boundp '*DT_COMPOSITE_ERASE_BEFORE*)
           *DT_COMPOSITE_ERASE_BEFORE*
           (not *DT_SIDEWALL_SYNC_BUSY*))
    (progn
      (setq *DT_SIDEWALL_SYNC_BUSY* T)
      (foreach record *DT_COMPOSITE_ERASE_BEFORE*
        (setq trayHandle (car record)
              tray       (handent trayHandle)
              affected   (not (and tray (DT--entity-alive-p tray))))
        (if (not affected)
          (foreach handle (cdr record)
            (if (not (DT--handle-alive-p handle)) (setq affected T))))
        (if affected
          (progn
            (DT--delete-group-by-name
              (strcat "DT$TAVA$" (strcase trayHandle)))
            (if (and tray (DT--entity-alive-p tray))
              (DT--safe-delete-ent tray)
              (foreach handle (cdr record)
                (setq ent (handent handle))
                (if (and ent (DT--entity-alive-p ent))
                  (vl-catch-all-apply 'entdel (list ent)))))
            (DT--remember-deleted-handle trayHandle)
            (foreach handle (cdr record) (DT--remember-deleted-handle handle)))))
      (setq *DT_COMPOSITE_ERASE_BEFORE* nil
            *DT_SIDEWALL_SYNC_BUSY* nil)))
  (princ)
)

(defun DT--sidewall-sync-command-start (reactor info / cmd)
  (if (not *DT_SIDEWALL_SYNC_BUSY*)
    (progn
      (setq cmd (DT--sidewall-sync-command-name info))
      (DT--composite-stretch-selection-begin cmd)
      (cond
        ((= cmd "ERASE")
          (setq *DT_COMPOSITE_ERASE_BEFORE* (DT--composite-erase-map)))
        ((DT--sidewall-sync-watched-command-p cmd)
          (setq *DT_SIDEWALL_SYNC_COMMAND* cmd
                *DT_SIDEWALL_SYNC_BEFORE* (DT--tray-signature-map))))))
  (princ)
)

(defun DT--sidewall-sync-command-finish (reactor info / cmd before now rec old tray result)
  (setq cmd (DT--sidewall-sync-command-name info))
  (if (= cmd "ERASE") (DT--composite-erase-finish))
  (if (DT--composite-undo-command-p cmd)
    (progn
      (setq *DT_DELETED_HANDLES* nil)
      (vl-catch-all-apply 'DT--repair-existing-hatch-associations '())
      (vl-catch-all-apply 'DT--repair-existing-tray-sidewalls '())
      (vl-catch-all-apply 'DT--repair-existing-tray-groups '())))
  (if (and (not *DT_SIDEWALL_SYNC_BUSY*)
           *DT_SIDEWALL_SYNC_COMMAND*
           (= cmd *DT_SIDEWALL_SYNC_COMMAND*))
    (progn
      (setq *DT_SIDEWALL_SYNC_BUSY* T
            before *DT_SIDEWALL_SYNC_BEFORE*
            now    (DT--tray-signature-map))
      (foreach rec now
        (setq old (assoc (car rec) before))
        (if (and old (not (equal (cdr old) (cdr rec) 0.000001)))
          (progn
            (setq tray (handent (car rec)))
            (if tray
              (setq result
                (vl-catch-all-apply 'DT--rebuild-tray-sidewall-geometry (list tray)))))))
      (setq *DT_SIDEWALL_SYNC_BEFORE* nil
            *DT_SIDEWALL_SYNC_COMMAND* nil
            *DT_SIDEWALL_SYNC_BUSY* nil)))
  (DT--composite-stretch-selection-end)
  (princ)
)

(defun DT--sidewall-sync-command-cancel (reactor info)
  (DT--composite-stretch-selection-end)
  (setq *DT_SIDEWALL_SYNC_BEFORE* nil
        *DT_SIDEWALL_SYNC_COMMAND* nil
        *DT_COMPOSITE_ERASE_BEFORE* nil
        *DT_SIDEWALL_SYNC_BUSY* nil)
  (princ)
)

(defun DT--reset-sidewall-sync-reactor ()
  (if (and (boundp '*DT_SIDEWALL_SYNC_REACTOR*) *DT_SIDEWALL_SYNC_REACTOR*)
    (vl-catch-all-apply 'vlr-remove (list *DT_SIDEWALL_SYNC_REACTOR*)))
  (setq *DT_SIDEWALL_SYNC_REACTOR*
    (vl-catch-all-apply
      'vlr-command-reactor
      (list
        nil
        (list
          (cons :vlr-commandWillStart 'DT--sidewall-sync-command-start)
          (cons :vlr-commandEnded 'DT--sidewall-sync-command-finish)
          (cons :vlr-commandCancelled 'DT--sidewall-sync-command-cancel)
          (cons :vlr-commandFailed 'DT--sidewall-sync-command-cancel)))))
  (if (vl-catch-all-error-p *DT_SIDEWALL_SYNC_REACTOR*)
    (setq *DT_SIDEWALL_SYNC_REACTOR* nil))
  *DT_SIDEWALL_SYNC_REACTOR*
)

(defun DT--repair-tray-hatch-associations (tray / hatches walls hatchList)
  (setq hatches (DT--linked-hatches tray)
        walls   (DT--linked-sidewalls tray))
  (if hatches
    (progn
      (if (or (null walls) (= (length hatches) (1+ (length walls))))
        (progn
          (DT--hatch-set-source (car hatches) tray)
          (setq hatchList (cdr hatches)))
        (setq hatchList hatches))
      (while (and hatchList walls)
        (DT--hatch-set-source (car hatchList) (car walls))
        (setq hatchList (cdr hatchList)
              walls     (cdr walls))))
  )
  tray
)

(defun DT--repair-existing-hatch-associations (/ ss i tray)
  (setq ss (ssget "_X" '((-3 ("DT_TRAY_HATCH"))))
        i 0)
  (if ss
    (while (< i (sslength ss))
      (setq tray (ssname ss i))
      (if (DT--visible-tray-p tray)
        (DT--repair-tray-hatch-associations tray))
      (setq i (1+ i))))
  T
)

(defun DT--safe-delete-ent (ent / h obj r hatch hh wall wh)
  (DT--delete-tray-group ent)
  (foreach hatch (DT--linked-hatches ent)
    (if (and hatch (entget hatch))
      (progn
        (setq hh (DT--ent-handle hatch))
        (vl-catch-all-apply 'entdel (list hatch))
        (if hh (DT--remember-deleted-handle hh))
      )
    )
  )
  (foreach wall (DT--linked-sidewalls ent)
    (if (and wall (entget wall))
      (progn
        (setq wh (DT--ent-handle wall))
        (vl-catch-all-apply 'entdel (list wall))
        (if wh (DT--remember-deleted-handle wh))
      )
    )
  )
  (setq h (DT--ent-handle ent))
  (if (and (DT--entity-alive-p ent) (not (DT--deleted-handle-p h)))
    (progn
      (setq obj (DT--vla-object-for-ent ent))
      (setq r
        (if obj
          (vl-catch-all-apply 'vla-delete (list obj))
          (vl-catch-all-apply 'entdel (list ent))
        )
      )
      (if (not (vl-catch-all-error-p r))
        (DT--remember-deleted-handle h)
      )
    )
  )
)
(defun DT--linked-trays (center / app ed xd rec h tray out x)
  (setq app "DT_TRAY_LINK")
  (setq ed (entget center (list app)))
  (setq xd (assoc -3 ed))
  (if xd
    (progn
      (setq rec (cadr xd))
      (foreach x (cdr rec)
        (if (= (car x) 1005)
          (progn
            (setq h (cdr x))
            (setq tray (handent h))
            (if (DT--entity-alive-p tray)
              (setq out (append out (list tray)))
            )
          )
        )
      )
    )
  )
  out
)

(defun DT--linked-tray (center)
  (car (DT--linked-trays center))
)

(defun DT--replace-linked-tray (center oldTray newTray / tray out replaced)
  (if (and center oldTray newTray
           (entget center) (entget oldTray) (entget newTray))
    (progn
      (foreach tray (DT--linked-trays center)
        (if (eq tray oldTray)
          (progn
            (setq out (append out (list newTray))
                  replaced T))
          (setq out (append out (list tray)))))
      (if (not replaced)
        (setq out (append out (list newTray))))
      (DT--xdata-link-tray center out)
      newTray))
)

(defun DT--cut-point (cut)
  (if (and (listp cut) (listp (car cut)))
    (car cut)
    cut
  )
)

(defun DT--cut-gap (cut fallback)
  (if (and (listp cut) (listp (car cut)) (numberp (cadr cut)) (> (cadr cut) 0.0))
    (cadr cut)
    fallback
  )
)

(defun DT--cut-encode (cut / p gap)
  (setq p (DT--cut-point cut))
  (setq gap (if (and (listp cut) (listp (car cut))) (cadr cut) nil))
  (strcat
    (rtos (car p) 2 12)
    "|"
    (rtos (cadr p) 2 12)
    (if (and (numberp gap) (> gap 0.0))
      (strcat "|" (rtos gap 2 12))
      ""
    )
  )
)

(defun DT--cut-decode (s / pos rest pos2 p gap)
  (if (and s (setq pos (vl-string-search "|" s)))
    (progn
      (setq rest (substr s (+ pos 2)))
      (setq pos2 (vl-string-search "|" rest))
      (if pos2
        (progn
          (setq p
            (list
              (atof (substr s 1 pos))
              (atof (substr rest 1 pos2))
              0.0
            )
          )
          (setq gap (atof (substr rest (+ pos2 2))))
        )
        (setq p
          (list
            (atof (substr s 1 pos))
            (atof rest)
            0.0
          )
        )
      )
      (list p (if (and (numberp gap) (> gap 0.0)) gap nil))
    )
    nil
  )
)

(defun DT--plus-cuts (center / app ed xd rec out x cut)
  (setq app "DT_PLUS_CUTS")
  (setq ed (entget center (list app)))
  (setq xd (assoc -3 ed))
  (if xd
    (progn
      (setq rec (cadr xd))
      (foreach x (cdr rec)
        (if (= (car x) 1000)
          (progn
            (setq cut (DT--cut-decode (cdr x)))
            (if cut (setq out (append out (list cut))))
          )
        )
      )
    )
  )
  out
)

(defun DT--set-plus-cuts (center cuts / app ed payload cut)
  (setq app "DT_PLUS_CUTS")
  (if (not (tblsearch "APPID" app)) (regapp app))
  (if (and center (entget center))
    (progn
      (setq payload (list app))
      (foreach cut cuts
        (setq payload (append payload (list (cons 1000 (DT--cut-encode cut)))))
      )
      (setq ed (entget center '("*")))
      ;; Bos cut listesinde eski DT_PLUS_CUTS XData kaydi kalmasin.
      (setq ed (DT--xdata-set-app ed app payload))
      (entmod ed)
      (entupd center)
    )
  )
  center
)

(defun DT--add-plus-cut (center pt gap / cuts out cut oldGap found)
  (setq cuts (DT--plus-cuts center))
  (foreach cut cuts
    (if (<= (distance pt (DT--cut-point cut)) 0.001)
      (progn
        (setq oldGap (DT--cut-gap cut 0.0))
        (setq out
          (append out
            (list
              (list pt
                (cond
                  ((and (numberp gap) (> gap oldGap)) gap)
                  ((> oldGap 0.0) oldGap)
                  (T nil)
                )
              )
            )
          )
        )
        (setq found T)
      )
      (setq out (append out (list cut)))
    )
  )
  (if (not found)
    (setq out (append out (list (list pt gap))))
  )
  (DT--set-plus-cuts center out)
  out
)

(defun DT--delete-ents (ents / ent)
  (foreach ent ents
    (DT--safe-delete-ent ent)
  )
)

(defun DT--visible-tray-segments (trays / out tray seg)
  (foreach tray trays
    (if (DT--visible-tray-p tray)
      (progn
        (setq seg (DT--tray-center-seg tray))
        (if (and seg (> (distance (car seg) (cadr seg)) 0.001))
          (setq out (append out (list seg)))
        )
      )
    )
  )
  out
)

(defun DT--shift-visible-segments-point
  (segs oldPoint newPoint tol / seg a b out)
  (foreach seg segs
    (if (and seg (= (length seg) 2))
      (progn
        (setq a (car seg)
              b (cadr seg))
        (if (<= (DT--distance-xy a oldPoint) tol)
          (setq a
            (list
              (car newPoint)
              (cadr newPoint)
              (if (caddr a) (caddr a) 0.0))))
        (if (<= (DT--distance-xy b oldPoint) tol)
          (setq b
            (list
              (car newPoint)
              (cadr newPoint)
              (if (caddr b) (caddr b) 0.0))))
        (if (> (DT--distance-xy a b) 0.001)
          (setq out (append out (list (list a b))))))))
  out
)

(defun DT--build-straight-pieces-for-segs (segs width cuts / out seg pieces)
  (foreach seg segs
    (setq pieces (DT--build-straight-pieces seg width cuts))
    (if pieces (setq out (append out pieces)))
  )
  out
)

(defun DT--replace-seg-point-near (point pairs / hit pair)
  (foreach pair pairs
    (if (and (null hit)
             (<= (DT--distance-xy point (car pair)) 0.01))
      (setq hit (cadr pair))
    )
  )
  (if hit hit point)
)

(defun DT--retarget-visible-segs-for-width (segs pts oldWidth newWidth / oldCorners newCorners pairs oldRec newRec oldQ1 oldQ2 newQ1 newQ2 out seg)
  (if (and segs pts
           (numberp oldWidth) (> oldWidth 0.0)
           (numberp newWidth) (> newWidth 0.0)
           (not (equal oldWidth newWidth 0.000001)))
    (progn
      (setq oldCorners (DT--corner-records pts oldWidth)
            newCorners (DT--corner-records pts newWidth))
      (foreach oldRec oldCorners
        (setq newRec (DT--corner-at newCorners (car oldRec)))
        (if newRec
          (progn
            (setq oldQ1 (DT--pt+ (nth 1 oldRec) (nth 2 oldRec) (- (nth 4 oldRec)))
                  oldQ2 (DT--pt+ (nth 1 oldRec) (nth 3 oldRec)    (nth 4 oldRec))
                  newQ1 (DT--pt+ (nth 1 newRec) (nth 2 newRec) (- (nth 4 newRec)))
                  newQ2 (DT--pt+ (nth 1 newRec) (nth 3 newRec)    (nth 4 newRec))
                  pairs (append pairs (list (list oldQ1 newQ1) (list oldQ2 newQ2))))
          )
        )
      )
      (foreach seg segs
        (if (and seg (= (length seg) 2))
          (setq out
            (append out
              (list
                (list
                  (DT--replace-seg-point-near (car seg) pairs)
                  (DT--replace-seg-point-near (cadr seg) pairs)))))
        )
      )
      out
    )
    segs
  )
)

(defun DT--piece-affected-by-cuts-p (piece cuts width / seg)
  (setq seg (DT--tray-center-seg piece))
  (and seg
       (> (distance (car seg) (cadr seg)) 0.001)
       (DT--segment-cut-ranges
         (car seg) (cadr seg) cuts width
         0.0 (distance (car seg) (cadr seg))))
)

(defun DT--rebuild-center-pieces (center width forcePts / oldPieces pts cuts newPieces useWidth sourceWidth oldActive oldElevation oldSide oldSideMm oldActive3d center3d useLayer visibleSegs endpointElevations elevationProfile meta sideMm localRebuild affectedPieces affectedSegs preservedPieces piece seg createdPieces deletePieces noChange *DT_BUILD_ROUTE_PTS* *DT_BUILD_START_ELEVATION* *DT_BUILD_END_ELEVATION* *DT_BUILD_START_TRIM* *DT_BUILD_END_TRIM* *DT_BUILD_START_LINE_ELEVATION* *DT_BUILD_END_LINE_ELEVATION*)
  (if (and center (entget center))
    (progn
      (setq oldPieces         (DT--linked-trays center)
            pts               (g365_get_pts center)
            endpointElevations (DT--center-end-elevations center)
            elevationProfile  (DT--center-elevation-profile center)
            *DT_BUILD_ROUTE_PTS* pts
            *DT_BUILD_START_ELEVATION* (car endpointElevations)
            *DT_BUILD_END_ELEVATION*   (cadr endpointElevations)
            *DT_BUILD_START_TRIM*      (car elevationProfile)
            *DT_BUILD_END_TRIM*        (cadr elevationProfile)
            *DT_BUILD_START_LINE_ELEVATION* (if (numberp (nth 2 elevationProfile))
                                               (nth 2 elevationProfile)
                                               (car endpointElevations))
            *DT_BUILD_END_LINE_ELEVATION*   (if (numberp (nth 3 elevationProfile))
                                               (nth 3 elevationProfile)
                                               (cadr endpointElevations)))
      (DT--cleanup-stale-plus-cuts center)
      (setq cuts (DT--plus-cuts center))
      (setq useWidth (DT--center-width center width))
      (setq meta         (DT--tray-meta center)
            sideMm       (if (and meta (numberp (caddr meta)) (> (caddr meta) 0.0))
                           (caddr meta)
                           (DT--active-side-height-mm))
            oldActive    *DT_ACTIVE_LAYER*
            oldElevation (DT--active-elevation)
            oldSide      (DT--active-side-height)
            oldSideMm    (DT--active-side-height-mm)
            oldActive3d  (DT--active-3d-enabled-p)
            center3d     (DT--entity-3d-enabled-p center)
            *DT_ACTIVE_ELEVATION* (DT--entity-elevation center)
            *DT_ACTIVE_SIDE_HEIGHT_MM* sideMm
            *DT_ACTIVE_SIDE_HEIGHT* (DT--plan-side-height sideMm)
            *DT_ACTIVE_3D* center3d)
      (setq useLayer (DT--center-layer center oldActive))
      (if useLayer (setq *DT_ACTIVE_LAYER* useLayer))
      ;; Eski centerline uzun kalmis olabilir. Rebuild yaparken mevcut gorunur
      ;; tava parcalarini baz al; silinmis bosluklari tekrar uretme.
      (setq visibleSegs (DT--visible-tray-segments oldPieces))
      (if (and visibleSegs
               (boundp '*DT_REBUILD_POINT_SHIFT*)
               *DT_REBUILD_POINT_SHIFT*
               (= (length *DT_REBUILD_POINT_SHIFT*) 3))
        (setq visibleSegs
          (DT--shift-visible-segments-point
            visibleSegs
            (car *DT_REBUILD_POINT_SHIFT*)
            (cadr *DT_REBUILD_POINT_SHIFT*)
            (caddr *DT_REBUILD_POINT_SHIFT*))))
      (setq sourceWidth
        (if (and (boundp '*DT_REBUILD_SOURCE_WIDTH*)
                 (numberp *DT_REBUILD_SOURCE_WIDTH*)
                 (> *DT_REBUILD_SOURCE_WIDTH* 0.0))
          *DT_REBUILD_SOURCE_WIDTH*
          useWidth))
      (if visibleSegs
        (setq visibleSegs
          (DT--retarget-visible-segs-for-width
            visibleSegs pts sourceWidth useWidth)))
      ;; Junction kesiminde uzun tavanin tamamini degil, kesimin denk geldigi
      ;; fiziksel parcayi yeniden kur. Resize ve nokta kaydirmalari tam rebuild'dir.
      (setq localRebuild
        (and
          (not forcePts)
          oldPieces
          cuts
          (equal sourceWidth useWidth 0.0001)
          (or
            (not (boundp '*DT_REBUILD_POINT_SHIFT*))
            (null *DT_REBUILD_POINT_SHIFT*))))
      (if localRebuild
        (foreach piece oldPieces
          (if (DT--piece-affected-by-cuts-p piece cuts useWidth)
            (progn
              (setq affectedPieces (cons piece affectedPieces)
                    seg (DT--tray-center-seg piece))
              (if seg (setq affectedSegs (cons seg affectedSegs))))
            (setq preservedPieces (cons piece preservedPieces)))))
      (setq affectedPieces (reverse affectedPieces)
            affectedSegs (reverse affectedSegs)
            preservedPieces (reverse preservedPieces))
      (cond
        ((and localRebuild affectedPieces)
          (setq createdPieces
            (DT--build-straight-pieces-for-segs
              affectedSegs useWidth cuts))
          (setq newPieces (append preservedPieces createdPieces)
                deletePieces affectedPieces))
        ((and localRebuild (null affectedPieces))
          (setq newPieces oldPieces
                noChange T))
        ((and (not forcePts) visibleSegs)
          (setq newPieces (DT--build-straight-pieces-for-segs visibleSegs useWidth cuts)
                createdPieces newPieces
                deletePieces oldPieces))
        ((and pts (> (length pts) 1))
          (setq newPieces (DT--build-straight-pieces pts useWidth cuts)
                createdPieces newPieces
                deletePieces oldPieces))
      )
      (if newPieces
        (progn
          (if (not noChange)
            (progn
              (DT--delete-ents deletePieces)
              (DT--xdata-link-tray center newPieces)))
          ;; A junction rebuild creates pieces before linking them to the
          ;; center. Copy the authoritative center metadata afterwards so
          ;; side height and elevation never fall back to inferred values.
          (if meta
            (foreach piece createdPieces
              (DT--set-tray-meta-one
                piece
                (car meta)
                (cadr meta)
                (caddr meta)
                (nth 3 meta))))
          (foreach piece createdPieces
            (DT--set-entity-3d-mode piece center3d))
        )
      )
      (setq *DT_ACTIVE_LAYER* oldActive
            *DT_ACTIVE_ELEVATION* oldElevation
            *DT_ACTIVE_SIDE_HEIGHT* oldSide
            *DT_ACTIVE_SIDE_HEIGHT_MM* oldSideMm
            *DT_ACTIVE_3D* oldActive3d)
    )
  )
  newPieces
)
(defun DT--center-in-list-p (center centers / hit c)
  (foreach c centers
    (if (eq center c) (setq hit T))
  )
  hit
)

(defun DT--point-dxf-items (pts / out p)
  (foreach p pts
    (setq out (append out (list (cons 10 (list (car p) (cadr p))))))
  )
  out
)

(defun DT--set-center-points (center pts / ed out item inserted)
  (if (and center (entget center) pts
           (= (cdr (assoc 0 (entget center))) "LWPOLYLINE"))
    (progn
      (setq ed (entget center '("*")))
      (foreach item ed
        (cond
          ((= (car item) 90)
            (setq out (append out (list (cons 90 (length pts))))))
          ((= (car item) 10)
            (if (not inserted)
              (progn
                (setq out (append out (DT--point-dxf-items pts)))
                (setq inserted T)
              )
            ))
          ((member (car item) '(40 41 42 91))
            nil)
          ((= (car item) -3)
            (if (not inserted)
              (progn
                (setq out (append out (DT--point-dxf-items pts)))
                (setq inserted T)
              )
            )
            (setq out (append out (list item))))
          (T
            (setq out (append out (list item))))
        )
      )
      (if (not inserted)
        (setq out (append out (DT--point-dxf-items pts)))
      )
      (entmod out)
      (entupd center)
    )
  )
  center
)

(defun DT--merge-center-contact-point (center adjustedPts pt / curPts changed)
  (if (and center (entget center) adjustedPts pt)
    (progn
      (setq curPts (g365_get_pts center))
      (if (and curPts (= (length curPts) (length adjustedPts)))
        (progn
          ;; Yalniz bu kaydin temas ettigi ucu deðiþtir; diðer ucu koru.
          (if (<= (distance (car adjustedPts) pt) 0.001)
            (progn
              (setq curPts (DT--replace-first-point curPts pt))
              (setq changed T)
            )
          )
          (if (<= (distance (g365_last adjustedPts) pt) 0.001)
            (progn
              (setq curPts (DT--replace-last-point curPts pt))
              (setq changed T)
            )
          )
          (if changed (DT--set-center-points center curPts))
        )
      )
    )
  )
  center
)

(defun DT--apply-tee-center-adjustments (newCenter teeRecords / rec pt oldCenter newAdjusted oldAdjusted)
  (foreach rec teeRecords
    (setq pt          (car rec)
          oldCenter   (cadr rec)
          newAdjusted (nth 2 rec)
          oldAdjusted (nth 3 rec))
    (if newAdjusted
      (DT--merge-center-contact-point newCenter newAdjusted pt)
    )
    (if (and oldCenter oldAdjusted)
      (DT--merge-center-contact-point oldCenter oldAdjusted pt)
    )
  )
)
(defun DT--dot-from-base (base u p)
  (g365_dot (- (car p) (car base)) (- (cadr p) (cadr base)) (car u) (cadr u))
)

(defun DT--line-distance (base u p / dx dy)
  (setq dx (- (car p) (car base))
        dy (- (cadr p) (cadr base)))
  (abs (- (* dx (cadr u)) (* dy (car u))))
)

(defun DT--pts-collinear-p (pts base u tol / ok p)
  (setq ok T)
  (foreach p pts
    (if (> (DT--line-distance base u p) tol)
      (setq ok nil)
    )
  )
  ok
)

(defun DT--straight-pts (pts / s)
  (setq s (DT--simplify-pts pts))
  (if (and (= (length s) 2) (> (distance (car s) (cadr s)) 0.001))
    s
  )
)

(defun DT--center-end-touch-p (p pts tol)
  (and pts
       (or
         (<= (distance p (car pts)) tol)
         (<= (distance p (g365_last pts)) tol)
       ))
)

(defun DT--pt-mid (a b)
  (list (/ (+ (car a) (car b)) 2.0) (/ (+ (cadr a) (cadr b)) 2.0) 0.0)
)

(defun DT--tray-center-seg (tray / pts p0 p1 p2 p3 l01 l12)
  ;; Egimli/dik tava kontrolu 3D POLYLINE olabilir. g365_get_pts bazi CAD
  ;; surumlerinde Z'yi dusurdugu icin cok kisa dik parcayi tava genisligiyle
  ;; karistiriyordu. Boyuna kenari gercek 3B mesafeyle belirle.
  (setq pts (DT--tray-corner-points-3d tray))
  (if (and pts (>= (length pts) 4))
    (progn
      (setq p0 (nth 0 pts)
            p1 (nth 1 pts)
            p2 (nth 2 pts)
            p3 (nth 3 pts)
            l01 (distance p0 p1)
            l12 (distance p1 p2))
      (if (>= l01 l12)
        (list (DT--pt-mid p0 p3) (DT--pt-mid p1 p2))
        (list (DT--pt-mid p0 p1) (DT--pt-mid p3 p2))
      )
    )
  )
)

(defun DT--tray-center-seg-on-line (tray base u / seg)
  (setq seg (DT--tray-center-seg tray))
  (if (and seg base u (DT--pts-collinear-p seg base u 20.0))
    seg
  )
)
(defun DT--nearest-seg-end (pt seg tol / a b da db)
  (if (and pt seg (= (length seg) 2))
    (progn
      (setq a (car seg)
            b (cadr seg)
            da (distance pt a)
            db (distance pt b))
      (cond
        ((and (<= da tol) (<= da db)) a)
        ((<= db tol) b)
        (T nil)
      )
    )
  )
)

(defun DT--deleted-fitting-end-gap-p (endPt oldStraight seg oldWidth tol / gapTol oldEnd segEnd gap)
  ;; Baglanti blocku elle silindiginde gorunen tava, eski centerline ucundan
  ;; biraz kisa kalabilir. Bu kisa ucu ayni dogrultuda devam icin baglanabilir say.
  (setq gapTol (+ (* 2.0 oldWidth) tol 2.0))
  (if (and endPt oldStraight seg)
    (progn
      (setq oldEnd (DT--nearest-seg-end endPt oldStraight gapTol))
      (if oldEnd
        (progn
          (setq segEnd (DT--nearest-seg-end oldEnd seg gapTol))
          (if segEnd
            (progn
              (setq gap (distance oldEnd segEnd))
              (and
                (<= gap gapTol)
                (> gap tol)
                (<= (distance endPt oldEnd) (+ gap tol))
                (<= (distance endPt segEnd) (+ gap tol))
              )
            )
          )
        )
      )
    )
  )
)

(defun DT--endpoint-away-dir (endPt base u)
  (if (<= (distance endPt base) 0.001)
    u
    (list (- (car u)) (- (cadr u)))
  )
)

(defun DT--seg-end-other (seg segEnd)
  (if (<= (distance segEnd (car seg)) (distance segEnd (cadr seg)))
    (cadr seg)
    (car seg)
  )
)

(defun DT--visible-seg-end-gap-contact-p (endPt base u seg oldWidth tol / gapTol segEnd other interior away gap)
  ;; T/+ gibi bir fitting silinince cut noktasi centerline ortasinda kalabilir.
  ;; Gorunen tava parcasinin ucundan disari dogru ayni dogrultuda ekleniyorsa birlestir.
  (setq gapTol (+ (* 2.0 oldWidth) tol 2.0))
  (if (and endPt base u seg)
    (progn
      (setq segEnd (DT--nearest-seg-end endPt seg gapTol))
      (if segEnd
        (progn
          (setq other    (DT--seg-end-other seg segEnd)
                interior (DT--seg-unit segEnd other)
                away     (DT--endpoint-away-dir endPt base u)
                gap      (distance endPt segEnd))
          (and
            (> gap tol)
            (<= gap gapTol)
            (< (g365_dot (car away) (cadr away) (car interior) (cadr interior)) -0.90)
          )
        )
      )
    )
  )
)

(defun DT--merge-end-contact-p (old endPt base u oldStraight seg oldWidth tol)
  (or
    (and
      (DT--center-end-touch-p endPt seg tol)
      (DT--center-visible-at-point-p old endPt oldWidth)
    )
    (DT--deleted-fitting-end-gap-p endPt oldStraight seg oldWidth tol)
    (DT--visible-seg-end-gap-contact-p endPt base u seg oldWidth tol)
  )
)

(defun DT--same-merge-candidate-p (a b)
  (and a b
       (eq (car a) (car b))
       (eq (nth 3 a) (nth 3 b)))
)

(defun DT--merge-candidate-used-p (old tray used / hit rec)
  (foreach rec used
    (if (and (eq old (car rec)) (eq tray (nth 3 rec)))
      (setq hit T)
    )
  )
  hit
)

(defun DT--delete-candidate-tray (cand / old tray)
  (setq old  (car cand)
        tray (nth 3 cand))
  (if (and tray (entget tray))
    (DT--delete-ents (list tray))
    (DT--delete-ents (DT--linked-trays old))
  )
  (if (not (DT--active-center-p old))
    (DT--safe-delete-ent old)
  )
)

(defun DT--remove-inactive-centers-from-list (centers / out c)
  (foreach c centers
    (if (and (DT--entity-alive-p c) (DT--active-center-p c))
      (setq out (append out (list c)))
    )
  )
  out
)
(defun DT--merge-bridge-candidate (endPt base u oldCenters width used / old oldPts oldStraight oldWidth tol hit tray seg)
  (foreach old oldCenters
    (if (and (null hit)
             (DT--entity-alive-p old)
             (DT--active-center-p old))
      (progn
        (setq oldPts      (g365_get_pts old)
              oldStraight (DT--straight-pts oldPts)
              oldWidth    (DT--center-width old width)
              tol         (+ (/ (max width oldWidth) 2.0) 1.0))
        (if (DT--same-width-p oldWidth width)
          (foreach tray (DT--linked-trays old)
            (if (and (null hit)
                     (DT--visible-tray-p tray)
                     (not (DT--merge-candidate-used-p old tray used)))
              (progn
                ;; Eski centerline kirikli olabilir; birlestirme kararini
                ;; komple centerline yerine gorunen duz tava parcasindan al.
                (setq seg (DT--tray-center-seg-on-line tray base u))
                (if (and seg
                         (DT--merge-end-contact-p old endPt base u oldStraight seg oldWidth tol))
                  (setq hit (list old seg oldWidth tray))
                )
              )
            )
          )
        )
      )
    )
  )
  hit
)
(defun DT--remove-centers-from-list (centers remove / out c)
  (foreach c centers
    (if (not (member c remove))
      (setq out (append out (list c)))
    )
  )
  out
)

(defun DT--merged-line-pts (allPts base u / minT maxT param p)
  (foreach p allPts
    (setq param (DT--dot-from-base base u p))
    (if (or (null minT) (< param minT)) (setq minT param))
    (if (or (null maxT) (> param maxT)) (setq maxT param))
  )
  (if (and minT maxT (> (- maxT minT) 0.001))
    (list (DT--pt+ base u minT) (DT--pt+ base u maxT))
  )
)
(defun DT--bridge-covers-cut-p (newStraight base u cut width / p gap a b s e c lo hi tol maxLen)
  (setq p (DT--cut-point cut))
  (if (and newStraight p)
    (progn
      (setq gap    (DT--cut-gap cut width)
            a      (DT--dot-from-base base u (car newStraight))
            b      (DT--dot-from-base base u (cadr newStraight))
            s      (min a b)
            e      (max a b)
            c      (DT--dot-from-base base u p)
            lo     (- c gap)
            hi     (+ c gap)
            tol    (+ (/ width 2.0) 2.0)
            maxLen (+ (* 2.0 gap) (* 4.0 width) 10.0))
      (and (<= (DT--line-distance base u p) tol)
           (<= s (+ lo tol))
           (>= e (- hi tol))
           (<= s (+ c tol))
           (>= e (- c tol))
           (<= (- e s) maxLen))
    )
  )
)

(defun DT--split-bridged-cuts (newStraight base u cuts width / kept removed cut)
  (foreach cut cuts
    (if (DT--bridge-covers-cut-p newStraight base u cut width)
      (setq removed (append removed (list cut)))
      (setq kept (append kept (list cut)))
    )
  )
  (list kept removed)
)

(defun DT--merge-internal-cut-bridge (newCenter newStraight oldCenters width base u / old oldPts oldStraight oldWidth tol cuts split kept removed mergedCuts cut)
  (foreach old oldCenters
    (if (and (null removed)
             (DT--entity-alive-p old)
             (DT--active-center-p old))
      (progn
        (setq oldPts      (g365_get_pts old)
              oldStraight (DT--straight-pts oldPts)
              oldWidth    (DT--center-width old width)
              tol         (+ (/ (max width oldWidth) 2.0) 1.0))
        (if (and oldStraight
                 (DT--same-width-p oldWidth width)
                 (DT--pts-collinear-p oldStraight base u tol)
                 (or
                   (DT--center-visible-at-point-p old (car newStraight) oldWidth)
                   (DT--center-visible-at-point-p old (cadr newStraight) oldWidth)))
          (progn
            (setq cuts (DT--plus-cuts old))
            (if cuts
              (progn
                (setq split   (DT--split-bridged-cuts newStraight base u cuts oldWidth)
                      kept    (car split)
                      removed (cadr split))
                (if removed
                  (progn
                    (setq mergedCuts (append (DT--plus-cuts newCenter) kept))
                    (DT--delete-ents (DT--linked-trays old))
                    (foreach cut removed
                      (DT--delete-existing-fittings-at (DT--cut-point cut) (DT--layer-fitting) (+ oldWidth 1.0))
                    )
                    (DT--safe-delete-ent old)
                    (DT--set-center-points newCenter oldStraight)
                    (DT--set-plus-cuts newCenter mergedCuts)
                    (setq oldCenters (DT--remove-centers-from-list oldCenters (list old)))
                  )
                )
              )
            )
          )
        )
      )
    )
  )
  (if removed
    (list oldStraight oldCenters 1)
  )
)
(defun DT--merge-one-sided-extension (newCenter newStraight oldCenters width base u c1 c2 / cand old oldStraight mergedPts oldLen mergedLen)
  (setq cand
    (cond
      ((and c1 (null c2)) c1)
      ((and c2 (null c1)) c2)
      (T nil)
    )
  )
  (if cand
    (progn
      (setq old         (car cand)
            oldStraight (cadr cand))
      (setq base (car oldStraight)
            u    (DT--seg-unit (car oldStraight) (cadr oldStraight)))
      (setq mergedPts
        (DT--merged-line-pts
          (append newStraight oldStraight)
          base
          u
        )
      )
      (if mergedPts
        (progn
          (setq oldLen    (distance (car oldStraight) (cadr oldStraight))
                mergedLen (distance (car mergedPts) (cadr mergedPts)))
          (if (> mergedLen (+ oldLen 0.001))
            (progn
              (DT--delete-candidate-tray cand)
              (DT--set-center-points newCenter mergedPts)
              (list mergedPts (DT--remove-inactive-centers-from-list oldCenters) 1)
            )
          )
        )
      )
    )
  )
)
(defun DT--line-end-near (pt line)
  (if (<= (distance pt (car line)) (distance pt (cadr line)))
    (car line)
    (cadr line)
  )
)

(defun DT--line-other-end (pt line)
  (if (<= (distance pt (car line)) (distance pt (cadr line)))
    (cadr line)
    (car line)
  )
)

(defun DT--drop-last-n (lst n / out i lim)
  (setq i 0
        lim (- (length lst) n))
  (while (< i lim)
    (setq out (append out (list (nth i lst))))
    (setq i (1+ i))
  )
  out
)

(defun DT--merge-bent-start-extension (newCenter pts oldCenters width / s a b base u cand oldSeg merged near other oldLen mergedLen dx dy rest newPts)
  (setq s (DT--simplify-pts pts))
  (if (and newCenter s (>= (length s) 3))
    (progn
      (setq a (car s)
            b (cadr s))
      (if (> (distance a b) 0.001)
        (progn
          (setq base a
                u    (DT--seg-unit a b)
                cand (DT--merge-bridge-candidate a base u oldCenters width nil))
          (if cand
            (progn
              (setq oldSeg (cadr cand)
                    merged (DT--merged-line-pts (append (list a b) oldSeg) (car oldSeg) (DT--seg-unit (car oldSeg) (cadr oldSeg))))
              (if merged
                (progn
                  (setq near      (DT--line-end-near b merged)
                        other     (DT--line-other-end b merged)
                        oldLen    (distance (car oldSeg) (cadr oldSeg))
                        mergedLen (distance (car merged) (cadr merged)))
                  (if (> mergedLen (+ oldLen 0.001))
                    (progn
                      (setq dx   (- (car near) (car b))
                            dy   (- (cadr near) (cadr b))
                            rest (DT--translate-pts (cddr s) dx dy)
                            newPts (append (list other near) rest))
                      (DT--delete-candidate-tray cand)
                      (DT--set-center-points newCenter newPts)
                      (list newPts (DT--remove-inactive-centers-from-list oldCenters) 1)
                    )
                  )
                )
              )
            )
          )
        )
      )
    )
  )
)

(defun DT--merge-bent-last-extension (newCenter pts oldCenters width / s n a b base u cand oldSeg merged near other oldLen mergedLen dx dy prefix newPts)
  (setq s (DT--simplify-pts pts))
  (if (and newCenter s (>= (length s) 3))
    (progn
      (setq n (length s)
            a (nth (- n 2) s)
            b (nth (- n 1) s))
      (if (> (distance a b) 0.001)
        (progn
          (setq base a
                u    (DT--seg-unit a b)
                cand (DT--merge-bridge-candidate b base u oldCenters width nil))
          (if cand
            (progn
              (setq oldSeg (cadr cand)
                    merged (DT--merged-line-pts (append (list a b) oldSeg) (car oldSeg) (DT--seg-unit (car oldSeg) (cadr oldSeg))))
              (if merged
                (progn
                  (setq near      (DT--line-end-near a merged)
                        other     (DT--line-other-end a merged)
                        oldLen    (distance (car oldSeg) (cadr oldSeg))
                        mergedLen (distance (car merged) (cadr merged)))
                  (if (> mergedLen (+ oldLen 0.001))
                    (progn
                      (setq dx     (- (car near) (car a))
                            dy     (- (cadr near) (cadr a))
                            prefix (DT--translate-pts (DT--drop-last-n s 2) dx dy)
                            newPts (append prefix (list near other)))
                      (DT--delete-candidate-tray cand)
                      (DT--set-center-points newCenter newPts)
                      (list newPts (DT--remove-inactive-centers-from-list oldCenters) 1)
                    )
                  )
                )
              )
            )
          )
        )
      )
    )
  )
)

(defun DT--merge-bent-end-extension (newCenter pts oldCenters width / res)
  (setq res (DT--merge-bent-start-extension newCenter pts oldCenters width))
  (if res
    res
    (DT--merge-bent-last-extension newCenter pts oldCenters width)
  )
)

(defun DT--merge-collinear-bridge (newCenter pts oldCenters width / newStraight base u c1 c2 old1 old2 mergedPts oneSideResult internalResult)
  (setq newStraight (DT--straight-pts pts))
  (if (and newCenter newStraight (= (length newStraight) 2))
    (progn
      (setq base (car newStraight)
            u    (DT--seg-unit (car newStraight) (cadr newStraight)))
      (setq c1 (DT--merge-bridge-candidate (car newStraight) base u oldCenters width nil))
      (setq c2 (DT--merge-bridge-candidate (cadr newStraight) base u oldCenters width (if c1 (list c1) nil)))
      (if (and c1 c2 (not (DT--same-merge-candidate-p c1 c2)))
        (progn
          (setq old1 (car c1)
                old2 (car c2))
          (setq base (caadr c1)
                u    (DT--seg-unit (caadr c1) (cadadr c1)))
          (setq mergedPts
            (DT--merged-line-pts
              (append newStraight (cadr c1) (cadr c2))
              base
              u
            )
          )
          (if mergedPts
            (progn
              (DT--delete-candidate-tray c1)
              (DT--delete-candidate-tray c2)
              (DT--set-center-points newCenter mergedPts)
              (list mergedPts (DT--remove-inactive-centers-from-list oldCenters) 2)
            )
          )
        )
        (progn
          (setq oneSideResult (DT--merge-one-sided-extension newCenter newStraight oldCenters width base u c1 c2))
          (if oneSideResult
            oneSideResult
            (progn
              (setq internalResult (DT--merge-internal-cut-bridge newCenter newStraight oldCenters width base u))
              (if internalResult internalResult)
            )
          )
        )
      )
    )
    (DT--merge-bent-end-extension newCenter pts oldCenters width)
  )
)
(defun DT--apply-junction-splits (newCenter fitResult width / plusRecords teeRecords flexRecords elbowRecords records rec pt oldCenter newGap oldGap centers center)
  (setq plusRecords  (nth 2 fitResult)
        teeRecords   (nth 3 fitResult)
        flexRecords  (nth 5 fitResult)
        elbowRecords (nth 7 fitResult)
        records      (append plusRecords teeRecords flexRecords elbowRecords))
  (if records
    (progn
      (DT--apply-tee-center-adjustments newCenter records)
      (setq centers (list newCenter))
      (foreach rec records
        (setq pt        (car rec)
              oldCenter (cadr rec)
              newGap    (nth 4 rec)
              oldGap    (nth 5 rec))
        (DT--add-plus-cut newCenter pt newGap)
        (if (and oldCenter (entget oldCenter) (DT--active-center-p oldCenter))
          (progn
            (DT--add-plus-cut oldCenter pt oldGap)
            (if (not (DT--center-in-list-p oldCenter centers))
              (setq centers (append centers (list oldCenter)))
            )
          )
        )
      )
      (foreach center centers
        (DT--rebuild-center-pieces center width (eq center newCenter))
      )
    )
  )
  (DT--linked-trays newCenter)
)
(defun DT--apply-plus-splits (newCenter fitResult width)
  (DT--apply-junction-splits newCenter fitResult width)
)

(defun DT--visible-tray-p (ent / ed)
  (and ent
       (DT--entity-alive-p ent)
       (setq ed (entget ent))
       (member (cdr (assoc 0 ed)) '("LWPOLYLINE" "POLYLINE"))
       (DT--tray-visible-layer-p (cdr (assoc 8 ed)))
       (DT--closed-p ent))
)
(defun DT--live-fitting-at-point-p
  (pt width / ent ed ip lay activeLayer fw tol d hit)
  (if (and pt (DT--layer-fitting))
    (progn
      (setq activeLayer (strcase (DT--layer-fitting)))
      (foreach ent (DT--fitting-inserts)
        (if (null hit)
          (progn
            (setq ed (entget ent)
                  ip  (if ed (cdr (assoc 10 ed)) nil)
                  lay (if ed (cdr (assoc 8 ed)) nil))
            (if (and ip
                     lay
                     (= (strcase lay) activeLayer)
                     (DT--same-active-elevation-p ent)
                     ;; Bu DT calismasinda az once uretilen 90 bloklari eski
                     ;; kavsak/fitting kaniti degildir; hayalet center kolunu canlandirmasin.
                     (not
                       (and (boundp '*DT_CURRENT_TURN_BLOCKS*)
                            (member ent *DT_CURRENT_TURN_BLOCKS*))))
              (progn
                (setq fw  (DT--fitting-insert-width ent width)
                      tol (+ (max 1.0 (/ fw 2.0)) 1.0)
                      d   (distance
                            (list (car pt) (cadr pt) 0.0)
                            (list (car ip) (cadr ip) 0.0)))
                (if (and
                      (<= d (+ (* fw 4.0) 1.0))
                      (or
                        (<= d tol)
                        (DT--point-in-fitting-box-p pt ent 0.5)))
                  (setq hit T))
              )
            )
          )
        )
      )
    )
  )
  hit
)

(defun DT--elevation-fitting-insert-p (ent / ed)
  (and ent
       (setq ed (entget ent '("DT_ELEVATION")))
       (= (cdr (assoc 0 ed)) "INSERT")
       (assoc -3 ed))
)

(defun DT--live-elevation-fitting-at-point-p
  (pt width / ent ed ip lay activeLayer fw tol d hit)
  ;; Gecis blocku eski veya yeni tavanin kotunda olabilir; XY kesimi iki tarafta da korur.
  (if (and pt (DT--layer-fitting))
    (progn
      (setq activeLayer (strcase (DT--layer-fitting)))
      (foreach ent (DT--fitting-inserts)
        (if (null hit)
          (progn
            (setq ed (entget ent)
                  ip  (if ed (cdr (assoc 10 ed)) nil)
                  lay (if ed (cdr (assoc 8 ed)) nil))
            (if (and ip
                     lay
                     (= (strcase lay) activeLayer)
                     (DT--elevation-fitting-insert-p ent))
              (progn
                (setq fw  (DT--fitting-insert-width ent width)
                      tol (+ (max 1.0 (/ fw 2.0)) 1.0)
                      d   (distance
                            (list (car pt) (cadr pt) 0.0)
                            (list (car ip) (cadr ip) 0.0)))
                (if (and
                      (<= d (+ (* fw 4.0) 1.0))
                      (or
                        (<= d tol)
                        (DT--point-in-fitting-box-p pt ent 0.5)))
                  (setq hit T))
              )
            )
          )
        )
      )
    )
  )
  hit
)

(defun DT--cleanup-stale-plus-cuts (center / cuts kept cut p w oldActive cutZ)
  (if (and center (entget center))
    (progn
      (setq cuts (DT--plus-cuts center)
            w    (DT--center-width center 10.0))
      (foreach cut cuts
        (setq p         (DT--cut-point cut)
              oldActive (DT--active-elevation)
              cutZ      (DT--center-elevation-at-point center p)
              *DT_ACTIVE_ELEVATION* cutZ)
        (if (or (DT--live-fitting-at-point-p p w)
                (DT--live-elevation-fitting-at-point-p p w))
          (setq kept (append kept (list cut)))
        )
        (setq *DT_ACTIVE_ELEVATION* oldActive)
      )
      (if (/= (length kept) (length cuts))
        (DT--set-plus-cuts center kept)
      )
    )
  )
  center
)
(defun DT--center-visible-at-point-p (center pt width / trays tray cp d w tol hit seg rec)
  ;; Eski centerline'in herhangi bir yerinde tava kalmasi yetmez.
  ;; Baglanti kararinda, tam baglanilacak noktada gorunur tava/fitting olmali.
  (if (and center pt (DT--entity-alive-p center))
    (progn
      (setq w (DT--center-width center width)
            tol (+ (/ w 2.0) 1.0)
            trays (DT--linked-trays center))
      (foreach tray trays
        (if (and (null hit) (DT--visible-tray-p tray))
          (progn
            (setq seg (DT--tray-center-seg tray)
                  rec (if seg (g365_closest_on_seg pt (car seg) (cadr seg)) nil)
                  cp  (if rec (car rec) nil))
            (if cp
              (progn
                (setq d (DT--distance-xy pt cp))
                (if (<= d tol) (setq hit T))
              )
            )
          )
        )
      )
      (if (and (null hit)
               (or (DT--live-fitting-at-point-p pt w)
                   (DT--live-elevation-fitting-at-point-p pt w)))
        (setq hit T)
      )
    )
  )
  hit
)
(defun DT--curve-total-length (ent / ep d)
  (setq ep (vl-catch-all-apply 'vlax-curve-getEndParam (list ent)))
  (if (vl-catch-all-error-p ep)
    0.0
    (progn
      (setq d (vl-catch-all-apply 'vlax-curve-getDistAtParam (list ent ep)))
      (if (or (vl-catch-all-error-p d) (not (numberp d))) 0.0 d)
    )
  )
)

(defun DT--legacy-center-tray (center / ss i tray total ratios ratio p cp d good found)
  (setq ss (ssget "_X" (list (cons 0 "LWPOLYLINE") (cons 8 (DT--visible-layer-filter)) (cons 70 1))))
  (setq total (DT--curve-total-length center))
  (setq ratios '(0.25 0.50 0.75))
  (if (and ss (> total 0.01))
    (progn
      (setq i 0)
      (while (and (< i (sslength ss)) (null found))
        (setq tray (ssname ss i) good 0)
        (foreach ratio ratios
          (setq p (vl-catch-all-apply 'vlax-curve-getPointAtDist (list center (* total ratio))))
          (if (not (vl-catch-all-error-p p))
            (progn
              (setq cp (vl-catch-all-apply 'vlax-curve-getClosestPointTo (list tray p)))
              (if (not (vl-catch-all-error-p cp))
                (progn
                  (setq d (distance p cp))
                  (if (and (>= d 3.5) (<= d 6.5)) (setq good (1+ good)))
                )
              )
            )
          )
        )
        (if (>= good 2) (setq found tray))
        (setq i (1+ i))
      )
    )
  )
  found
)

(defun DT--active-center-p (center / trays tray hit)
  (setq trays (DT--linked-trays center))
  (foreach tray trays
    (if (DT--visible-tray-p tray) (setq hit T))
  )
  ;; Silinmis tava parcalarini eski merkez hattan tekrar uretme.
  ;; Sadece XData ile canli tava polyline''ina bagli centerline aktif sayilir.
  (if hit T nil)
)

(defun DT--cleanup-stale-centers (/ ss i ent)
  (setq ss (ssget "_X" (list (cons 0 "LWPOLYLINE,POLYLINE") (cons 8 (DT--layer-center)))))
  (if ss
    (progn
      (setq i 0)
      (while (< i (sslength ss))
        (setq ent (ssname ss i))
        (if (and (DT--entity-alive-p ent)
                 (not (DT--active-center-p ent)))
          (DT--safe-delete-ent ent)
          (DT--cleanup-stale-plus-cuts ent)
        )
        (setq i (1+ i))
      )
    )
  )
  nil
)
(defun DT--dir-at-point (pts pt / i best bestD rec d)
  (setq i 0 best nil bestD 1e99)
  (while (< i (1- (length pts)))
    (setq rec (g365_closest_on_seg pt (nth i pts) (nth (1+ i) pts)))
    (setq d (nth 2 rec))
    (if (< d bestD)
      (setq bestD d best (DT--seg-unit (nth i pts) (nth (1+ i) pts)))
    )
    (setq i (1+ i))
  )
  best
)

(defun DT--away-from-end-dir (pts pt tol / firstPt lastPt n)
  (setq n (length pts) firstPt (car pts) lastPt (g365_last pts))
  (cond
    ((and (> n 1) (<= (distance pt firstPt) tol))
      (DT--seg-unit firstPt (nth 1 pts)))
    ((and (> n 1) (<= (distance pt lastPt) tol))
      (DT--seg-unit lastPt (nth (- n 2) pts)))
    (T (DT--dir-at-point pts pt))
  )
)
(defun DT--replace-first-point (pts p)
  (if pts (cons p (cdr pts)) pts)
)

(defun DT--replace-last-point (pts p / out i)
  (setq i 0)
  (while (< i (length pts))
    (if (= i (1- (length pts)))
      (setq out (append out (list p)))
      (setq out (append out (list (nth i pts))))
    )
    (setq i (1+ i))
  )
  out
)

(defun DT--near-end-contact (endPt hostPts tol / rec)
  (setq rec (g365_closest_on_poly endPt hostPts))
  (if (and rec (> (nth 3 rec) 0.001) (<= (nth 3 rec) tol)) rec nil)
)

(defun DT--hit-near-center-p (hits center pt tol / hit rec)
  (foreach rec hits
    (if (and (eq (cadr rec) center)
             (<= (distance (car rec) pt) tol))
      (setq hit T)
    )
  )
  hit
)

(defun DT--nearest-poly-end (pt pts tol / firstPt lastPt dFirst dLast)
  (if (and pt pts (> (length pts) 1))
    (progn
      (setq firstPt (car pts)
            lastPt (g365_last pts)
            dFirst (distance pt firstPt)
            dLast (distance pt lastPt))
      (cond
        ((and (<= dFirst tol) (<= dFirst dLast)) firstPt)
        ((<= dLast tol) lastPt)
        (T nil)
      )
    )
  )
)

(defun DT--snap-poly-ends-to-host-ends (pts hostPts tol / out cp)
  (setq out pts)
  (if (and out hostPts)
    (progn
      ;; Uc kenarinin hangi noktasina tiklanirsa tiklansin merkez ucunu kullan.
      (setq cp (DT--nearest-poly-end (car out) hostPts tol))
      (if cp (setq out (DT--replace-first-point out cp)))
      (setq cp (DT--nearest-poly-end (g365_last out) hostPts tol))
      (if cp (setq out (DT--replace-last-point out cp)))
    )
  )
  out
)

(defun DT--snap-poly-ends-to-point (pts pt tol / out)
  (setq out pts)
  (if (and out pt)
    (progn
      ;; If the intersection is only within tray-width reach of an end,
      ;; treat it as an end touch instead of a through crossing.
      (if (<= (distance (car out) pt) tol)
        (setq out (DT--replace-first-point out pt))
      )
      (if (<= (distance (g365_last out) pt) tol)
        (setq out (DT--replace-last-point out pt))
      )
    )
  )
  out
)

(defun DT--pts-from-arms (pt arms dist / pts arm)
  (if arms
    (progn
      (setq pts (list (list (car pt) (cadr pt) 0.0)))
      (foreach arm arms
        (setq pts (append pts (list (DT--pt+ pt arm dist) (list (car pt) (cadr pt) 0.0))))
      )
      pts
    )
  )
)

(defun DT--visible-end-adjusted-pts (center pt width / trays tray seg segEnd other tol dir arms)
  ;; Baglanti/fitting silinmis olsa bile eski centerline arkada kalabilir.
  ;; Kavsak hesabinda centerline'i degil, o noktaya gelen CANLI tava uclarini kol say.
  (setq tol (+ (* 2.0 width) (/ width 2.0) 2.0))
  (foreach tray (DT--linked-trays center)
    (if (DT--visible-tray-p tray)
      (progn
        (setq seg (DT--tray-center-seg tray))
        (if (and seg (> (distance (car seg) (cadr seg)) 0.001))
          (progn
            (setq segEnd (DT--nearest-seg-end pt seg tol))
            (if segEnd
              (progn
                (setq other (DT--seg-end-other seg segEnd)
                      dir   (DT--seg-unit segEnd other))
                (if (<= (DT--line-distance segEnd dir pt) (+ (/ width 2.0) 1.0))
                  (setq arms (DT--add-ray-unique (DT--vec-from-to (list (car pt) (cadr pt) 0.0) other) arms))
                )
              )
            )
          )
        )
      )
    )
  )
  (DT--pts-from-arms pt arms width)
)

(defun DT--old-arm-matches-new-p (oldArm newArms mode / hit newArm)
  (foreach newArm newArms
    (cond
      ((and (= mode 'OPPOSITE) (DT--opposite-p oldArm newArm)) (setq hit T))
      ((and (= mode 'PERP) (DT--perpendicular-p oldArm newArm)) (setq hit T))
    )
  )
  hit
)

(defun DT--filter-deleted-fitting-old-arms (pt oldArms newArms width / opp perp arm keep)
  ;; Canli baglanti blocku yoksa, eski silinmis fitting'in butun kollarini
  ;; T hesabina sokma. Yeni cizimin baglandigi tek eski kolu kullan.
  (if (and pt
           oldArms
           newArms
           (> (length oldArms) 1)
           ;; Iki zit canli kol, parcalara bolunmus olsa da tek ve
           ;; kesintisiz ana tava eksenidir. Yeni dal bunu T yapmalidir.
           (not (DT--straight-axis oldArms))
           (not (DT--live-fitting-at-point-p pt width)))
    (progn
      (foreach arm oldArms
        (if (DT--old-arm-matches-new-p arm newArms 'OPPOSITE)
          (setq opp (DT--add-ray-unique arm opp))
        )
        (if (DT--old-arm-matches-new-p arm newArms 'PERP)
          (setq perp (DT--add-ray-unique arm perp))
        )
      )
      (setq keep
        (cond
          (opp (list (car opp)))
          (perp (list (car perp)))
          (T (list (car oldArms)))
        )
      )
      keep
    )
    oldArms
  )
)

(defun DT--collect-cross-hits (newPts oldEnts width / hits old oldPts oldWidth workNewPts i j a b c d ip tolOld tolNew rec cp adjustedNew adjustedOld pStart pEnd oStart oEnd u v endRec visibleOldPts)
  (foreach old oldEnts
    (if (DT--active-center-p old)
      (progn
        (setq oldPts (g365_get_pts old))
        (setq oldWidth (DT--center-width old width))
        (setq tolOld (+ (/ oldWidth 2.0) 0.5))
        (setq tolNew (+ (/ width 2.0) 0.5))
        (setq workNewPts (DT--snap-poly-ends-to-host-ends newPts oldPts tolOld))
        (if (and oldPts (> (length oldPts) 1))
          (progn
            ;; Tam merkez hat kesiÅŸmeleri.
            (setq i 0)
            (while (< i (1- (length workNewPts)))
              (setq a (nth i workNewPts) b (nth (1+ i) workNewPts) j 0)
              (while (< j (1- (length oldPts)))
                (setq c (nth j oldPts) d (nth (1+ j) oldPts))
                (setq ip (inters a b c d T))
                (if ip                   (progn                     (setq cp (list (car ip) (cadr ip) 0.0))                     (setq visibleOldPts (DT--visible-end-adjusted-pts old cp oldWidth))                     (if (and (or visibleOldPts (DT--center-visible-at-point-p old cp oldWidth))                              (not (DT--point-known-p ip (mapcar 'car hits) 0.0001)))                       (progn                         (setq adjustedNew (DT--snap-poly-ends-to-point workNewPts cp tolNew)                               adjustedOld (if visibleOldPts visibleOldPts (DT--snap-poly-ends-to-point oldPts cp tolOld)))                         (setq hits (append hits (list (list cp old adjustedOld adjustedNew))))                       )                     )                   )                 )
                (setq j (1+ j))
              )
              (setq i (1+ i))
            )

            ;; Yeni DT ucu eski tavanin gorunen kenarina degiyorsa merkeze projekte et.
            (setq pStart (car workNewPts) pEnd (g365_last workNewPts))
            (foreach endRec (list (list pStart 0) (list pEnd 1))
              (setq rec (DT--near-end-contact (car endRec) oldPts tolOld))
              (if (and rec (DT--center-visible-at-point-p old (car rec) oldWidth))
                (progn
                  (setq cp (car rec))
                  (setq adjustedNew
                    (if (= (cadr endRec) 0)
                      (DT--replace-first-point workNewPts cp)
                      (DT--replace-last-point workNewPts cp)
                    )
                  )
                  (setq u (DT--away-from-end-dir adjustedNew cp 0.001))
                  (setq v (DT--dir-at-point oldPts cp))
                  (if (not (DT--point-known-p cp (mapcar 'car hits) 0.0001))
                    (setq hits (append hits (list (list cp old (if (DT--visible-end-adjusted-pts old cp oldWidth) (DT--visible-end-adjusted-pts old cp oldWidth) oldPts) adjustedNew))))
                  )
                )
              )
            )

            ;; Eski DT ucu yeni tavanin gorunen kenarina degiyorsa ayni islemi ters yonde yap.
            (setq oStart (car oldPts) oEnd (g365_last oldPts))
            (foreach endRec (list (list oStart 0) (list oEnd 1))
              (setq rec (DT--near-end-contact (car endRec) workNewPts tolNew))
              (if (and rec (DT--center-visible-at-point-p old (car rec) oldWidth))
                (progn
                  (setq cp (car rec))
                  (setq adjustedOld
                    (if (= (cadr endRec) 0)
                      (DT--replace-first-point oldPts cp)
                      (DT--replace-last-point oldPts cp)
                    )
                  )
                  (setq u (DT--away-from-end-dir adjustedOld cp 0.001))
                  (setq v (DT--dir-at-point workNewPts cp))
                  ;; Ayni tava ucunun kenar/kose temasi daha once merkezden bulunduysa
                  ;; ikinci bir baglanti sayma ve eski merkez hattini koseye tasima.
                  (if (not (DT--hit-near-center-p hits old cp (max tolOld tolNew)))
                    (setq hits (append hits (list (list cp old (if (DT--visible-end-adjusted-pts old cp oldWidth) (DT--visible-end-adjusted-pts old cp oldWidth) adjustedOld) workNewPts))))
                  )
                )
              )
            )
          )
        )
      )
    )
  )
  hits
)
(defun DT--collect-self-hits (pts / hits n i j a b c d ip)
  (setq n (length pts) i 0)
  (while (< i (1- n))
    (setq a (nth i pts) b (nth (1+ i) pts) j (+ i 2))
    (while (< j (1- n))
      (setq c (nth j pts) d (nth (1+ j) pts))
      (setq ip (inters a b c d T))
      (if (and ip (not (DT--point-known-p ip (mapcar 'car hits) 0.0001)))
        (setq hits (append hits (list (list (list (car ip) (cadr ip) 0.0) i j))))
      )
      (setq j (1+ j))
    )
    (setq i (1+ i))
  )
  hits
)

(defun DT--point-angle-around (base p)
  (atan (- (cadr p) (cadr base)) (- (car p) (car base)))
)

(defun DT--sort-points-around (pts base)
  (vl-sort pts
    (function
      (lambda (a b)
        (< (DT--point-angle-around base a) (DT--point-angle-around base b))
      )
    )
  )
)

(defun DT--unique-points (pts tol / out p)
  (foreach p pts
    (if (not (DT--point-known-p p out tol))
      (setq out (append out (list p)))
    )
  )
  out
)

(defun DT--combine-arms (a b / out u)
  (foreach u (append a b)
    (setq out (DT--add-ray-unique u out))
  )
  out
)

(defun DT--all-collinear-p (arms / base ok u)
  (setq ok T)
  (if arms
    (progn
      (setq base (car arms))
      (foreach u (cdr arms)
        (if (< (abs (g365_dot (car base) (cadr base) (car u) (cadr u))) 0.995)
          (setq ok nil)
        )
      )
    )
  )
  ok
)

(defun DT--flexible-arms-p (arms / n)
  (setq n (length arms))
  (and (>= n 2)
       (<= n 4)
       (not (DT--all-collinear-p arms))
       (not (and (= n 2) (DT--perpendicular-p (car arms) (cadr arms))))
  )
)

(defun DT--same-width-p (a b)
  (and (numberp a) (numberp b) (<= (abs (- a b)) 0.0001))
)

(defun DT--add-arm-spec (ray width specs / out rec found)
  (if (and ray (numberp width) (> width 0.0))
    (progn
      (foreach rec specs
        (if (DT--same-ray-p ray (car rec))
          (progn
            (setq out (append out (list (list (car rec) (max width (cadr rec))))))
            (setq found T)
          )
          (setq out (append out (list rec)))
        )
      )
      (if (not found)
        (setq out (append out (list (list ray width))))
      )
    )
    (setq out specs)
  )
  out
)

(defun DT--combine-arm-specs (newArms newWidth oldArms oldWidth / specs u)
  (foreach u newArms
    (setq specs (DT--add-arm-spec u newWidth specs))
  )
  (foreach u oldArms
    (setq specs (DT--add-arm-spec u oldWidth specs))
  )
  specs
)

(defun DT--arm-spec-rays (specs / out rec)
  (foreach rec specs
    (setq out (append out (list (car rec))))
  )
  out
)

(defun DT--flex-kind (specs / sig rec i j a b dotv)
  (setq sig "esnek"
        i 0)
  (while (< i (length specs))
    (setq j (1+ i))
    (while (< j (length specs))
      (setq a (car (nth i specs))
            b (car (nth j specs))
            dotv (fix (* 1000.0 (g365_dot (car a) (cadr a) (car b) (cadr b)))))
      (setq sig (strcat sig "_" (itoa dotv)))
      (setq j (1+ j))
    )
    (setq i (1+ i))
  )
  sig
)

(defun DT--center-info-at-point (center pt width tol ptsOverride / pts arms w visiblePts)
  (if (and center
           (entget center)
           (or ptsOverride (DT--center-visible-at-point-p center pt width)))
    (progn
      (setq w (DT--center-width center width))
      (setq pts
        (cond
          (ptsOverride ptsOverride)
          ((setq visiblePts (DT--visible-end-adjusted-pts center pt w)) visiblePts)
          (T (g365_get_pts center))
        )
      )
      (setq arms (if pts (DT--arms-at-point pts pt tol) nil))
      (if arms
        (list center pts w arms)
      )
    )
  )
)
(defun DT--junction-old-infos (pt oldEnts seedCenter seedPts width tol newArms / infos center info arms filtered visibleEnd deletedEndSeen singleOld)
  (foreach center oldEnts
    (setq info
      (DT--center-info-at-point
        center
        pt
        width
        tol
        (if (eq center seedCenter) seedPts nil)
      )
    )
    (if info
      (progn
        (setq arms (nth 3 info))
        (setq visibleEnd (DT--visible-end-adjusted-pts center pt (nth 2 info)))
        (setq filtered
          (if visibleEnd
            (DT--filter-deleted-fitting-old-arms pt arms newArms (nth 2 info))
            arms
          )
        )
        (if visibleEnd (setq deletedEndSeen T))
        (if (/= (length filtered) (length arms))
          (progn
            (setq info (list (car info) (DT--pts-from-arms pt filtered (nth 2 info)) (nth 2 info) filtered))
          )
        )
        (setq infos (append infos (list info)))
      )
    )
  )
  (setq singleOld T)
  (foreach info infos
    (if (/= (length (nth 3 info)) 1)
      (setq singleOld nil)
    )
  )
  (if (and deletedEndSeen
           singleOld
           (= (length newArms) 2)
           (or
             (DT--opposite-p (car newArms) (cadr newArms))
             (DT--perpendicular-p (car newArms) (cadr newArms))
           )
           (not (DT--live-fitting-at-point-p pt width)))
    nil
    infos
  )
)

(defun DT--infos-arms (infos / arms info u)
  (foreach info infos
    (foreach u (nth 3 info)
      (setq arms (DT--add-ray-unique u arms))
    )
  )
  arms
)

(defun DT--infos-arm-specs (newArms newWidth infos / specs info u)
  (foreach u newArms
    (setq specs (DT--add-arm-spec u newWidth specs))
  )
  (foreach info infos
    (foreach u (nth 3 info)
      (setq specs (DT--add-arm-spec u (nth 2 info) specs))
    )
  )
  specs
)

(defun DT--forced-through-tee-specs
  (pt adjustedNewPts oldCenter oldPts newWidth
    / newArms oldWidth visibleOldPts visibleOldArms
      rawOldPts rawOldArms physicalOldArms axis branch)
  ;; Fiziksel olarak kesintisiz iki zit ana kol ve bunlara dik tek yeni kol
  ;; varsa, eski fitting/cache durumundan bagimsiz olarak bu kavsak T'dir.
  (setq newArms (DT--arms-at-point adjustedNewPts pt 0.001)
        oldWidth (if oldCenter (DT--center-width oldCenter newWidth) newWidth)
        visibleOldPts
          (if oldCenter
            (DT--visible-end-adjusted-pts oldCenter pt oldWidth)))
  (setq visibleOldArms
          (if visibleOldPts
            (DT--arms-at-point visibleOldPts pt 0.001))
        rawOldPts
          (if oldCenter
            (g365_get_pts oldCenter)
            oldPts)
        rawOldArms
          (if rawOldPts
            (DT--arms-at-point rawOldPts pt 0.001))
        physicalOldArms
          (cond
            ((DT--straight-axis visibleOldArms) visibleOldArms)
            ((DT--straight-axis rawOldArms) rawOldArms)
            (visibleOldArms visibleOldArms)
            (T rawOldArms)))
  (setq axis (DT--straight-axis physicalOldArms)
        branch (if (= (length newArms) 1) (car newArms)))
  (if (and axis branch (DT--perpendicular-p axis branch))
    (DT--combine-arm-specs newArms newWidth physicalOldArms oldWidth))
)


(defun DT--endpoint-continuation-p (pt pts oldArms / tol dir arm hit)
  ;; Yeni cizim eski tavanin ucundan ayni dogrultuda devam ediyorsa
  ;; baslangic noktasini T baglantisi sayma.
  (setq tol 0.001)
  (if (and pt pts oldArms (> (length pts) 1))
    (progn
      (cond
        ((<= (distance pt (car pts)) tol)
          (setq dir (DT--seg-unit (car pts) (cadr pts))))
        ((<= (distance pt (g365_last pts)) tol)
          (setq dir (DT--seg-unit (g365_last pts) (nth (- (length pts) 2) pts))))
      )
      (if dir
        (foreach arm oldArms
          (if (> (abs (g365_dot (car dir) (cadr dir) (car arm) (cadr arm))) 0.995)
            (setq hit T)
          )
        )
      )
    )
  )
  hit
)
(defun DT--internal-90-corner-p (pt pts tol / i prev cur next hit)
  (if (and pt pts (> (length pts) 2))
    (progn
      (setq i 1)
      (while (and (< i (1- (length pts))) (not hit))
        (setq prev (nth (1- i) pts)
              cur  (nth i pts)
              next (nth (1+ i) pts))
        (if (and (<= (distance pt cur) tol)
                 (> (distance prev cur) 0.001)
                 (> (distance cur next) 0.001)
                 (DT--perpendicular-p (DT--seg-unit cur prev) (DT--seg-unit cur next)))
          (setq hit T)
        )
        (setq i (1+ i))
      )
    )
  )
  hit
)
(defun DT--internal-corner-continuation-p (pt pts oldArms / newArms oldArm u ok hit)
  ;; Yeni polyline'in kendi 90 kosesinde eski taraf sadece ayni dogrultuda
  ;; devam ediyorsa bunu kavsak sayma; normal 90 donus blogu kalsin.
  (setq newArms (DT--arms-at-point pts pt 0.001))
  (if (and pt
           pts
           oldArms
           (= (length newArms) 2)
           (DT--perpendicular-p (car newArms) (cadr newArms)))
    (progn
      (setq ok T)
      (foreach oldArm oldArms
        (setq hit nil)
        (foreach u newArms
          (if (> (abs (g365_dot (car oldArm) (cadr oldArm) (car u) (cadr u))) 0.995)
            (setq hit T)
          )
        )
        (if (not hit) (setq ok nil))
      )
    )
  )
  ok
)
(defun DT--specs-max-width (specs fallback / maxWidth rec)
  (setq maxWidth fallback)
  (foreach rec specs
    (if (and (numberp (cadr rec)) (> (cadr rec) maxWidth))
      (setq maxWidth (cadr rec))
    )
  )
  maxWidth
)

(defun DT--t-axis-branch (arms / axis branch u)
  (if (= (length arms) 3)
    (progn
      (foreach u arms
        (if (and (null axis) (DT--opposite-exists-p u arms))
          (setq axis u)
        )
      )
      (if axis
        (foreach u arms
          (if (and (null branch)
                   (not (DT--same-ray-p u axis))
                   (not (DT--opposite-p u axis)))
            (setq branch u)
          )
        )
      )
      (if (and axis branch (DT--perpendicular-p axis branch))
        (list axis branch)
      )
    )
  )
)

(defun DT--two-arm-elbow (arms)
  (if (and (= (length arms) 2) (DT--perpendicular-p (car arms) (cadr arms)))
    (list (car arms) (cadr arms))
  )
)

(defun DT--junction-records (pt infos adjustedNewPts fitWidth / records info)
  (if infos
    (foreach info infos
      (setq records
        (append records
          (list (list pt (car info) adjustedNewPts (cadr info) fitWidth fitWidth))
        )
      )
    )
    (setq records (list (list pt nil adjustedNewPts nil fitWidth nil)))
  )
  records
)

(defun DT--draw-updated-junction-fitting (pt arms specs fitWidth / axes tb elbow)
  (cond
    ((setq axes (DT--four-way-axes arms))
      (DT--delete-existing-fittings-at pt (DT--layer-fitting) (+ fitWidth 1.0))
      (DT--draw-plus-fitting pt (car axes) (cadr axes) fitWidth (DT--layer-fitting))
      'PLUS)
    ((setq tb (DT--t-axis-branch arms))
      (DT--delete-existing-fittings-at pt (DT--layer-fitting) (+ fitWidth 1.0))
      (DT--draw-t-fitting pt (car tb) (cadr tb) fitWidth (DT--layer-fitting))
      'TEE)
    ((setq elbow (DT--two-arm-elbow arms))
      (DT--delete-existing-fittings-at pt (DT--layer-fitting) (+ fitWidth 1.0))
      (DT--draw-end-elbow-fitting pt (car elbow) (cadr elbow) fitWidth (DT--layer-fitting))
      'ELBOW)
    ((DT--flexible-arms-p arms)
      (DT--delete-existing-fittings-at pt (DT--layer-fitting) (+ fitWidth 1.0))
      (DT--draw-flex-fitting pt specs (DT--layer-fitting))
      'FLEX)
    (T nil)
  )
)
(defun DT--draw-variable-fitting (kind pt specs lay / corners ports spec u width maxWidth h n q outline ref second ang yscale)
  (setq maxWidth 0.0)
  (foreach spec specs
    (setq u (car spec)
          width (cadr spec)
          maxWidth (max maxWidth width)
          h (/ width 2.0)
          n (DT--perp u)
          q (DT--pt+ pt u width))
    (setq ports (append ports (list q)))
    (setq corners
      (append corners
        (list
          (DT--pt+ q n h)
          (DT--pt+ q n (- h))
        )
      )
    )
  )
  (setq corners (DT--unique-points corners 0.0001))
  (setq outline (DT--sort-points-around corners pt))
  (setq ref (caar specs)
        second (if (> (length specs) 1) (car (nth 1 specs)) (DT--perp ref))
        ang (DT--vec-angle ref)
        yscale (DT--mirror-for ref second))
  (if (>= (length outline) 3)
    (DT--make-fitting-block kind maxWidth pt (list (list outline T nil ports)) ang yscale)
  )
)

(defun DT--draw-flex-fitting (pt specs lay)
  (DT--draw-variable-fitting (DT--flex-kind specs) pt specs lay)
)

(defun DT--mark-elevation-transition (ins fromZ toZ / app ed payload)
  (setq app "DT_ELEVATION")
  (if (not (tblsearch "APPID" app)) (regapp app))
  (if (and ins (entget ins))
    (progn
      (setq payload
        (list app
          (cons 1000 "ELEVATION")
          (cons 1040 (if (numberp fromZ) fromZ 0.0))
          (cons 1040 (if (numberp toZ) toZ 0.0))))
      (setq ed (entget ins '("*")))
      (setq ed (DT--xdata-set-app ed app payload))
      (entmod ed)
      (entupd ins)
    )
  )
  (DT--cache-fitting-insert ins)
  ins
)

(defun DT--elevation-fitting-kind (newArm oldArm newWidth oldWidth / dotv)
  (setq dotv
    (if (and newArm oldArm)
      (fix (* 1000.0 (g365_dot (car newArm) (cadr newArm) (car oldArm) (cadr oldArm))))
      0))
  (strcat "ELEVATION_"
          (DT--width-name newWidth) "_"
          (DT--width-name oldWidth) "_"
          (itoa dotv))
)

(defun DT--draw-elevation-fitting (rec newPts width / pt oldPts oldWidth oldZ pairedZ newArm oldArm specs kind maxWidth oldActiveElevation ins)
  (setq pt       (car rec)
        oldPts   (nth 2 rec)
        oldWidth (nth 3 rec)
        oldZ     (nth 4 rec)
        pairedZ  (nth 6 rec)
        newArm   (DT--away-from-end-dir newPts pt 0.001)
        oldArm   (DT--away-from-end-dir oldPts pt 0.001))
  (if (and pt newArm oldArm)
    (progn
      (setq specs (DT--add-arm-spec newArm width specs))
      (setq specs (DT--add-arm-spec oldArm oldWidth specs))
      ;; Ust uste fakat farkli kotlu tavada da iki kollu bir gecis govdesi gerekir.
      (if (< (length specs) 2)
        (setq specs
          (DT--add-arm-spec
            (list (- (car newArm)) (- (cadr newArm)))
            oldWidth
            specs))
      )
      (setq kind (DT--elevation-fitting-kind newArm oldArm width oldWidth)
            maxWidth (max width oldWidth)
            oldActiveElevation (DT--active-elevation)
            *DT_ACTIVE_ELEVATION* oldZ)
      (DT--delete-existing-fittings-at pt (DT--layer-fitting) (+ maxWidth 1.0))
      (setq ins (DT--draw-variable-fitting kind pt specs (DT--layer-fitting)))
      (setq *DT_ACTIVE_ELEVATION* oldActiveElevation)
      (if ins (DT--mark-elevation-transition ins oldZ pairedZ))
    )
  )
  ins
)

(defun DT--transition-center-specs (pt centers oldZ fallbackWidth / center pts centerZ centerWidth arms arm specs used oldActive)
  (foreach center centers
    (if (and center (entget center) (DT--active-center-p center))
      (progn
        (setq pts         (g365_get_pts center)
              centerZ     (DT--center-elevation-at-point center pt)
              centerWidth (DT--center-width center fallbackWidth)
              oldActive   (DT--active-elevation)
              *DT_ACTIVE_ELEVATION* oldZ)
        (if (and pts
                 (equal centerZ oldZ 0.000001)
                 (DT--center-visible-at-point-p center pt centerWidth))
          (progn
            (setq arms (DT--arms-at-point pts pt 0.001))
            (foreach arm arms
              (setq specs (DT--add-arm-spec arm centerWidth specs))
            )
            (if arms (setq used (DT--add-ent-unique center used)))
          )
        )
        (setq *DT_ACTIVE_ELEVATION* oldActive)
      )
    )
  )
  (list specs used)
)

(defun DT--draw-transition-normal-fitting (rec newPts width centers / pt oldZ newArm collected specs used fitWidth kind oldActive)
  (setq pt      (car rec)
        oldZ    (nth 4 rec)
        newArm  (DT--away-from-end-dir newPts pt 0.001)
        collected (DT--transition-center-specs pt centers oldZ width)
        specs   (car collected)
        used    (cadr collected))
  (if newArm (setq specs (DT--add-arm-spec newArm width specs)))
  (setq fitWidth (DT--specs-max-width specs width))
  (if (and newArm (> (length specs) 1))
    (progn
      (setq oldActive (DT--active-elevation)
            *DT_ACTIVE_ELEVATION* oldZ
            kind
              (DT--draw-updated-junction-fitting
                pt
                (DT--arm-spec-rays specs)
                specs
                fitWidth)
            *DT_ACTIVE_ELEVATION* oldActive)
    )
  )
  (list kind fitWidth used)
)

(defun DT--center-slope-along-dir (center pt dir span / sample p1 p2 z1 z2)
  (setq sample (max 0.01 (min 1.0 (/ (max span 0.1) 10.0)))
        p1     (DT--pt+ pt dir sample)
        p2     (DT--pt+ pt dir (- sample))
        z1     (DT--center-elevation-at-point center p1)
        z2     (DT--center-elevation-at-point center p2))
  (/ (- z1 z2) (* 2.0 sample))
)

(defun DT--tangent-rise (run slope)
  (if (and (numberp run) (numberp slope))
    (/ (* run slope) (+ (sqrt (+ 1.0 (* slope slope))) 1.0))
    0.0
  )
)

(defun DT--solve-tangent-slope (delta middleRun transitionRun / sign target lo hi mid value i)
  (if (< (abs delta) 1e-9)
    0.0
    (progn
      (setq sign   (if (< delta 0.0) -1.0 1.0)
            target (abs delta)
            lo     0.0
            hi     (max 1.0 (/ target (max middleRun 0.001))))
      (while (< (+ (* hi middleRun)
                   (DT--tangent-rise transitionRun hi))
                target)
        (setq hi (* hi 2.0))
      )
      (setq i 0)
      (while (< i 60)
        (setq mid   (/ (+ lo hi) 2.0)
              value (+ (* mid middleRun)
                       (DT--tangent-rise transitionRun mid)))
        (if (< value target) (setq lo mid) (setq hi mid))
        (setq i (1+ i))
      )
      (* sign (/ (+ lo hi) 2.0))
    )
  )
)

(defun DT--center-profile-middle-slope (center / pts elevations profile total usable startLineZ endLineZ)
  (setq pts        (g365_get_pts center)
        elevations (DT--center-end-elevations center)
        profile     (DT--center-elevation-profile center)
        total       (DT--route-total-length pts)
        usable      (- total (car profile) (cadr profile))
        startLineZ  (if (numberp (nth 2 profile)) (nth 2 profile) (car elevations))
        endLineZ    (if (numberp (nth 3 profile)) (nth 3 profile) (cadr elevations)))
  (if (> usable 0.000001)
    (/ (- endLineZ startLineZ) usable)
    0.0
  )
)

(defun DT--draw-inline-elevation-fitting
  (rec newCenter newPts width normalGap baseDistance spanOverride
    / pt oldWidth oldZ pairedZ newArm reverseArm maxWidth fitSpan
      useBase shiftDistance shiftPt oldPort newPort kind oldPortZ
      newPortZ insertZ slope oldActive ins)
  (setq pt       (car rec)
        oldWidth (nth 3 rec)
        oldZ     (nth 4 rec)
        pairedZ  (nth 6 rec)
        newArm   (DT--away-from-end-dir newPts pt 0.001)
        maxWidth (max width oldWidth))
  (if newArm
    (progn
      (setq reverseArm   (list (- (car newArm)) (- (cadr newArm)))
            fitSpan      (if (and (numberp spanOverride) (> spanOverride 0.001))
                           spanOverride
                           maxWidth)
            useBase      (if (and (numberp baseDistance) (>= baseDistance 0.0))
                           baseDistance
                           (if (and (numberp normalGap) (> normalGap 0.0))
                             normalGap
                             0.0))
            shiftDistance (+ useBase fitSpan)
            shiftPt      (DT--pt+ pt newArm shiftDistance)
            oldPort      (DT--pt+ shiftPt newArm (- fitSpan))
            newPort      (DT--pt+ shiftPt newArm fitSpan)
            kind         (DT--elevation-fitting-kind newArm reverseArm width oldWidth)
            oldPortZ     (DT--center-elevation-at-point newCenter oldPort)
            newPortZ     (DT--center-elevation-at-point newCenter newPort)
            insertZ      (/ (+ oldPortZ newPortZ) 2.0)
            slope        (DT--center-profile-middle-slope newCenter)
            slope        (if (= (nth 5 rec) 0) slope (- slope))
            oldActive    (DT--active-elevation)
            *DT_ACTIVE_ELEVATION* insertZ)
      (DT--delete-existing-fittings-at shiftPt (DT--layer-fitting) 0.01)
      (setq ins
        (DT--make-elevation-fitting-block-span
          kind width oldWidth shiftPt newArm slope fitSpan))
      (setq *DT_ACTIVE_ELEVATION* oldActive)
      (if ins (DT--mark-elevation-transition ins oldZ pairedZ))
    )
  )
  (list ins shiftPt fitSpan)
)

(defun DT--apply-elevation-transitions
  (newCenter contacts width allCenters
    / rec pt oldCenter oldWidth oldCenters blocks ins count newPieces
      normalResult normalKind normalGap effectiveGap span used center
      elevationResult shiftPt elevationGap newPts transitionRecords
      transitionRecord startBase endBase startSpan endSpan total
      elevations startZ endZ delta provisionalSlope arcP startRun
      endRun middleRun middleSlope startTrim endTrim startLineZ
      endLineZ initialStartBase initialEndBase routeAvailable verticalP
      verticalRun naturalStartRun naturalEndRun naturalRun blockRunBudget
      runWeight extraBase startBlockSpan endBlockSpan baseOverride
      spanOverride)
  (setq newPts (g365_get_pts newCenter))
  (foreach rec contacts
    (setq pt        (car rec)
          oldCenter (cadr rec)
          oldWidth  (nth 3 rec)
          normalResult (DT--draw-transition-normal-fitting rec newPts width allCenters)
          normalKind   (car normalResult)
          normalGap    (cadr normalResult)
          used         (caddr normalResult)
          effectiveGap (if normalKind normalGap 0.0)
          span          (max width oldWidth))
    (setq transitionRecords
      (append transitionRecords
        (list (list rec normalKind normalGap used effectiveGap span))))
    (if (= (nth 5 rec) 0)
      (setq startBase effectiveGap startSpan span)
      (setq endBase effectiveGap endSpan span))
    (if normalKind
      (progn
        (DT--add-plus-cut newCenter pt normalGap)
        (foreach center used
          (DT--add-plus-cut center pt normalGap)
          (if (not (DT--center-in-list-p center oldCenters))
            (setq oldCenters (append oldCenters (list center)))
          )
        )
      )
    )
  )
  (setq initialStartBase (if (numberp startBase) startBase 0.0)
        initialEndBase   (if (numberp endBase) endBase 0.0)
        startBase initialStartBase
        endBase   initialEndBase
        total     (DT--route-total-length newPts)
        elevations (DT--center-end-elevations newCenter)
        startZ    (car elevations)
        endZ      (cadr elevations)
        delta     (- endZ startZ)
        provisionalSlope (/ delta (max 0.001 (- total startBase endBase)))
        arcP      (DT--elevation-arc-required-p provisionalSlope)
        routeAvailable (- total startBase endBase)
        verticalP
          (and arcP
               (numberp startSpan)
               (numberp endSpan)
               (> routeAvailable 0.01)
               (> (abs delta) 0.01)))
  ;; Palet esigini gecen gecislerde iki esnek block arasindaki tava,
  ;; planda ihmal edilebilir bir mesafede gercek 3B dik inis yapar.
  ;; Kalan yatay mesafe iki uca esit dagitilarak mevcut tava ekseni korunur.
  (if verticalP
    (progn
      (setq verticalRun
        (max
          0.002
          (min
            (max 0.01 (* 0.01 (DEG:PLAN-UNIT-SCALE)))
            (* routeAvailable 0.001))))
      (if (>= verticalRun (* routeAvailable 0.25))
        (setq verticalP nil))))
  (if verticalP
    (progn
      (setq naturalStartRun (* 2.0 startSpan)
            naturalEndRun   (* 2.0 endSpan)
            naturalRun      (+ naturalStartRun naturalEndRun)
            blockRunBudget
              (min
                naturalRun
                (* (abs delta) 0.40)
                (- routeAvailable verticalRun)))
      (if (<= blockRunBudget 0.004)
        (setq verticalP nil))))
  (if verticalP
    (progn
      (setq runWeight (+ startSpan endSpan)
            startRun
              (* blockRunBudget
                 (/ startSpan (max runWeight 0.001)))
            endRun      (- blockRunBudget startRun)
            extraBase   (max 0.0
                          (- routeAvailable verticalRun startRun endRun))
            startBase   (+ initialStartBase (/ extraBase 2.0))
            endBase     (+ initialEndBase (/ extraBase 2.0))
            middleRun   verticalRun
            startBlockSpan (/ startRun 2.0)
            endBlockSpan   (/ endRun 2.0)))
    (setq startRun  (if (and arcP startSpan) (* 2.0 startSpan) 0.0)
          endRun    (if (and arcP endSpan) (* 2.0 endSpan) 0.0)
          middleRun (- total startBase endBase startRun endRun)))
  (if (and arcP (> middleRun 0.001))
    (setq middleSlope
      (DT--solve-tangent-slope delta middleRun (+ startRun endRun)))
    (progn
      (setq arcP nil
            startRun 0.0
            endRun 0.0
            middleRun (- total startBase endBase)
            middleSlope (/ delta (max 0.001 middleRun)))
    )
  )
  (setq startTrim  (+ startBase startRun)
        endTrim    (+ endBase endRun)
        startLineZ (+ startZ (DT--tangent-rise startRun middleSlope))
        endLineZ   (- endZ (DT--tangent-rise endRun middleSlope)))
  (DT--set-center-elevation-profile
    newCenter
    startTrim endTrim startLineZ endLineZ)
  (foreach transitionRecord transitionRecords
    (setq rec        (car transitionRecord)
          normalKind (cadr transitionRecord)
          normalGap  (nth 4 transitionRecord)
          baseOverride nil
          spanOverride nil)
    (if verticalP
      (if (= (nth 5 rec) 0)
        (setq baseOverride startBase
              spanOverride startBlockSpan)
        (setq baseOverride endBase
              spanOverride endBlockSpan)))
    (setq elevationResult
      (DT--draw-inline-elevation-fitting
        rec newCenter newPts width normalGap baseOverride spanOverride)
      ins          (car elevationResult)
      shiftPt      (cadr elevationResult)
      elevationGap (caddr elevationResult))
    (if ins
      (progn
        (setq count (1+ (if count count 0))
              blocks (append blocks (list ins)))
        (DT--add-plus-cut newCenter shiftPt elevationGap)
      )
    )
  )
  (foreach oldCenter oldCenters
    (DT--rebuild-center-pieces oldCenter (DT--center-width oldCenter width) nil)
  )
  (if contacts
    (setq newPieces (DT--rebuild-center-pieces newCenter width T))
  )
  (list (if count count 0) newPieces blocks)
)

(defun DT--draw-end-elbow-fitting (pt u v width lay / incoming rec)
  ;; AyrÄ± Ã§izilmiÅŸ iki dik tavada da normal DT kÃ¶ÅŸe bloÄŸunun aynÄ±sÄ±nÄ± kullan.
  (setq incoming (list (- (car u)) (- (cadr u))))
  (setq rec (list 0 pt incoming v width))
  (DT--make-turn-block rec width)
)

(defun DT--poly-area2 (pts / area i n a b)
  (setq area 0.0
        i 0
        n (length pts))
  (while (< i n)
    (setq a (nth i pts)
          b (nth (rem (1+ i) n) pts)
          area (+ area (- (* (car a) (cadr b)) (* (cadr a) (car b)))))
    (setq i (1+ i))
  )
  area
)

(defun DT--same-point-p (a b tol)
  (and a b (<= (distance a b) tol))
)

(defun DT--replace-last-item (lst val / out i n x)
  (setq i 0
        n (length lst))
  (foreach x lst
    (setq out
      (append out
        (list
          (if (= i (1- n)) val x)
        )
      )
    )
    (setq i (1+ i))
  )
  out
)

(defun DT--drop-last-item (lst)
  (reverse (cdr (reverse lst)))
)

(defun DT--shape-add-point (data pt bulge / pts buls)
  (setq pts  (car data)
        buls (cadr data))
  (if (and pts (DT--same-point-p (g365_last pts) pt 1e-8))
    (setq buls (DT--replace-last-item buls bulge))
    (progn
      (setq pts  (append pts (list pt)))
      (setq buls (append buls (list bulge)))
    )
  )
  (list pts buls)
)

(defun DT--fillet-internal-90-corners (pts radius / area orient data n i prev cur next uPrev uNext lenPrev lenNext cross dotv conc trim t1 t2 bulge outPts outBuls)
  (setq area (DT--poly-area2 pts)
        orient (if (< area 0.0) -1.0 1.0)
        data (list nil nil)
        n (length pts)
        i 0)
  (while (< i n)
    (setq prev (nth (if (= i 0) (1- n) (1- i)) pts)
          cur  (nth i pts)
          next (nth (rem (1+ i) n) pts)
          lenPrev (distance prev cur)
          lenNext (distance cur next))
    (if (and (> radius 0.0001) (> lenPrev 0.0001) (> lenNext 0.0001))
      (progn
        (setq uPrev (DT--seg-unit prev cur)
              uNext (DT--seg-unit cur next)
              cross (DT--cross2 uPrev uNext)
              dotv  (g365_dot (car uPrev) (cadr uPrev) (car uNext) (cadr uNext))
              conc  (and (< (* orient cross) -1e-6) (< (abs dotv) 0.001)))
        (if conc
          (progn
            (setq trim (min radius lenPrev lenNext)
                  t1 (DT--pt+ cur uPrev (- trim))
                  t2 (DT--pt+ cur uNext trim)
                  bulge (* 0.414213562373095 (if (< cross 0.0) -1.0 1.0)))
            (setq data (DT--shape-add-point data t1 bulge))
            (setq data (DT--shape-add-point data t2 0.0))
          )
          (setq data (DT--shape-add-point data cur 0.0))
        )
      )
      (setq data (DT--shape-add-point data cur 0.0))
    )
    (setq i (1+ i))
  )
  (setq outPts  (car data)
        outBuls (cadr data))
  (if (and (> (length outPts) 1) (DT--same-point-p (car outPts) (g365_last outPts) 1e-8))
    (progn
      (setq outPts  (DT--drop-last-item outPts))
      (setq outBuls (DT--drop-last-item outBuls))
    )
  )
  (list outPts outBuls)
)
(defun DT--draw-plus-fitting (pt u v width lay / hu hv lu lv p1 p2 p3 p4 p5 p6 p7 p8 p9 p10 p11 p12 outline filleted)
  (setq hu (/ width 2.0)
        hv (/ width 2.0)
        lu width
        lv width)
  ;; Tek kapali + konturu: dort kolu merkezde birlestirir.
  (setq p1  (DT--pt+ (DT--pt+ pt u lu) v hv))
  (setq p2  (DT--pt+ (DT--pt+ pt u lu) v (- hv)))
  (setq p3  (DT--pt+ (DT--pt+ pt v (- hv)) u hu))
  (setq p4  (DT--pt+ (DT--pt+ pt v (- lv)) u hu))
  (setq p5  (DT--pt+ (DT--pt+ pt v (- lv)) u (- hu)))
  (setq p6  (DT--pt+ (DT--pt+ pt v (- hv)) u (- hu)))
  (setq p7  (DT--pt+ (DT--pt+ pt u (- lu)) v (- hv)))
  (setq p8  (DT--pt+ (DT--pt+ pt u (- lu)) v hv))
  (setq p9  (DT--pt+ (DT--pt+ pt v hv) u (- hu)))
  (setq p10 (DT--pt+ (DT--pt+ pt v lv) u (- hu)))
  (setq p11 (DT--pt+ (DT--pt+ pt v lv) u hu))
  (setq p12 (DT--pt+ (DT--pt+ pt v hv) u hu))
  (setq outline (list p1 p2 p3 p4 p5 p6 p7 p8 p9 p10 p11 p12))
  (setq filleted (DT--fillet-internal-90-corners outline (/ width 2.0)))
  (DT--make-fitting-block
    (strcat "art" (chr 253)) width pt
    (list
      (list (car filleted) T (cadr filleted)
        (list
          (DT--pt+ pt u lu) (DT--pt+ pt u (- lu))
          (DT--pt+ pt v lv) (DT--pt+ pt v (- lv)))))
    (DT--vec-angle u) (DT--mirror-for u v))
)
(defun DT--draw-t-fitting (pt main branch width lay / h lm lb p1 p2 p3 p4 p5 p6 p7 p8 outline filleted)
  (setq h  (/ width 2.0)
        lm width
        lb width)
  ;; Tek kapali T konturu: ana hat iki yon, dal bir yon.
  (setq p1 (DT--pt+ (DT--pt+ pt main lm) branch h))
  (setq p2 (DT--pt+ (DT--pt+ pt main h) branch h))
  (setq p3 (DT--pt+ (DT--pt+ pt main h) branch lb))
  (setq p4 (DT--pt+ (DT--pt+ pt main (- h)) branch lb))
  (setq p5 (DT--pt+ (DT--pt+ pt main (- h)) branch h))
  (setq p6 (DT--pt+ (DT--pt+ pt main (- lm)) branch h))
  (setq p7 (DT--pt+ (DT--pt+ pt main (- lm)) branch (- h)))
  (setq p8 (DT--pt+ (DT--pt+ pt main lm) branch (- h)))
  (setq outline (list p1 p2 p3 p4 p5 p6 p7 p8))
  (setq filleted (DT--fillet-internal-90-corners outline (/ width 2.0)))
  (DT--make-fitting-block
    "T" width pt
    (list
      (list (car filleted) T (cadr filleted)
        (list
          (DT--pt+ pt main lm) (DT--pt+ pt main (- lm))
          (DT--pt+ pt branch lb))))
    (DT--vec-angle main) (DT--mirror-for main branch))
)
(defun DT--place-network-fittings (newPts oldEnts width / hits rec pt oldCenter oldPts fitWidth adjustedNewPts newArms oldInfos oldArms armSpecs forcedTSpecs allArms kind skipJunction records doneT doneP doneF doneE tCount pCount fCount eCount self rec2 axes tb selfArms plusRecords teeRecords flexRecords elbowRecords)
  (setq hits (DT--collect-cross-hits newPts oldEnts width)
        doneT nil doneP nil doneF nil doneE nil
        tCount 0 pCount 0 fCount 0 eCount 0
        plusRecords nil teeRecords nil flexRecords nil elbowRecords nil)
  (foreach rec hits
    (setq pt             (car rec)
          oldCenter      (cadr rec)
          oldPts         (caddr rec)
          adjustedNewPts (if (nth 3 rec) (nth 3 rec) newPts))
    (setq newArms  (DT--arms-at-point adjustedNewPts pt 0.001))
    (setq oldInfos (DT--junction-old-infos pt oldEnts oldCenter oldPts width 0.001 newArms))
    (setq oldArms  (DT--infos-arms oldInfos))
    (setq forcedTSpecs
      (DT--forced-through-tee-specs
        pt adjustedNewPts oldCenter oldPts width))
    (setq armSpecs
      (if forcedTSpecs
        forcedTSpecs
        (DT--infos-arm-specs newArms width oldInfos)))
    (setq allArms  (DT--arm-spec-rays armSpecs))
    (setq fitWidth (DT--specs-max-width armSpecs width))
    (setq skipJunction
      (and (not forcedTSpecs)
           oldArms
           (or
             (DT--endpoint-continuation-p pt adjustedNewPts oldArms)
             (DT--internal-corner-continuation-p pt adjustedNewPts oldArms)
             (DT--internal-90-corner-p pt adjustedNewPts 0.001))
           (not (DT--live-fitting-at-point-p pt fitWidth))))
    (setq kind
      (if skipJunction
        nil
        (if (and forcedTSpecs (setq tb (DT--t-axis-branch allArms)))
          (progn
            (DT--delete-existing-fittings-at
              pt (DT--layer-fitting) (+ fitWidth 1.0))
            (DT--draw-t-fitting
              pt (car tb) (cadr tb) fitWidth (DT--layer-fitting))
            'TEE)
          (DT--draw-updated-junction-fitting
            pt allArms armSpecs fitWidth))
      )
    )
    (cond
      ((= kind 'PLUS)
        (if (not (DT--point-known-p pt doneP 0.001))
          (progn
            (setq doneP (cons pt doneP) pCount (1+ pCount))
            (setq plusRecords (append plusRecords (DT--junction-records pt oldInfos adjustedNewPts fitWidth)))
          )
        ))
      ((= kind 'TEE)
        (if (not (DT--point-known-p pt doneT 0.001))
          (progn
            (setq doneT (cons pt doneT) tCount (1+ tCount))
            (setq teeRecords (append teeRecords (DT--junction-records pt oldInfos adjustedNewPts fitWidth)))
          )
        ))
      ((= kind 'ELBOW)
        (if (not (DT--point-known-p pt doneE 0.001))
          (progn
            (setq doneE (cons pt doneE) eCount (1+ eCount))
            (setq elbowRecords (append elbowRecords (DT--junction-records pt oldInfos adjustedNewPts fitWidth)))
          )
        ))
      ((= kind 'FLEX)
        (if (not (DT--point-known-p pt doneF 0.001))
          (progn
            (setq doneF (cons pt doneF) fCount (1+ fCount))
            (setq flexRecords (append flexRecords (DT--junction-records pt oldInfos adjustedNewPts fitWidth)))
          )
        ))
    )
  )
  (setq self (DT--collect-self-hits newPts))
  (foreach rec2 self
    (setq pt       (car rec2)
          selfArms (DT--arms-at-point newPts pt 0.001)
          axes     (DT--four-way-axes selfArms)
          tb       (DT--t-axis-branch selfArms))
    (cond
      (axes
        (if (not (DT--point-known-p pt doneP 0.001))
          (progn
            (DT--delete-existing-fittings-at pt (DT--layer-fitting) (+ width 1.0))
            (DT--draw-plus-fitting pt (car axes) (cadr axes) width (DT--layer-fitting))
            (setq doneP (cons pt doneP) pCount (1+ pCount))))
        (setq plusRecords
          (append plusRecords (list (list pt nil nil nil width nil)))))
      (tb
        (if (not (DT--point-known-p pt doneT 0.001))
          (progn
            (DT--delete-existing-fittings-at pt (DT--layer-fitting) (+ width 1.0))
            (DT--draw-t-fitting pt (car tb) (cadr tb) width (DT--layer-fitting))
            (setq doneT (cons pt doneT)
                  tCount (1+ tCount)
                  teeRecords
                    (append teeRecords
                      (list (list pt nil newPts nil width nil))))))))
  )
  (list tCount pCount plusRecords teeRecords fCount flexRecords eCount elbowRecords)
)
(defun DT--nominal-width (v / allowed hit item)
  (setq allowed '(10.0 20.0 30.0 40.0 50.0))
  (if (numberp v)
    (foreach item allowed
      (if (equal (float v) item 0.000001) (setq hit item))
    )
  )
  hit
)

(defun DT--parse-width (s / v)
  (if s
    (progn
      (setq v (distof s 2))
      (if (or (null v) (<= v 0.0))
        (setq v (atof (vl-string-translate "," "." s)))
      )
      (DT--nominal-width v)
    )
  )
)

(defun DT--plan-width (nominalWidth)
  (if (and (numberp nominalWidth) (> nominalWidth 0.0))
    (* nominalWidth (DEG:PLAN-UNIT-SCALE))
  )
)

(defun DT--plan-side-height (sideHeightMm / scale)
  (if (and (numberp sideHeightMm) (> sideHeightMm 0.0))
    (progn
      (setq scale (DEG:PLAN-UNIT-SCALE))
      (if (<= scale 0.0) (setq scale 1.0))
      (* sideHeightMm (/ scale 10.0)))
    0.0
  )
)

(defun DT--plan-material-thickness (/ scale)
  ;; One physical centimetre in the active PLAN unit convention.
  (setq scale (DEG:PLAN-UNIT-SCALE))
  (if (> scale 0.0) scale 1.0)
)

(defun DT--nominal-from-plan-width (planWidth / scale)
  (setq scale (DEG:PLAN-UNIT-SCALE))
  (if (<= scale 0.0) (setq scale 1.0))
  (/ (float planWidth) scale)
)

(defun DT--last-width (/ s v)
  (setq s (getenv "DEG_DT_LAST_WIDTH"))
  (setq v (DT--parse-width s))
  (if v v 10.0)
)

(defun DT--remember-width (width)
  (if (and (numberp width) (> width 0.0))
    (progn
      (setq *DT_LAST_WIDTH* width)
      (setenv "DEG_DT_LAST_WIDTH" (rtos width 2 12))
    )
  )
  width
)

(defun DT--last-elevation-angle (/ value)
  (setq value
    (atof
      (if (getenv "DEG_DT_ELEVATION_ANGLE")
        (getenv "DEG_DT_ELEVATION_ANGLE")
        "")))
  (if (and (> value 0.0) (<= value 90.0)) value 45.0)
)

(defun DT--remember-elevation-angle (value)
  (if (and (numberp value) (> value 0.0) (<= value 90.0))
    (setenv "DEG_DT_ELEVATION_ANGLE" (rtos value 2 6)))
  value
)

(defun DT--active-elevation-angle ()
  (if (and (boundp '*DT_ACTIVE_ELEVATION_ANGLE*)
           (numberp *DT_ACTIVE_ELEVATION_ANGLE*)
           (> *DT_ACTIVE_ELEVATION_ANGLE* 0.0)
           (<= *DT_ACTIVE_ELEVATION_ANGLE* 90.0))
    *DT_ACTIVE_ELEVATION_ANGLE*
    (DT--last-elevation-angle))
)

(defun DT--meta-app () "DT_TRAY_META")

(defun DT--3d-mode-app () "DT_TRAY_3D")

(defun DT--entity-3d-mode-value (ent / app ed xd rec item value)
  (setq app (DT--3d-mode-app))
  (if (and ent (entget ent) (tblsearch "APPID" app))
    (progn
      (setq ed  (entget ent (list app))
            xd  (assoc -3 ed)
            rec (if xd (cadr xd) nil))
      (if (and rec (= (car rec) app))
        (foreach item (cdr rec)
          (if (= (car item) 1070)
            (setq value (if (= (cdr item) 0) "0" "1")))))))
  value
)

(defun DT--entity-3d-enabled-p (ent / value center)
  (setq value (DT--entity-3d-mode-value ent))
  (if (null value)
    (progn
      (if (and ent (DT--visible-tray-p ent))
        (setq center (DT--center-for-tray ent)))
      (if center (setq value (DT--entity-3d-mode-value center)))))
  ;; Legacy DT geometry predates this flag and is therefore 3D.
  (if (= value "0") nil T)
)

(defun DT--set-entity-3d-mode (ent enabled / app ed payload)
  (setq app (DT--3d-mode-app))
  (if (not (tblsearch "APPID" app)) (regapp app))
  (if (and ent (setq ed (entget ent '("*"))))
    (progn
      (setq payload
        (list app (cons 1070 (if enabled 1 0))))
      (setq ed (DT--xdata-set-app ed app payload))
      (entmod ed)
      (entupd ent)
      ent))
)

(defun DT--set-tray-3d-mode (center pieces turnBlocks enabled / ent)
  (DT--set-entity-3d-mode center enabled)
  (foreach ent pieces
    (DT--set-entity-3d-mode ent enabled)
    (if (and ent (DT--visible-tray-p ent))
      (DT--light-migrate-tray ent)))
  (foreach ent turnBlocks (DT--set-entity-3d-mode ent enabled))
  center
)

(defun DT--tray-meta (ent / app ed xd rec item mode nominal sideHeight trayHeight)
  (setq app (DT--meta-app))
  (if (and ent (entget ent))
    (progn
      (setq ed (entget ent (list app))
            xd (assoc -3 ed)
            rec (if xd (cadr xd) nil))
      (if (and rec (= (car rec) app))
        (foreach item (cdr rec)
          (cond
            ((= (car item) 1000)
              (if mode
                (setq trayHeight (cdr item))
                (setq mode (cdr item))))
            ((= (car item) 1040)
              (if nominal
                (setq sideHeight (cdr item))
                (setq nominal (cdr item))))
          )
        )
      )
    )
  )
  (if (or mode nominal sideHeight trayHeight)
    (list mode nominal sideHeight (if trayHeight trayHeight ""))
  )
)

(defun DT--set-tray-meta-one (ent mode nominal sideHeight trayHeight / app ed payload)
  (setq app (DT--meta-app))
  (if (not (tblsearch "APPID" app)) (regapp app))
  (if (and ent (entget ent))
    (progn
      (setq payload
        (list
          app
          (cons 1000 (DT--normalize-mode mode))
          (cons 1040 (float nominal))
          (cons 1040 (float sideHeight))
          (cons 1000 (if trayHeight trayHeight ""))))
      (setq ed (entget ent '("*")))
      (setq ed (DT--xdata-set-app ed app payload))
      (entmod ed)
      (entupd ent)
    )
  )
  ent
)

(defun DT--set-entity-layer-only (ent lay / ed pair)
  (if (and ent lay (setq ed (entget ent)))
    (progn
      (setq pair (assoc 8 ed)
            ed   (if pair
                   (subst (cons 8 lay) pair ed)
                   (append ed (list (cons 8 lay)))))
      (entmod ed)
      (entupd ent)
      ent)
  )
)

(defun DT--set-tray-meta (center pieces turnBlocks mode nominal sideHeight trayHeight / ent)
  (DT--set-tray-meta-one center mode nominal sideHeight trayHeight)
  (foreach ent pieces
    (DT--set-tray-meta-one ent mode nominal sideHeight trayHeight)
  )
  (foreach ent turnBlocks
    (DT--set-tray-meta-one ent mode nominal sideHeight trayHeight)
  )
  center
)

(defun DT--tray-piece-override-p (tray / app ed)
  (setq app "DT_TRAY_PIECE_OVERRIDE")
  (and tray
       (tblsearch "APPID" app)
       (setq ed (entget tray (list app)))
       (assoc -3 ed))
)

(defun DT--set-tray-piece-override (tray / app ed payload)
  (setq app "DT_TRAY_PIECE_OVERRIDE")
  (if (not (tblsearch "APPID" app)) (regapp app))
  (if (and tray (setq ed (entget tray '("*"))))
    (progn
      (setq payload (list app (cons 1070 1))
            ed      (DT--xdata-set-app ed app payload))
      (entmod ed)
      (entupd tray)
      tray))
)

(defun DT--tray-meta-effective (tray / trayMeta center centerMeta)
  (setq trayMeta (DT--tray-meta tray)
        center   (DT--center-for-tray tray)
        centerMeta (if center (DT--tray-meta center)))
  ;; The center route is authoritative. A legacy lightweight migration may
  ;; have persisted the total elevation delta as the tray side height. A tray
  ;; edited alone from the palette keeps its own explicit metadata.
  (if (and trayMeta (DT--tray-piece-override-p tray))
    trayMeta
    (if centerMeta centerMeta trayMeta))
)

(defun DT--string-add-unique-ci (value values / u hit item)
  (setq value (vl-string-trim " \t\r\n" (if value value ""))
        u     (strcase value))
  (if (/= value "")
    (progn
      (foreach item values
        (if (= u (strcase item)) (setq hit T))
      )
      (if (not hit) (append values (list value)) values)
    )
    values
  )
)

(defun DT--plan-height-values (/ ss i ent meta height values)
  (setq ss (ssget "_X" (list (cons 0 "LWPOLYLINE,POLYLINE") (cons 8 (DT--layer-center)))))
  (if ss
    (progn
      (setq i 0)
      (while (< i (sslength ss))
        (setq ent    (ssname ss i)
              meta   (DT--tray-meta ent)
              height (if meta (nth 3 meta) nil)
              values (DT--string-add-unique-ci height values)
              i      (1+ i))
      )
    )
  )
  (if values (acad_strlsort values) nil)
)

(defun DT--panel-widths () '(10.0 20.0 30.0 40.0 50.0))

(defun DT--panel-side-values (/ nominal value values)
  (foreach nominal (DT--panel-widths)
    (setq value  (DEG:NUM->STR (DTT--side-height-mm nominal))
          values (DT--string-add-unique-ci value values))
  )
  (if values (acad_strlsort values) '("40" "50"))
)

(defun DT--last-side-height (nominal / value)
  (setq value (atof (if (getenv "DEG_DT_LAST_SIDE_HEIGHT") (getenv "DEG_DT_LAST_SIDE_HEIGHT") "")))
  (if (> value 0.0) value (DTT--side-height-mm nominal))
)

(defun DT--remember-side-height (value)
  (if (and (numberp value) (> value 0.0))
    (setenv "DEG_DT_LAST_SIDE_HEIGHT" (rtos value 2 8))
  )
  value
)

(defun DT--last-tray-height ()
  (if (getenv "DEG_DT_LAST_TRAY_HEIGHT") (getenv "DEG_DT_LAST_TRAY_HEIGHT") "")
)

(defun DT--remember-tray-height (value)
  (setq value (vl-string-trim " \t\r\n" (if value value "")))
  (setenv "DEG_DT_LAST_TRAY_HEIGHT" value)
  value
)

(defun DT--last-ladder-bottom ()
  (if (getenv "DEG_DT_LAST_LADDER_BOTTOM")
    (getenv "DEG_DT_LAST_LADDER_BOTTOM")
    "0")
)

(defun DT--remember-ladder-bottom (value)
  (setq value (vl-string-trim " \t\r\n" (if value value "")))
  (setenv "DEG_DT_LAST_LADDER_BOTTOM" value)
  value
)

(defun DT--last-3d-enabled (/ value)
  (setq value (getenv "DEG_DT_LAST_3D"))
  (if (null value)
    T
    (/= value "0")
  )
)

(defun DT--remember-3d-enabled (enabled)
  (setenv "DEG_DT_LAST_3D" (if enabled "1" "0"))
  (if enabled T nil)
)

(defun DT--palette-process-id (/ value)
  (setq value (vl-catch-all-apply 'getvar (list "PROCESSID")))
  (if (and (not (vl-catch-all-error-p value)) (numberp value))
    (fix value)
    0
  )
)

(defun DT--palette-window-handle (/ app value)
  (vl-load-com)
  (setq app (vl-catch-all-apply 'vlax-get-acad-object '()))
  (if (and app (not (vl-catch-all-error-p app)))
    (setq value (vl-catch-all-apply 'vlax-get-property (list app 'HWND))))
  (if (and value (not (vl-catch-all-error-p value)) (numberp value))
    (fix value)
    0
  )
)

(defun DT--palette-script-path (/ found path)
  (setq found (findfile "DG_DT_TAVA_PALET.ps1"))
  (if found
    found
    (progn
      (setq path (strcat (getenv "USERPROFILE") "\\Documents\\metraj\\DEG\\DG_DT_TAVA_PALET.ps1"))
      (if (findfile path) path nil)
    )
  )
)

(defun DT--palette-state-path (/ pid hwnd key)
  (setq pid  (DT--palette-process-id)
        hwnd (DT--palette-window-handle)
        key  (if (> pid 0) pid hwnd))
  (strcat (getenv "TEMP") "\\deg_dt_tava_palette_" (itoa key) ".txt")
)

(defun DT--palette-state-read (path / file line pos key value out)
  (if (and path (setq file (open path "r")))
    (progn
      (while (setq line (read-line file))
        (setq pos (vl-string-search "=" line))
        (if (and pos (> pos 0))
          (progn
            (setq key   (strcase (vl-string-trim " \t\r\n" (substr line 1 pos)))
                  value (substr line (+ pos 2)))
            (setq out (cons (cons key value) out))
          )
        )
      )
      (close file)
    )
  )
  (reverse out)
)

(defun DT--palette-state-get (key state / pair)
  (if (setq pair (assoc (strcase key) state)) (cdr pair) nil)
)

(defun DT--palette-state-put (key value state / pair item out upper)
  (setq upper (strcase key))
  (foreach item state
    (if (= (car item) upper)
      (setq out (append out (list (cons upper (if value value "")))))
      (setq out (append out (list item)))
    )
  )
  (if (null (assoc upper state))
    (setq out (append out (list (cons upper (if value value "")))))
  )
  out
)

(defun DT--palette-join (values / out value)
  (foreach value values
    (setq value (vl-string-trim " \t\r\n" (if value value "")))
    (if (/= value "")
      (setq out (if out (strcat out "|" value) value))
    )
  )
  (if out out "")
)

(defun DT--palette-state-write (path state / file key value)
  (if (setq file (open path "w"))
    (progn
      (foreach key
          '("MODE" "WIDTH" "SIDE" "HEIGHT" "LADDER_BOTTOM" "ELEVATION_ANGLE" "THREE_D"
          "TYPE_OPTIONS" "WIDTH_OPTIONS" "SIDE_OPTIONS" "HEIGHT_OPTIONS"
          "CONTEXT" "SELECTION_ACTIVE" "SELECTION_COUNT"
          "SELECTION_MODE" "SELECTION_WIDTH" "SELECTION_SIDE" "SELECTION_HEIGHT"
          "SELECTION_LADDER_BOTTOM" "SELECTION_3D"
          "SELECTION_REV" "REQUEST" "REQUEST_3D" "REQUEST_ID" "REQUEST_DONE" "STATUS"
          "CLOSED" "PID")
        (setq value (DT--palette-state-get key state))
        (if value (write-line (strcat key "=" value) file))
      )
      (close file)
      T
    )
    nil
  )
)

(defun DT--palette-prepare-state (path defaultMode defaultWidth / state active mode width side height ladderBottom elevationAngle threeD heights value)
  (setq state  (DT--palette-state-read path)
        active (= (DT--palette-state-get "CLOSED" state) "0")
        mode   (if active (DT--palette-state-get "MODE" state) nil)
        width  (if active (DT--palette-state-get "WIDTH" state) nil)
        side   (if active (DT--palette-state-get "SIDE" state) nil)
        height (if active (DT--palette-state-get "HEIGHT" state) nil)
        ladderBottom (if active (DT--palette-state-get "LADDER_BOTTOM" state) nil)
        threeD (if active (DT--palette-state-get "THREE_D" state) nil)
        elevationAngle
          (atof
            (vl-string-translate
              "," "."
              (if (DT--palette-state-get "ELEVATION_ANGLE" state)
                (DT--palette-state-get "ELEVATION_ANGLE" state)
                ""))))
  (if (null (DT--find-type mode)) (setq mode (DT--normalize-mode defaultMode)))
  (if (null (DT--parse-width width)) (setq width (rtos defaultWidth 2 0)))
  (if (<= (atof (if side side "")) 0.0)
    (setq side (DEG:NUM->STR (DT--last-side-height (DT--parse-width width))))
  )
  (if (null height) (setq height (DT--last-tray-height)))
  (if (null ladderBottom) (setq ladderBottom (DT--last-ladder-bottom)))
  (if (not (member threeD '("0" "1")))
    (setq threeD (if (DT--last-3d-enabled) "1" "0")))
  (if (or (<= elevationAngle 0.0) (> elevationAngle 90.0))
    (setq elevationAngle (DT--last-elevation-angle)))
  (setq heights (DT--plan-height-values))
  (if (/= (vl-string-trim " \t\r\n" height) "")
    (setq heights (DT--string-add-unique-ci height heights))
  )
  (setq state (DT--palette-state-put "MODE" mode state)
        state (DT--palette-state-put "WIDTH" width state)
        state (DT--palette-state-put "SIDE" side state)
        state (DT--palette-state-put "HEIGHT" height state)
        state (DT--palette-state-put "LADDER_BOTTOM" ladderBottom state)
        state (DT--palette-state-put "ELEVATION_ANGLE" (DEG:NUM->STR elevationAngle) state)
        state (DT--palette-state-put "THREE_D" threeD state)
        state (DT--palette-state-put "TYPE_OPTIONS" (DT--palette-join (mapcar 'car (DT--type-configs))) state)
        state (DT--palette-state-put "WIDTH_OPTIONS" (DT--palette-join (mapcar '(lambda (v) (rtos v 2 0)) (DT--panel-widths))) state)
        state (DT--palette-state-put "SIDE_OPTIONS" (DT--palette-join (DT--panel-side-values)) state)
        state (DT--palette-state-put "HEIGHT_OPTIONS" (DT--palette-join heights) state)
        state (DT--palette-state-put "CONTEXT" "DRAW" state)
        state (DT--palette-state-put "SELECTION_ACTIVE" "0" state)
        state (DT--palette-state-put "SELECTION_COUNT" "0" state)
        state (DT--palette-state-put "SELECTION_LADDER_BOTTOM" "" state)
        state (DT--palette-state-put "SELECTION_3D" "" state)
        state (DT--palette-state-put "REQUEST" "" state)
        state (DT--palette-state-put "CLOSED" "0" state)
        state (DT--palette-state-put "PID" "0" state))
  (if (DT--palette-state-write path state) state nil)
)

(defun DT--palette-open-state (/ path state)
  (setq path  (DT--palette-state-path)
        state (DT--palette-state-read path))
  (if (= (DT--palette-state-get "CLOSED" state) "0")
    (list path state)
  )
)

(defun DT--palette-refresh-type-options (/ path state options mode)
  (setq path    (DT--palette-state-path)
        state   (DT--palette-state-read path)
        options (mapcar 'car (DT--type-configs))
        mode    (DT--palette-state-get "MODE" state))
  (if state
    (progn
      (if (or (null mode) (null (DT--find-type mode)))
        (setq mode (if options (car options) "KA")))
      (setq state
        (DT--palette-state-put
          "TYPE_OPTIONS" (DT--palette-join options) state))
      (setq state (DT--palette-state-put "MODE" mode state))
      (DT--palette-state-write path state)
    )
  )
)

(defun DT--palette-set-context (context / rec path state)
  (setq rec (DT--palette-open-state))
  (if rec
    (progn
      (setq path  (car rec)
            state (cadr rec)
            state (DT--palette-state-put "CONTEXT" context state))
      (DT--palette-state-write path state)
    )
  )
)

(defun DT--palette-quote (value)
  (strcat "\"" value "\"")
)

(defun DT--run-hidden-process (executable arguments / shell commandLine result)
  (vl-load-com)
  (setq commandLine (strcat (DT--palette-quote executable) " " arguments)
        shell       (vl-catch-all-apply 'vlax-create-object (list "WScript.Shell")))
  (if (and shell (not (vl-catch-all-error-p shell)))
    (progn
      ;; 0 = gizli pencere, waitOnReturn = false; PowerShell konsolu hic gosterilmez.
      (setq result
        (vl-catch-all-apply
          'vlax-invoke-method
          (list shell 'Run commandLine 0 :vlax-false)))
      (vlax-release-object shell)
      (not (vl-catch-all-error-p result)))
    nil
  )
)

(defun DT--palette-start (defaultMode defaultWidth / script path pid hwnd args result)
  (setq script (DT--palette-script-path)
        path   (DT--palette-state-path)
        pid    (DT--palette-process-id)
        hwnd   (DT--palette-window-handle))
  (if (and script (DT--palette-prepare-state path defaultMode defaultWidth))
    (progn
      (setq *DT_PALETTE_STATE_PATH* path
            args
              (strcat
                "-NoProfile -ExecutionPolicy Bypass -STA -WindowStyle Hidden -File "
                (DT--palette-quote script)
                " -StatePath " (DT--palette-quote path)
                " -HostPid " (itoa pid)
                " -HostHwnd " (itoa hwnd)))
      (setq result (DT--run-hidden-process "powershell.exe" args))
      result
    )
    nil
  )
)

(defun DT--palette-settings (defaultMode defaultWidth / path state modeText mode width sideText side heightText height elevationAngleText elevationAngle threeDText threeD)
  (setq path
    (if (and (boundp '*DT_PALETTE_STATE_PATH*) (= (type *DT_PALETTE_STATE_PATH*) 'STR))
      *DT_PALETTE_STATE_PATH*
      (DT--palette-state-path)))
  (setq state      (DT--palette-state-read path)
        modeText   (DT--palette-state-get "MODE" state)
        mode       (DT--normalize-mode (if modeText modeText defaultMode))
        width      (DT--parse-width (DT--palette-state-get "WIDTH" state))
        sideText   (DT--palette-state-get "SIDE" state)
        side       (atof (vl-string-translate "," "." (if sideText sideText "")))
        heightText (DT--palette-state-get "HEIGHT" state)
        height     (if heightText heightText (DT--last-tray-height))
        threeDText (DT--palette-state-get "THREE_D" state)
        threeD     (if (= threeDText "0") nil T)
        elevationAngleText (DT--palette-state-get "ELEVATION_ANGLE" state)
        elevationAngle
          (atof
            (vl-string-translate
              "," "."
              (if elevationAngleText elevationAngleText ""))))
  (if (null width) (setq width (DT--nominal-width defaultWidth)))
  (if (null width) (setq width (DT--last-width)))
  (if (<= side 0.0) (setq side (DT--last-side-height width)))
  (if (or (<= elevationAngle 0.0) (> elevationAngle 90.0))
    (setq elevationAngle (DT--last-elevation-angle)))
  (DT--remember-mode mode)
  (DT--remember-width width)
  (DT--remember-side-height side)
  (DT--remember-tray-height height)
  (DT--remember-elevation-angle elevationAngle)
  (DT--remember-3d-enabled threeD)
  (list mode width side height elevationAngle threeD)
)

(defun DT--ladder-meta-app () "DT_LADDER_META")

(defun DT--ladder-meta (ent / app ed xd rec item strings numbers)
  (setq app (DT--ladder-meta-app))
  (if (and ent (entget ent))
    (progn
      (setq ed  (entget ent (list app))
            xd  (assoc -3 ed)
            rec (if xd (cadr xd) nil))
      (if (and rec (= (car rec) app))
        (foreach item (cdr rec)
          (cond
            ((= (car item) 1000)
              (setq strings (append strings (list (cdr item)))))
            ((= (car item) 1040)
              (setq numbers (append numbers (list (cdr item)))))))
      )
    )
  )
  (if (and strings (>= (length numbers) 4))
    (list
      (car strings)
      (nth 0 numbers)
      (nth 1 numbers)
      (nth 2 numbers)
      (nth 3 numbers)
      (if (> (length strings) 1) (nth 1 strings) ""))
  )
)

(defun DT--set-ladder-meta
  (ent mode nominal side topElevation bottomElevation groupId / app ed payload)
  (setq app (DT--ladder-meta-app))
  (if (not (tblsearch "APPID" app)) (regapp app))
  (if (and ent (entget ent))
    (progn
      (setq payload
        (list
          app
          (cons 1000 (DT--normalize-mode mode))
          (cons 1000 (if groupId groupId ""))
          (cons 1040 (float nominal))
          (cons 1040 (float side))
          (cons 1040 (float topElevation))
          (cons 1040 (float bottomElevation))))
      (setq ed (entget ent '("*"))
            ed (DT--xdata-set-app ed app payload))
      (entmod ed)
      (entupd ent)))
  ent
)

(defun DT--ladder-group-name (groupId)
  (if (and groupId (/= groupId ""))
    (strcat "DT$MERDIVEN$" (strcase groupId)))
)

(defun DT--group-members-by-name (name / group ed item members)
  (setq group (if name (DT--group-by-name name)))
  (if (and group (setq ed (entget group)))
    (foreach item ed
      (if (and (= (car item) 340) (DT--entity-alive-p (cdr item)))
        (setq members (append members (list (cdr item))))))
  )
  members
)

(defun DT--entity-in-list-p (ent entities / handle item found)
  (setq handle (if ent (DT--ent-handle ent)))
  (while (and handle entities (null found))
    (setq item     (car entities)
          entities (cdr entities))
    (if (and item (= handle (DT--ent-handle item)))
      (setq found T)))
  found
)

(defun DT--ladder-named-members (ent / meta groupId members)
  (setq meta    (DT--ladder-meta ent)
        groupId (if meta (nth 5 meta)))
  (if (and groupId (/= groupId ""))
    (setq members
      (DT--group-members-by-name (DT--ladder-group-name groupId))))
  ;; COPY, XData'daki eski groupId'yi tasir; fakat kopya eski named group'un
  ;; uyesi degildir. Yalniz gercek uyelik dogrulanirsa bu grubu kullan.
  (if (and members (DT--entity-in-list-p ent members)) members)
)

(defun DT--ladder-attached-group-p (ent)
  (if (DT--ladder-named-members ent) T nil)
)

(defun DT--ladder-members (ent / members)
  (setq members (DT--ladder-named-members ent))
  (if members members (if (and ent (entget ent)) (list ent)))
)

(defun DT--delete-ladder-composite (ent / meta groupId members entity handle)
  (setq meta    (DT--ladder-meta ent)
        groupId (if meta (nth 5 meta))
        members (DT--ladder-members ent))
  (if (and groupId (/= groupId "") (DT--ladder-attached-group-p ent))
    (DT--delete-group-by-name (DT--ladder-group-name groupId)))
  (foreach entity members
    (if (and entity (entget entity))
      (progn
        (setq handle (DT--ent-handle entity))
        (vl-catch-all-apply 'entdel (list entity))
        (if handle (DT--remember-deleted-handle handle)))))
  T
)

(defun DT--ladder-block-name (mode planWidth sideHeight deltaZ)
  (strcat
    "e_" (DT--name-safe (DT--normalize-mode mode))
    "_merdiven_W" (DT--width-name planWidth)
    "_H" (DT--width-name sideHeight)
    "_DZ" (DT--width-name deltaZ)
    "_DIK_S30_B2_KAPAK3_X_K1"
    (DT--shell-style-token))
)

(defun DT--ladder-local-point (x y deltaZ ratio zOffset)
  (list
    x
    y
    (+ (* deltaZ ratio) zOffset))
)

(defun DT--ladder-side-solid
  (outerX innerX front back deltaZ)
  (DT--block-face-hatched-flags
    (list
      (DT--ladder-local-point outerX front deltaZ 0.0 0.0)
      (DT--ladder-local-point outerX front deltaZ 1.0 0.0)
      (DT--ladder-local-point outerX back  deltaZ 1.0 0.0)
      (DT--ladder-local-point outerX back  deltaZ 0.0 0.0))
    0)
  (DT--block-face-hatched-flags
    (list
      (DT--ladder-local-point innerX back  deltaZ 0.0 0.0)
      (DT--ladder-local-point innerX back  deltaZ 1.0 0.0)
      (DT--ladder-local-point innerX front deltaZ 1.0 0.0)
      (DT--ladder-local-point innerX front deltaZ 0.0 0.0))
    0)
  (DT--block-face-hatched-flags
    (list
      (DT--ladder-local-point outerX front deltaZ 0.0 0.0)
      (DT--ladder-local-point innerX front deltaZ 0.0 0.0)
      (DT--ladder-local-point innerX front deltaZ 1.0 0.0)
      (DT--ladder-local-point outerX front deltaZ 1.0 0.0))
    0)
  (DT--block-face-hatched-flags
    (list
      (DT--ladder-local-point innerX back deltaZ 0.0 0.0)
      (DT--ladder-local-point outerX back deltaZ 0.0 0.0)
      (DT--ladder-local-point outerX back deltaZ 1.0 0.0)
      (DT--ladder-local-point innerX back deltaZ 1.0 0.0))
    0)
)

(defun DT--ladder-rung-solid
  (left right front back deltaZ r1 r2)
  (DT--block-face-hatched-flags
    (list
      (DT--ladder-local-point left  front deltaZ r1 0.0)
      (DT--ladder-local-point right front deltaZ r1 0.0)
      (DT--ladder-local-point right front deltaZ r2 0.0)
      (DT--ladder-local-point left  front deltaZ r2 0.0))
    0)
  (DT--block-face-hatched-flags
    (list
      (DT--ladder-local-point right back deltaZ r1 0.0)
      (DT--ladder-local-point left  back deltaZ r1 0.0)
      (DT--ladder-local-point left  back deltaZ r2 0.0)
      (DT--ladder-local-point right back deltaZ r2 0.0))
    0)
  (DT--block-face-hatched-flags
    (list
      (DT--ladder-local-point left  front deltaZ r1 0.0)
      (DT--ladder-local-point left  back  deltaZ r1 0.0)
      (DT--ladder-local-point right back  deltaZ r1 0.0)
      (DT--ladder-local-point right front deltaZ r1 0.0))
    0)
  (DT--block-face-hatched-flags
    (list
      (DT--ladder-local-point left  front deltaZ r2 0.0)
      (DT--ladder-local-point right front deltaZ r2 0.0)
      (DT--ladder-local-point right back  deltaZ r2 0.0)
      (DT--ladder-local-point left  back  deltaZ r2 0.0))
    0)
  (DT--block-face-hatched-flags
    (list
      (DT--ladder-local-point left front deltaZ r1 0.0)
      (DT--ladder-local-point left front deltaZ r2 0.0)
      (DT--ladder-local-point left back  deltaZ r2 0.0)
      (DT--ladder-local-point left back  deltaZ r1 0.0))
    0)
  (DT--block-face-hatched-flags
    (list
      (DT--ladder-local-point right back  deltaZ r1 0.0)
      (DT--ladder-local-point right back  deltaZ r2 0.0)
      (DT--ladder-local-point right front deltaZ r2 0.0)
      (DT--ladder-local-point right front deltaZ r1 0.0))
    0)
)

(defun DT--ladder-cap-hatched
  (left right front back elevation / pts data)
  (setq pts
    (list
      (list left  front elevation)
      (list right front elevation)
      (list right back  elevation)
      (list left  back  elevation)))
  (DT--block-poly-entmake-at pts T nil elevation)
  (setq data
    (DT--hatch-data
      (DT--layer-fitting)
      pts
      (DT--mode-hatch-pattern *DT_ACTIVE_MODE*)
      (DT--mode-hatch-color *DT_ACTIVE_MODE*)
      elevation))
  (if data (entmake data))
)

(defun DT--create-ladder-block-def
  (name planWidth sideHeight deltaZ
    / half left right front back rise material leftInner rightInner rungBack
      spacing rungDepth ratioHalf rungDistance ratio r1 r2)
  (if (and name
           (numberp planWidth) (> planWidth 0.0)
           (numberp sideHeight) (> sideHeight 0.0)
           (numberp deltaZ) (> (abs deltaZ) 0.0))
    (progn
      (entmake
        (list
          '(0 . "BLOCK")
          (cons 2 name)
          '(70 . 0)
          '(10 0.0 0.0 0.0)))
      (setq half  (/ planWidth 2.0)
             left  (- half)
            right half
            front (- (/ sideHeight 2.0))
            back  (/ sideHeight 2.0)
            rise  (abs deltaZ)
            material
              (min
                (DT--plan-material-thickness)
                (/ planWidth 4.0)
                (/ sideHeight 2.0))
            leftInner  (+ left material)
            rightInner (- right material)
            rungBack   (min back (+ front material)))

      ;; Iki dik yanak, PLAN birimine gore fiziksel 1 cm et kalinligina sahiptir.
      (DT--ladder-side-solid left  leftInner  front back deltaZ)
      (DT--ladder-side-solid right rightInner front back deltaZ)

      ;; Merdivenin ust ve alt kesitleri hatch ile kapanir.
      (DT--ladder-cap-hatched left right front back 0.0)
      (DT--ladder-cap-hatched left right front back deltaZ)

      ;; Ust ve alt kapaklarda koseden koseye X isareti.
      (DT--block-line-entmake
        (DT--ladder-local-point left  front deltaZ 0.0 0.0)
        (DT--ladder-local-point right back  deltaZ 0.0 0.0))
      (DT--block-line-entmake
        (DT--ladder-local-point right front deltaZ 0.0 0.0)
        (DT--ladder-local-point left  back  deltaZ 0.0 0.0))
      (DT--block-line-entmake
        (DT--ladder-local-point left  front deltaZ 1.0 0.0)
        (DT--ladder-local-point right back  deltaZ 1.0 0.0))
      (DT--block-line-entmake
        (DT--ladder-local-point right front deltaZ 1.0 0.0)
        (DT--ladder-local-point left  back  deltaZ 1.0 0.0))

      ;; Yanak dis kenarlari.
      (DT--block-line-entmake
        (DT--ladder-local-point left front deltaZ 0.0 0.0)
        (DT--ladder-local-point left front deltaZ 1.0 0.0))
      (DT--block-line-entmake
        (DT--ladder-local-point right front deltaZ 0.0 0.0)
        (DT--ladder-local-point right front deltaZ 1.0 0.0))

      ;; Basamak merkezleri PLAN birimine gore tam 30 cm aralikla yerlestirilir.
      (setq spacing (DT--plan-width 30.0))
      (if (or (null spacing) (<= spacing 0.0)) (setq spacing planWidth))
      (setq rungDepth
        (min
          (* 2.0 (DT--plan-material-thickness))
          (/ rise 3.0)))
      (setq ratioHalf (/ rungDepth (* 2.0 rise))
            rungDistance 0.0)
      (while (<= rungDistance (+ rise 0.000001))
        (setq ratio (/ rungDistance rise)
              r1 (max 0.0 (- ratio ratioHalf))
              r2 (min 1.0 (+ ratio ratioHalf)))
        ;; Basamak gorunur yuksekligi 2 cm, govde derinligi 1 cm'dir.
        (DT--ladder-rung-solid left right front rungBack deltaZ r1 r2)
        (DT--block-line-entmake
          (DT--ladder-local-point left  front deltaZ ratio 0.0)
          (DT--ladder-local-point right front deltaZ ratio 0.0))
        (setq rungDistance (+ rungDistance spacing)))

      (entmake '((0 . "ENDBLK")))
      (DT--block-associate-hatches name)
      (DT--set-block-linework-050 name)
      T))
)

(defun DT--make-ladder-block-at
  (base rotation mode nominal side topElevation bottomElevation
    / planWidth sideHeight deltaZ rise name ins)
  (setq mode       (DT--normalize-mode mode)
        planWidth  (DT--plan-width nominal)
        sideHeight (DT--plan-side-height side)
        deltaZ     (- bottomElevation topElevation)
        rise       (abs deltaZ))
  (if (and base
           (DT--find-type mode)
           (numberp planWidth) (> planWidth 0.0)
           (numberp sideHeight) (> sideHeight 0.0)
           (> rise 0.0))
    (progn
      (setq *DT_ACTIVE_MODE* mode
            *DT_ACTIVE_LAYER* (cadr (DT--find-type mode))
            *DT_ACTIVE_SIDE_HEIGHT_MM* side
            *DT_ACTIVE_SIDE_HEIGHT* sideHeight
            *DT_ACTIVE_ELEVATION* topElevation)
      (DT--ensure-type-layers)
      (setq name (DT--ladder-block-name mode planWidth sideHeight deltaZ))
      (if (not (tblsearch "BLOCK" name))
        (DT--create-ladder-block-def name planWidth sideHeight deltaZ))
      (DT--block-associate-hatches name)
      (DT--set-block-linework-050 name)
      (setq ins
        (entmakex
          (list
            '(0 . "INSERT")
            (cons 2 name)
            (cons 8 (DT--layer-visible))
            (cons 10 (DT--point-at-elevation base topElevation))
            '(41 . 1.0)
            '(42 . 1.0)
            '(43 . 1.0)
            (cons 50 (if (numberp rotation) rotation 0.0)))))
      (DT--set-ladder-meta
        ins mode nominal side topElevation bottomElevation "")
      ins))
)

(defun DT--explode-insert-entities
  (ins / object exploded item ent entities)
  (if (and ins (entget ins))
    (progn
      (setq object (vl-catch-all-apply 'vlax-ename->vla-object (list ins)))
      (if (not (vl-catch-all-error-p object))
        (setq exploded (degw-explode->list object)))
      (foreach item exploded
        (if (and item (vlax-objectp item))
          (progn
            (setq ent (vl-catch-all-apply 'vlax-vla-object->ename (list item)))
            (if (and (not (vl-catch-all-error-p ent)) ent (entget ent))
              (setq entities (append entities (list ent)))))))
      (if entities
        (vl-catch-all-apply 'vla-Delete (list object)))
    )
  )
  entities
)

(defun DT--ladder-world-point (base rotation point / ca sa)
  (setq ca (cos rotation)
        sa (sin rotation))
  (list
    (+ (car base)
       (- (* (car point) ca) (* (cadr point) sa)))
    (+ (cadr base)
       (+ (* (car point) sa) (* (cadr point) ca)))
    (+ (if (caddr base) (caddr base) 0.0)
       (if (caddr point) (caddr point) 0.0)))
)

(defun DT--ladder-model-face (base rotation points / world)
  (setq world
    (mapcar
      '(lambda (point) (DT--ladder-world-point base rotation point))
      points))
  (if (= (length world) 4)
    (DT--make-3d-face
      (DT--layer-linework)
      (nth 0 world) (nth 1 world) (nth 2 world) (nth 3 world)))
)

(defun DT--ladder-model-face-hatched
  (base rotation points / world face hatch entities)
  (setq world
    (mapcar
      '(lambda (point) (DT--ladder-world-point base rotation point))
      points))
  (if (= (length world) 4)
    (progn
      (setq face
        (DT--make-3d-face
          (DT--layer-linework)
          (nth 0 world) (nth 1 world) (nth 2 world) (nth 3 world)))
      (if face
        (progn
          (setq entities (list face)
                hatch (DT--make-plane-hatch face (DT--layer-fitting) world))
          (if hatch (setq entities (append entities (list hatch))))))))
  entities
)

(defun DT--ladder-model-line (base rotation point1 point2)
  (entmakex
    (list
      '(0 . "LINE")
      '(100 . "AcDbEntity")
      (cons 8 (DT--layer-linework))
      '(370 . 30)
      '(100 . "AcDbLine")
      (cons 10 (DT--ladder-world-point base rotation point1))
      (cons 11 (DT--ladder-world-point base rotation point2))))
)

(defun DT--ladder-model-side-solid
  (base rotation outerX innerX front back deltaZ / entities newEntities points)
  (foreach points
    (list
      (list
        (DT--ladder-local-point outerX front deltaZ 0.0 0.0)
        (DT--ladder-local-point outerX front deltaZ 1.0 0.0)
        (DT--ladder-local-point outerX back  deltaZ 1.0 0.0)
        (DT--ladder-local-point outerX back  deltaZ 0.0 0.0))
      (list
        (DT--ladder-local-point innerX back  deltaZ 0.0 0.0)
        (DT--ladder-local-point innerX back  deltaZ 1.0 0.0)
        (DT--ladder-local-point innerX front deltaZ 1.0 0.0)
        (DT--ladder-local-point innerX front deltaZ 0.0 0.0))
      (list
        (DT--ladder-local-point outerX front deltaZ 0.0 0.0)
        (DT--ladder-local-point innerX front deltaZ 0.0 0.0)
        (DT--ladder-local-point innerX front deltaZ 1.0 0.0)
        (DT--ladder-local-point outerX front deltaZ 1.0 0.0))
      (list
        (DT--ladder-local-point innerX back deltaZ 0.0 0.0)
        (DT--ladder-local-point outerX back deltaZ 0.0 0.0)
        (DT--ladder-local-point outerX back deltaZ 1.0 0.0)
        (DT--ladder-local-point innerX back deltaZ 1.0 0.0)))
    (setq newEntities
      (DT--ladder-model-face-hatched base rotation points))
    (if newEntities (setq entities (append entities newEntities))))
  entities
)

(defun DT--ladder-model-rung-solid
  (base rotation left right front back deltaZ r1 r2 / entities newEntities points)
  (foreach points
    (list
      (list
        (DT--ladder-local-point left  front deltaZ r1 0.0)
        (DT--ladder-local-point right front deltaZ r1 0.0)
        (DT--ladder-local-point right front deltaZ r2 0.0)
        (DT--ladder-local-point left  front deltaZ r2 0.0))
      (list
        (DT--ladder-local-point right back deltaZ r1 0.0)
        (DT--ladder-local-point left  back deltaZ r1 0.0)
        (DT--ladder-local-point left  back deltaZ r2 0.0)
        (DT--ladder-local-point right back deltaZ r2 0.0))
      (list
        (DT--ladder-local-point left  front deltaZ r1 0.0)
        (DT--ladder-local-point left  back  deltaZ r1 0.0)
        (DT--ladder-local-point right back  deltaZ r1 0.0)
        (DT--ladder-local-point right front deltaZ r1 0.0))
      (list
        (DT--ladder-local-point left  front deltaZ r2 0.0)
        (DT--ladder-local-point right front deltaZ r2 0.0)
        (DT--ladder-local-point right back  deltaZ r2 0.0)
        (DT--ladder-local-point left  back  deltaZ r2 0.0))
      (list
        (DT--ladder-local-point left front deltaZ r1 0.0)
        (DT--ladder-local-point left front deltaZ r2 0.0)
        (DT--ladder-local-point left back  deltaZ r2 0.0)
        (DT--ladder-local-point left back  deltaZ r1 0.0))
      (list
        (DT--ladder-local-point right back  deltaZ r1 0.0)
        (DT--ladder-local-point right back  deltaZ r2 0.0)
        (DT--ladder-local-point right front deltaZ r2 0.0)
        (DT--ladder-local-point right front deltaZ r1 0.0)))
    (setq newEntities
      (DT--ladder-model-face-hatched base rotation points))
    (if newEntities (setq entities (append entities newEntities))))
  entities
)

(defun DT--ladder-model-cap
  (base rotation left right front back elevation / local world boundary hatch entities)
  (setq local
    (list
      (list left  front elevation)
      (list right front elevation)
      (list right back  elevation)
      (list left  back  elevation))
        world
          (mapcar
            '(lambda (point) (DT--ladder-world-point base rotation point))
            local)
        boundary (DT--make-poly3d (DT--layer-linework) world T))
  (if boundary
    (progn
      (setq entities (list boundary)
            hatch (DT--make-plane-hatch boundary (DT--layer-fitting) world))
      (if hatch (setq entities (append entities (list hatch))))))
  entities
)

(defun DT--create-ladder-model-entities
  (base rotation mode nominal side topElevation bottomElevation /
    planWidth sideHeight deltaZ rise half left right front back material
    leftInner rightInner rungBack spacing rungDepth ratioHalf rungDistance
    ratio r1 r2 entities newEntities entity pair)
  (setq mode       (DT--normalize-mode mode)
        planWidth  (DT--plan-width nominal)
        sideHeight (DT--plan-side-height side)
        deltaZ     (- bottomElevation topElevation)
        rise       (abs deltaZ)
        base        (DT--point-at-elevation base topElevation))
  (if (and (DT--find-type mode)
           (numberp planWidth) (> planWidth 0.0)
           (numberp sideHeight) (> sideHeight 0.0)
           (> rise 0.0))
    (progn
      (setq *DT_ACTIVE_MODE* mode
            *DT_ACTIVE_LAYER* (cadr (DT--find-type mode))
            *DT_ACTIVE_SIDE_HEIGHT_MM* side
            *DT_ACTIVE_SIDE_HEIGHT* sideHeight
            *DT_ACTIVE_ELEVATION* topElevation)
      (DT--ensure-type-layers)
      (setq half       (/ planWidth 2.0)
            left       (- half)
            right      half
            front      (- (/ sideHeight 2.0))
            back       (/ sideHeight 2.0)
            material   (min
                         (DT--plan-material-thickness)
                         (/ planWidth 4.0)
                         (/ sideHeight 2.0))
            leftInner  (+ left material)
            rightInner (- right material)
            rungBack   (min back (+ front material)))

      (setq entities
        (append
          entities
          (DT--ladder-model-side-solid
            base rotation left leftInner front back deltaZ)
          (DT--ladder-model-side-solid
            base rotation right rightInner front back deltaZ)
          (DT--ladder-model-cap
            base rotation left right front back 0.0)
          (DT--ladder-model-cap
            base rotation left right front back deltaZ)))

      (foreach pair
        (list
          (list (list left front 0.0) (list right back 0.0))
          (list (list right front 0.0) (list left back 0.0))
          (list (list left front deltaZ) (list right back deltaZ))
          (list (list right front deltaZ) (list left back deltaZ))
          (list (list left front 0.0) (list left front deltaZ))
          (list (list right front 0.0) (list right front deltaZ)))
        (setq entity
          (DT--ladder-model-line base rotation (car pair) (cadr pair)))
        (if entity (setq entities (append entities (list entity)))))

      (setq spacing (DT--plan-width 30.0))
      (if (or (null spacing) (<= spacing 0.0)) (setq spacing planWidth))
      (setq rungDepth
        (min (* 2.0 (DT--plan-material-thickness)) (/ rise 3.0))
            ratioHalf (/ rungDepth (* 2.0 rise))
            rungDistance 0.0)
      (while (<= rungDistance (+ rise 0.000001))
        (setq ratio (/ rungDistance rise)
              r1 (max 0.0 (- ratio ratioHalf))
              r2 (min 1.0 (+ ratio ratioHalf))
              newEntities
                (DT--ladder-model-rung-solid
                  base rotation left right front rungBack deltaZ r1 r2)
              entities (append entities newEntities)
              entity
                (DT--ladder-model-line
                  base rotation
                  (DT--ladder-local-point left  front deltaZ ratio 0.0)
                  (DT--ladder-local-point right front deltaZ ratio 0.0)))
        (if entity (setq entities (append entities (list entity))))
        (setq rungDistance (+ rungDistance spacing)))
      (DT--unique-alive-entities entities)
    )
  )
)

(defun DT--make-ladder-composite-at
  (base rotation mode nominal side topElevation bottomElevation
    / entities groupId groupName group entity)
  (setq entities
    (DT--create-ladder-model-entities
      base rotation mode nominal side topElevation bottomElevation))
  (if entities
    (progn
      (setq groupId   (DT--ent-handle (car entities))
            groupName (DT--ladder-group-name groupId))
      (foreach entity entities
        (DT--set-ladder-meta
          entity mode nominal side topElevation bottomElevation groupId))
      (setq group (DT--make-group-object groupName entities))
      (DT--ensure-composite-pickstyle)
      (car entities))
  )
)

(defun DT--ladder-normalize-elevations (topElevation bottomElevation)
  (if (and (numberp topElevation)
           (numberp bottomElevation)
           (equal topElevation 0.0 0.000001)
           (equal bottomElevation 0.0 0.000001))
    (list (DT--plan-width 5.0) 0.0)
    (list topElevation bottomElevation))
)

(defun DT--ladder-selection-key (ent / meta groupId)
  (setq meta    (DT--ladder-meta ent)
        groupId (if meta (nth 5 meta)))
  (if (and groupId (/= groupId ""))
    (strcase groupId)
    (DT--ent-handle ent))
)

(defun DT--add-ladder-unique (ent ladders / key item found)
  (setq key (DT--ladder-selection-key ent))
  (foreach item ladders
    (if (= key (DT--ladder-selection-key item)) (setq found T)))
  (if found ladders (append ladders (list ent)))
)

(defun DT--ladder-entity-vertex-elevation (ent / pts point total count)
  (setq pts (if ent (DT--entity-points3d ent)))
  (foreach point pts
    (if (and point (numberp (caddr point)))
      (setq total (+ (if total total 0.0) (caddr point))
            count (1+ (if count count 0)))))
  (if (> (if count count 0) 0)
    (/ total (float count))
    (DT--entity-elevation ent))
)

(defun DT--ladder-top-cap-entity-p (ent / meta top ed typ elevation)
  (setq meta      (DT--ladder-meta ent)
        top       (if meta (nth 3 meta))
        ed        (if ent (entget ent))
        typ       (if ed (cdr (assoc 0 ed)))
        elevation (if ed (DT--ladder-entity-vertex-elevation ent)))
  (and
    meta
    (member typ '("LWPOLYLINE" "POLYLINE"))
    (numberp top)
    (numberp elevation)
    (equal elevation top 0.001))
)

(defun DT--ladder-top-cap (ent / meta top entity ed typ elevation difference best bestDifference)
  (setq meta (DT--ladder-meta ent)
        top  (if meta (nth 3 meta)))
  (foreach entity (DT--ladder-members ent)
    (setq ed   (if entity (entget entity))
          typ  (if ed (cdr (assoc 0 ed))))
    (if (and (member typ '("LWPOLYLINE" "POLYLINE")) (numberp top))
      (progn
        (setq elevation  (DT--ladder-entity-vertex-elevation entity)
              difference (abs (- elevation top)))
        (if (or (null bestDifference) (< difference bestDifference))
          (setq best entity bestDifference difference)))))
  (if (and bestDifference (<= bestDifference 0.001)) best)
)

(defun DT--ladder-placement-data (ent / ed typ meta cap pts count point sumX sumY first second)
  (setq ed   (if ent (entget ent))
        typ  (if ed (cdr (assoc 0 ed)))
        meta (DT--ladder-meta ent))
  (cond
    ((= typ "INSERT")
      (list
        (cdr (assoc 10 ed))
        (if (assoc 50 ed) (cdr (assoc 50 ed)) 0.0)))
    (meta
      (setq cap (DT--ladder-top-cap ent)
            pts (if cap (g365_get_pts cap)))
      (if (and pts (>= (length pts) 2))
        (progn
          (foreach point pts
            (setq sumX (+ (if sumX sumX 0.0) (car point))
                  sumY (+ (if sumY sumY 0.0) (cadr point))))
          (setq count  (float (length pts))
                first  (car pts)
                second (cadr pts))
          (list
            (list (/ sumX count) (/ sumY count) (nth 3 meta))
            (angle first second)))))
  )
)

(defun DT--panel-write-dcl (/ fn f line lines)
  (setq fn (strcat (getenv "TEMP") "\\deg_dt_panel.dcl")
        lines
          '("dt_panel : dialog {"
            "  label = \"DT - Tava Secenekleri\";"
            "  : boxed_column {"
            "    label = \"Cizilecek Tava\";"
            "    : popup_list { key = \"dtp_mode\"; label = \"Tava Tipi\"; edit_width = 24; }"
            "    : popup_list { key = \"dtp_width\"; label = \"Genislik\"; edit_width = 24; }"
            "    : popup_list { key = \"dtp_side\"; label = \"Yanak Yuksekligi\"; edit_width = 24; }"
            "    : edit_box { key = \"dtp_height\"; label = \"Tava Yuksekligi\"; edit_width = 24; }"
            "    : popup_list { key = \"dtp_height_pick\"; label = \"Plandaki Yukseklikler\"; edit_width = 24; }"
            "  }"
            "  : row { spacer; : button { key = \"draw\"; label = \"Ciz\"; is_default = true; width = 14; fixed_width = true; } : button { key = \"cancel\"; label = \"Kapat\"; is_cancel = true; width = 14; fixed_width = true; } spacer; }"
            "}"))
  (setq f (open fn "w"))
  (if f
    (progn
      (foreach line lines (write-line line f))
      (close f)
      fn
    )
  )
)

(defun DT--panel-height-picked (/ idx value)
  (setq idx (atoi (get_tile "dtp_height_pick")))
  (if (> idx 0)
    (progn
      (setq value (nth (1- idx) *DT_PANEL_HEIGHT_VALUES*))
      (if value (set_tile "dtp_height" value))
    )
  )
)

(defun DT--panel-screen-point (/ sx sy)
  (cond
    ((and (listp *DT_PANEL_SCREEN_POINT*) (= (length *DT_PANEL_SCREEN_POINT*) 2))
      *DT_PANEL_SCREEN_POINT*)
    ((and (setq sx (getenv "DEG_DT_PANEL_X"))
          (setq sy (getenv "DEG_DT_PANEL_Y")))
      (setq *DT_PANEL_SCREEN_POINT* (list (atoi sx) (atoi sy))))
    (T nil)
  )
)

(defun DT--panel-done (status / pt)
  (setq pt (done_dialog status))
  (if (and (listp pt) (= (length pt) 2))
    (progn
      (setq *DT_PANEL_SCREEN_POINT* pt)
      (setenv "DEG_DT_PANEL_X" (itoa (fix (car pt))))
      (setenv "DEG_DT_PANEL_Y" (itoa (fix (cadr pt))))
    )
  )
  pt
)

(defun DT--panel-width-changed (/ idx nominal sideValue sideIdx)
  (setq idx       (atoi (get_tile "dtp_width"))
        nominal   (nth idx *DT_PANEL_WIDTH_VALUES*)
        sideValue (if nominal (DEG:NUM->STR (DTT--side-height-mm nominal)) nil)
        sideIdx   (if sideValue (DEGDO--string-index-ci sideValue *DT_PANEL_SIDE_VALUES*) nil))
  (if sideIdx (set_tile "dtp_side" (itoa sideIdx)))
)

(defun DT--panel-accept (/ modeIdx widthIdx sideIdx modeRec nominal sideValue trayHeight)
  (setq modeIdx   (atoi (get_tile "dtp_mode"))
        widthIdx  (atoi (get_tile "dtp_width"))
        sideIdx   (atoi (get_tile "dtp_side"))
        modeRec   (nth modeIdx *DT_PANEL_TYPE_VALUES*)
        nominal   (nth widthIdx *DT_PANEL_WIDTH_VALUES*)
        sideValue (atof (nth sideIdx *DT_PANEL_SIDE_VALUES*))
        trayHeight (vl-string-trim " \t\r\n" (get_tile "dtp_height")))
  (if (and modeRec nominal (> sideValue 0.0))
    (progn
      (setq *DT_PANEL_RESULT*
        (list
          (car modeRec) nominal sideValue trayHeight
          (DT--last-elevation-angle)
          (DT--last-3d-enabled)))
      (DT--remember-mode (car modeRec))
      (DT--remember-width nominal)
      (DT--remember-side-height sideValue)
      (DT--remember-tray-height trayHeight)
      (DT--panel-done 1)
    )
    (DEG:WIN-MESSAGE "Tava tipi, genislik ve yanak yuksekligi secilmelidir.")
  )
)

(defun DT--panel-show (defaultMode defaultWidth / dclFn dclId rc idx rec value label defaultSide screenPt dialogOk)
  (setq *DT_PANEL_RESULT* nil
        *DT_PANEL_TYPE_VALUES* (DT--type-configs)
        *DT_PANEL_WIDTH_VALUES* (DT--panel-widths)
        *DT_PANEL_SIDE_VALUES* (DT--panel-side-values)
        *DT_PANEL_HEIGHT_VALUES* (DT--plan-height-values)
        *DT_PANEL_DCL_FAILED* nil
        dclFn (DT--panel-write-dcl)
        dclId (if dclFn (load_dialog dclFn) -1))
  (setq screenPt (DT--panel-screen-point))
  (if (and dclId (>= dclId 0))
    (setq dialogOk
      (if screenPt
        (new_dialog "dt_panel" dclId "" screenPt)
        (new_dialog "dt_panel" dclId)))
  )
  (if (not dialogOk)
    (progn
      (if (and dclId (>= dclId 0)) (unload_dialog dclId))
      (setq *DT_PANEL_DCL_FAILED* T)
      (DEG:WIN-MESSAGE "DT tava secim paneli acilamadi. Son kullanilan ayarlarla bir kez cizilecek.")
      (setq *DT_PANEL_RESULT*
        (list
          (DT--normalize-mode defaultMode)
          defaultWidth
          (DT--last-side-height defaultWidth)
          (DT--last-tray-height)
          (DT--last-elevation-angle)
          (DT--last-3d-enabled))))
    (progn
      (start_list "dtp_mode")
      (foreach rec *DT_PANEL_TYPE_VALUES* (add_list (car rec)))
      (end_list)
      (setq idx (DEGDO--string-index-ci (DT--normalize-mode defaultMode) (mapcar 'car *DT_PANEL_TYPE_VALUES*)))
      (set_tile "dtp_mode" (itoa (if idx idx 0)))

      (start_list "dtp_width")
      (foreach value *DT_PANEL_WIDTH_VALUES*
        (add_list (strcat (rtos (* value 10.0) 2 0) " mm")))
      (end_list)
      (setq idx 0)
      (while (and (< idx (length *DT_PANEL_WIDTH_VALUES*))
                  (not (equal defaultWidth (nth idx *DT_PANEL_WIDTH_VALUES*) 0.001)))
        (setq idx (1+ idx))
      )
      (if (>= idx (length *DT_PANEL_WIDTH_VALUES*)) (setq idx 0))
      (set_tile "dtp_width" (itoa idx))

      (start_list "dtp_side")
      (foreach value *DT_PANEL_SIDE_VALUES* (add_list (strcat value " mm")))
      (end_list)
      (setq defaultSide (DEG:NUM->STR (DT--last-side-height defaultWidth))
            idx (DEGDO--string-index-ci defaultSide *DT_PANEL_SIDE_VALUES*))
      (set_tile "dtp_side" (itoa (if idx idx 0)))

      (set_tile "dtp_height" (DT--last-tray-height))
      (start_list "dtp_height_pick")
      (add_list "Seciniz")
      (foreach value *DT_PANEL_HEIGHT_VALUES* (add_list value))
      (end_list)
      (set_tile "dtp_height_pick" "0")

      (action_tile "dtp_width" "(DT--panel-width-changed)")
      (action_tile "dtp_height_pick" "(DT--panel-height-picked)")
      (action_tile "draw" "(DT--panel-accept)")
      (action_tile "cancel" "(DT--panel-done 0)")
      (setq rc (start_dialog))
      (unload_dialog dclId)
      (if (/= rc 1) (setq *DT_PANEL_RESULT* nil))
    )
  )
  *DT_PANEL_RESULT*
)

(defun DT--snap-new-point-to-live-route (point pts width / i limit rec cp d best bestD tol)
  ;; Son segment yeni segmente komsudur. Daha eski bir tava kenarina
  ;; tiklanirsa yeni ucu o segmentin merkez hattina tasi.
  (setq i 0
        limit (- (length pts) 2)
        tol (+ (/ width 2.0) 2.0))
  (while (< i limit)
    (setq rec (g365_closest_on_seg point (nth i pts) (nth (1+ i) pts))
          cp  (if rec (car rec))
          d   (if rec (nth 2 rec)))
    (if (and cp (numberp d) (<= d tol) (or (null bestD) (< d bestD)))
      (setq best cp bestD d))
    (setq i (1+ i)))
  (if best
    (DT--point-at-elevation best (DT--active-elevation))
    point)
)

(defun DT--live-self-tee (pts width / rec pt arms tb blk blocks cuts)
  (foreach rec (DT--collect-self-hits pts)
    (setq pt   (car rec)
          arms (DT--arms-at-point pts pt 0.001)
          tb   (DT--t-axis-branch arms))
    (if tb
      (progn
        (setq blk
          (DT--draw-t-fitting
            pt (car tb) (cadr tb) width (DT--layer-fitting)))
        (if blk
          (setq blocks (append blocks (list blk))
                cuts   (append cuts (list (list pt width))))))))
  (list blocks cuts)
)

(defun DT--live-silhouette-clear (/ result)
  (if (and (boundp '*DT_LIVE_SILHOUETTE_TEMP*)
           *DT_LIVE_SILHOUETTE_TEMP*
           (DT--entity-alive-p *DT_LIVE_SILHOUETTE_TEMP*))
    (progn
      ;; This is a temporary native preview entity, not a built tray. Delete it
      ;; directly so tray cleanup cannot leave ERASE or a selection prompt open.
      (setq result
        (vl-catch-all-apply
          'entdel
          (list *DT_LIVE_SILHOUETTE_TEMP*)))
      (if (and (vl-catch-all-error-p result)
               (DT--entity-alive-p *DT_LIVE_SILHOUETTE_TEMP*))
        (vl-catch-all-apply
          'vla-delete
          (list
            (vlax-ename->vla-object *DT_LIVE_SILHOUETTE_TEMP*))))))
  (setq *DT_LIVE_SILHOUETTE_TEMP* nil)
)

(defun DT--live-preview-clear (/ *DT_SUPPRESS_DELETE_HISTORY*)
  ;; Gecici onizleme entity'lerinin handle'larini kalici silme listesine
  ;; doldurma. Uzun cizimde bu liste on binlere cikarak MEMBER sorgularini
  ;; ve her sonraki silme islemini yavaslatiyordu.
  (setq *DT_SUPPRESS_DELETE_HISTORY* T)
  (DT--live-silhouette-clear)
  (DT--live-osnap-guides-clear)
  (if (and (boundp '*DT_LIVE_PREVIEW_PIECES*) *DT_LIVE_PREVIEW_PIECES*)
    (DT--delete-ents *DT_LIVE_PREVIEW_PIECES*))
  (if (and (boundp '*DT_LIVE_PREVIEW_BLOCKS*) *DT_LIVE_PREVIEW_BLOCKS*)
    (DT--delete-ents *DT_LIVE_PREVIEW_BLOCKS*))
  (setq *DT_LIVE_PREVIEW_PIECES* nil
        *DT_LIVE_PREVIEW_BLOCKS* nil)
  (redraw)
)

(defun DT--live-preview-rebuild
  (pts width / build elevation teeBuild teeBlocks teeCuts
    *DT_BUILD_ROUTE_PTS* *DT_BUILD_START_ELEVATION*
    *DT_BUILD_END_ELEVATION* *DT_BUILD_START_TRIM*
    *DT_BUILD_END_TRIM* *DT_BUILD_START_LINE_ELEVATION*
    *DT_BUILD_END_LINE_ELEVATION* *DT_LIVE_PREVIEW_LIGHTWEIGHT*)
  (DT--live-preview-clear)
  (if (and pts (> (length pts) 1) (numberp width) (> width 0.0))
    (progn
      (setq *DT_LIVE_PREVIEW_LIGHTWEIGHT* T
            elevation (DT--active-elevation)
            *DT_BUILD_ROUTE_PTS* pts
            *DT_BUILD_START_ELEVATION* elevation
            *DT_BUILD_END_ELEVATION* elevation
            *DT_BUILD_START_TRIM* 0.0
            *DT_BUILD_END_TRIM* 0.0
            *DT_BUILD_START_LINE_ELEVATION* elevation
            *DT_BUILD_END_LINE_ELEVATION* elevation
            build (DT--build-piecewise-tray pts width)
            *DT_LIVE_PREVIEW_PIECES* (car build)
            *DT_LIVE_PREVIEW_BLOCKS* (cadr build)
            teeBuild (DT--live-self-tee pts width)
            teeBlocks (car teeBuild)
            teeCuts (cadr teeBuild))
      (if teeCuts
        (progn
          (DT--delete-ents *DT_LIVE_PREVIEW_PIECES*)
          (setq *DT_LIVE_PREVIEW_PIECES*
            (DT--build-straight-pieces pts width teeCuts))))
      (if teeBlocks
        (setq *DT_LIVE_PREVIEW_BLOCKS*
          (append *DT_LIVE_PREVIEW_BLOCKS* teeBlocks)))
      (DT--live-osnap-guides-rebuild *DT_LIVE_PREVIEW_PIECES*)
      (redraw)))
  (list *DT_LIVE_PREVIEW_PIECES* *DT_LIVE_PREVIEW_BLOCKS*)
)

(defun DT--drawing-osmode (value / os)
  ;; Running OSNAP kapaliysa 16384 biti acik olur. DT boyunca bu biti
  ;; temizle ve tava kenarinda Dik (Perpendicular) yakalamayi etkinlestir.
  (setq os (if (numberp value) value 0))
  (if (/= 0 (logand os 16384))
    (setq os (- os 16384)))
  (logior os 128)
)

(defun DT--drawing-autosnap (value)
  ;; Marker, magnet ve AutoSnap bilgi balonunu DT cizimi boyunca goster.
  (logior (if (numberp value) value 0) 7)
)

(defun DT--drawing-osoptions (value)
  ;; Hatch geometrisini running OSNAP hesabina katma. Canli tava bloklarindaki
  ;; hatchlerin dis kenarda bekleme imleci olusturmasini engeller.
  (logior (if (numberp value) value 0) 1)
)

(defun DT--make-live-osnap-line (a b)
  (if (and a b (> (distance a b) 0.000001))
    (entmakex
      (list
        '(0 . "LINE")
        '(100 . "AcDbEntity")
        (cons 8 (DT--layer-linework))
        '(370 . 30)
        '(100 . "AcDbLine")
        (cons 10 a)
        (cons 11 b))))
)

(defun DT--live-osnap-guides-clear ()
  (if (and (boundp '*DT_LIVE_OSNAP_GUIDES*) *DT_LIVE_OSNAP_GUIDES*)
    (DT--delete-ents *DT_LIVE_OSNAP_GUIDES*))
  (setq *DT_LIVE_OSNAP_GUIDES* nil)
)

(defun DT--live-osnap-guides-rebuild (pieces / tray pts guide)
  (DT--live-osnap-guides-clear)
  (foreach tray pieces
    (setq pts (DT--tray-corner-points-3d tray))
    (if (= (length pts) 4)
      (progn
        ;; Iki uzun kenarin ustune tam cakisan sade LINE hedefleri koy.
        ;; Cizim bitince silinir; tavada kalici veya gorunur ek olusturmaz.
        (setq guide (DT--make-live-osnap-line (nth 0 pts) (nth 1 pts)))
        (if guide
          (setq *DT_LIVE_OSNAP_GUIDES*
            (append *DT_LIVE_OSNAP_GUIDES* (list guide))))
        (setq guide (DT--make-live-osnap-line (nth 3 pts) (nth 2 pts)))
        (if guide
          (setq *DT_LIVE_OSNAP_GUIDES*
            (append *DT_LIVE_OSNAP_GUIDES* (list guide)))))))
  *DT_LIVE_OSNAP_GUIDES*
)

(defun DT--curve-endpoint-wcs (ent / ed typ item point elevation node result)
  (if (and ent (setq ed (entget ent)))
    (progn
      (setq typ (cdr (assoc 0 ed)))
      (cond
        ((= typ "LWPOLYLINE")
          (setq elevation
            (if (numberp (cdr (assoc 38 ed)))
              (cdr (assoc 38 ed))
              0.0))
          (foreach item ed
            (if (= (car item) 10)
              (setq point
                (list
                  (car (cdr item))
                  (cadr (cdr item))
                  elevation))))
          (if point
            (setq result
              (vl-catch-all-apply 'trans (list point ent 0)))))
        ((= typ "POLYLINE")
          (setq node (entnext ent))
          (while (and node
                      (/= (cdr (assoc 0 (entget node))) "SEQEND"))
            (if (= (cdr (assoc 0 (entget node))) "VERTEX")
              (setq point (cdr (assoc 10 (entget node)))))
            (setq node (entnext node)))
          (if point
            (setq result
              (vl-catch-all-apply 'trans (list point ent 0)))))
        (T
          (setq result
            (vl-catch-all-apply
              'vlax-curve-getEndPoint
              (list ent)))))
      (if (vl-catch-all-error-p result) nil result))
  )
)

(defun DT--new-polyline-after (before / ent ed typ found)
  ;; ENTLAST is unreliable when a legacy POLYLINE owns vertex subentities.
  ;; Walk everything added after the saved boundary and keep the newest parent.
  (setq ent
    (if before
      (entnext before)
      (entnext)))
  (while ent
    (setq ed  (entget ent)
          typ (if ed (cdr (assoc 0 ed)) nil))
    (if (member typ '("LWPOLYLINE" "POLYLINE"))
      (setq found ent))
    (setq ent (entnext ent)))
  found
)

(defun DT--get-live-silhouette-point
  (base width / before after endpoint result oldLayer oldPlineWidth oldPlineType
    oldElevationVar targetLayer baseUcs previewElevation)
  ;; Native wide PLINE preview preserves AutoCAD's own OSNAP markers, tracking
  ;; and perpendicular acquisition. The temporary entity is deleted as soon as
  ;; the point is accepted, before the real live tray segment is rebuilt.
  (setq oldLayer      (getvar "CLAYER")
        oldPlineWidth (getvar "PLINEWID")
        oldPlineType  (getvar "PLINETYPE")
        oldElevationVar (getvar "ELEVATION")
        targetLayer   (DT--layer-linework)
        baseUcs       (trans base 0 1)
        previewElevation
          (if (and baseUcs (numberp (caddr baseUcs)))
            (caddr baseUcs)
            0.0))
  (DT--live-silhouette-clear)
  (setq before (entlast))
  ;; Eski tip POLYLINE'da ENTLAST yeni ana entity yerine onceki entityyi
  ;; dondurebilir. Canli siluet daima LWPOLYLINE olsun; kullanici ayari korunur.
  (if (numberp oldPlineType) (setvar "PLINETYPE" 2))
  (if (numberp previewElevation) (setvar "ELEVATION" previewElevation))
  (if (and targetLayer (/= targetLayer ""))
    (progn
      (DT--ensure-layer
        targetLayer
        (DT--layer-color-for-name targetLayer)
        nil)
      (setvar "CLAYER" targetLayer)))
  (princ "\nDT: Sonraki noktayi tikla <Enter=bitir>: ")
  (setq result
    (vl-catch-all-apply
      'vl-cmdf
      (list
        "_.PLINE"
        "_non" baseUcs
        "_Width" width width
        pause)))
  ;; A picked point leaves PLINE active; Enter already terminates it. Sending
  ;; another Enter after an empty pick would repeat the previous command.
  (if (wcmatch (strcase (getvar "CMDNAMES")) "*PLINE*")
    (vl-catch-all-apply 'vl-cmdf (list "")))
  (setq after (DT--new-polyline-after before))
  (if (and after
           (not (eq after before))
           (DT--entity-alive-p after))
    (setq *DT_LIVE_SILHOUETTE_TEMP* after
          *DT_LIVE_SILHOUETTE_LAST_ELEVATION*
            (DT--entity-elevation after)))
  (if (and *DT_LIVE_SILHOUETTE_TEMP*
           (not (vl-catch-all-error-p result)))
    (progn
      (setq endpoint
        (DT--curve-endpoint-wcs *DT_LIVE_SILHOUETTE_TEMP*))
      (if (or (null endpoint)
              (<= (distance base endpoint) 1e-9))
        (setq endpoint nil))))
  (DT--live-silhouette-clear)
  (if (and oldLayer (tblsearch "LAYER" oldLayer))
    (setvar "CLAYER" oldLayer))
  (if (numberp oldPlineWidth)
    (setvar "PLINEWID" oldPlineWidth))
  (if (numberp oldPlineType)
    (setvar "PLINETYPE" oldPlineType))
  (if (numberp oldElevationVar)
    (setvar "ELEVATION" oldElevationVar))
  endpoint
)

(defun DT--draw-center-polyline (defaultWidth defaultMode / first width planWidth mode p q pts ent paletteValues)
  (setq width defaultWidth
        mode (DT--normalize-mode defaultMode)
        *DT_LIVE_SILHOUETTE_LAST_ELEVATION* nil)
  (DT--remember-mode mode)
  (setq first (getpoint "\nDT: Ilk noktayi tikla <Enter=bitir>: "))
  (if (listp first)
    (progn
      ;; GETPOINT returns UCS coordinates; DT stores and builds in WCS.
      (setq first (trans first 1 0))
      (if *DT_PALETTE_ACTIVE*
        (progn
          (setq paletteValues (DT--palette-settings mode width)
                mode          (car paletteValues)
                width         (cadr paletteValues)
                *DT_PALETTE_SIDE_HEIGHT* (caddr paletteValues)
                *DT_PALETTE_TRAY_HEIGHT* (cadddr paletteValues)
                *DT_ACTIVE_ELEVATION_ANGLE*
                  (if (numberp (nth 4 paletteValues))
                    (nth 4 paletteValues)
                    (DT--last-elevation-angle))
                *DT_ACTIVE_3D*
                  (if (nth 5 paletteValues) T nil))
        )
      )
      (setq *DT_ACTIVE_ELEVATION*
        (DT--tray-height-elevation *DT_PALETTE_TRAY_HEIGHT*))
      (setq *DT_ACTIVE_SIDE_HEIGHT_MM* *DT_PALETTE_SIDE_HEIGHT*
            *DT_ACTIVE_SIDE_HEIGHT*
              (DT--plan-side-height *DT_PALETTE_SIDE_HEIGHT*)
            planWidth (DT--plan-width width))
      (setq p first)
    )
  )
  (if p
    (progn
      (setq p (DT--point-at-elevation p (DT--active-elevation)))
      (setq pts (list p))
      (while (setq q (DT--get-live-silhouette-point p planWidth))
        (setq q (DT--point-at-elevation q (DT--active-elevation)))
        (setq q (DT--snap-new-point-to-live-route q pts planWidth))
        (if (> (distance p q) 1e-9)
          (progn
            (setq pts (append pts (list q)))
            (DT--live-preview-rebuild pts planWidth)
            (setq p q)
          )
        )
      )
      (DT--live-preview-clear)
      (if (> (length pts) 1)
        (setq ent (DT--make-poly (DT--layer-center) pts nil))
      )
    )
  )
  (list ent width mode)
)
(defun DT--add-ent-unique (ent lst / hit e)
  (if (and ent (entget ent))
    (progn
      (foreach e lst
        (if (eq ent e) (setq hit T))
      )
      (if (not hit) (append lst (list ent)) lst)
    )
    lst
  )
)

(defun DT--mode-from-layer (lay / u rec hit)
  (setq u (if lay (strcase (DT--base-layer-name lay)) ""))
  (foreach rec (DT--type-configs)
    (if (= u (strcase (cadr rec))) (setq hit (car rec)))
  )
  (if hit hit (DT--last-mode))
)

(defun DT--activate-layer-mode (lay / mode)
  (setq lay (DT--base-layer-name lay))
  (setq mode (DT--mode-from-layer lay))
  (DT--remember-mode mode)
  (if (and lay (/= lay "")) (setq *DT_ACTIVE_LAYER* lay))
  *DT_ACTIVE_LAYER*
)

(defun DT--pickfirst-selection (/ ss)
  (setq ss (vl-catch-all-apply 'ssget (list "_I")))
  (if (or (vl-catch-all-error-p ss) (null ss)) nil ss)
)

(defun DT--center-layer-p (ent / ed typ lay)
  (if (and ent (setq ed (entget ent)))
    (progn
      (setq typ (cdr (assoc 0 ed))
            lay (cdr (assoc 8 ed)))
      (and (wcmatch typ "LWPOLYLINE,POLYLINE")
           (= (strcase lay) (strcase (DT--layer-center))))
    )
  )
)

(defun DT--center-for-tray (tray / ss i center trays trayItem found)
  (if (and tray (DT--visible-tray-p tray))
    (progn
      (setq ss (ssget "_X" (list (cons 0 "LWPOLYLINE,POLYLINE") (cons 8 (DT--layer-center)))))
      (if ss
        (progn
          (setq i 0)
          (while (and (< i (sslength ss)) (null found))
            (setq center (ssname ss i))
            (if (and (DT--entity-alive-p center) (DT--active-center-p center))
              (progn
                (setq trays (DT--linked-trays center))
                (foreach trayItem trays
                  (if (eq tray trayItem) (setq found center))
                )
              )
            )
            (setq i (1+ i))
          )
        )
      )
    )
  )
  found
)

(defun DT--selected-info (ss / i ent ed typ center centers fittings looseTrays ladders)
  (if (and ss (= (type ss) 'PICKSET))
    (progn
      (setq i 0)
      (while (< i (sslength ss))
        (setq ent (ssname ss i)
              ed  (if ent (entget ent '("DT_FITTING")) nil)
              typ (if ed (cdr (assoc 0 ed)) nil))
        (cond
          ((DT--ladder-meta ent)
            (setq ladders (DT--add-ladder-unique ent ladders)))
          ((DT--center-layer-p ent)
            (setq centers (DT--add-ent-unique ent centers)))
          ((DT--visible-tray-p ent)
            (setq center (DT--center-for-tray ent))
            (if center
              (setq centers (DT--add-ent-unique center centers))
              (setq looseTrays (DT--add-ent-unique ent looseTrays))
            ))
          ((and (= typ "INSERT") (DT--fitting-insert-p ent))
            (setq fittings (DT--add-ent-unique ent fittings)))
        )
        (setq i (1+ i))
      )
    )
  )
  (list centers fittings looseTrays ladders)
)

(defun DT--palette-tray-width (tray / pts p0 p1 p2)
  (setq pts (if tray (g365_get_pts tray) nil))
  (if (and pts (>= (length pts) 4))
    (progn
      (setq p0 (nth 0 pts)
            p1 (nth 1 pts)
            p2 (nth 2 pts))
      (min (DT--distance-xy p0 p1) (DT--distance-xy p1 p2))
    )
  )
)

(defun DT--palette-height-text (ent meta / value)
  (setq value
    (if (and meta (= (type (nth 3 meta)) 'STR)
             (/= (vl-string-trim " \t\r\n" (nth 3 meta)) ""))
      (nth 3 meta)
      (rtos (DT--entity-elevation ent) 2 4)))
  (vl-string-trim " \t\r\n" value)
)

(defun DT--palette-center-record (center / meta lay mode width nominal side height)
  (if (and center (entget center))
    (progn
      (setq meta    (DT--tray-meta center)
            lay     (DT--center-layer center (DT--mode-layer (DT--last-mode)))
            mode    (if (and meta (car meta)) (car meta) (DT--mode-from-layer lay))
            width   (DT--center-width center (DT--plan-width (DT--last-width)))
            nominal (if (and meta (numberp (cadr meta)) (> (cadr meta) 0.0))
                      (cadr meta)
                      (DT--nominal-from-plan-width width))
            side    (if (and meta (numberp (caddr meta)) (> (caddr meta) 0.0))
                      (caddr meta)
                      (DTT--side-height-mm nominal))
            height  (DT--palette-height-text center meta))
      (list
        (DT--normalize-mode mode)
        (rtos nominal 2 0)
        (rtos side 2 0)
        height
        ""
        (if (DT--entity-3d-enabled-p center) "1" "0"))
    )
  )
)

(defun DT--palette-loose-record (tray / meta lay mode width nominal side height)
  (if (and tray (DT--visible-tray-p tray))
    (progn
      (setq meta    (DT--tray-meta-effective tray)
            lay     (cdr (assoc 8 (entget tray)))
            mode    (if (and meta (car meta)) (car meta) (DT--mode-from-layer lay))
            width   (DT--palette-tray-width tray)
            nominal (if (and meta (numberp (cadr meta)) (> (cadr meta) 0.0))
                      (cadr meta)
                      (DT--nominal-from-plan-width width))
            side    (if (and meta (numberp (caddr meta)) (> (caddr meta) 0.0))
                      (caddr meta)
                      (DTT--side-height-mm nominal))
            height  (DT--palette-height-text tray meta))
      (list
        (DT--normalize-mode mode)
        (rtos nominal 2 0)
        (rtos side 2 0)
        height
        ""
        (if (DT--entity-3d-enabled-p tray) "1" "0"))
    )
  )
)

(defun DT--palette-ladder-record (ladder / meta)
  (setq meta (DT--ladder-meta ladder))
  (if meta
    (list
      (DT--normalize-mode (nth 0 meta))
      (rtos (nth 1 meta) 2 0)
      (rtos (nth 2 meta) 2 0)
      (DEG:NUM->STR (nth 3 meta))
      (DEG:NUM->STR (nth 4 meta))
      ""))
)

(defun DT--palette-fitting-record (fitting)
  (if (and fitting (DT--fitting-insert-p fitting))
    (list "" "" "" "" "" (if (DT--fitting-3d-enabled-p fitting) "1" "0")))
)

(defun DT--palette-selection-records (ss / info records center fitting tray ladder rec)
  (setq info (DT--selected-info ss))
  (foreach center (car info)
    (setq rec (DT--palette-center-record center))
    (if rec (setq records (append records (list rec))))
  )
  (foreach tray (caddr info)
    (setq rec (DT--palette-loose-record tray))
    (if rec (setq records (append records (list rec))))
  )
  (foreach fitting (cadr info)
    (setq rec (DT--palette-fitting-record fitting))
    (if rec (setq records (append records (list rec))))
  )
  (foreach ladder (nth 3 info)
    (setq rec (DT--palette-ladder-record ladder))
    (if rec (setq records (append records (list rec))))
  )
  records
)

(defun DT--palette-common-field (records index / value mixed rec current)
  (if records
    (progn
      (setq value (nth index (car records)))
      (foreach rec (cdr records)
        (setq current (nth index rec))
        (if (/= (strcase (if value value "")) (strcase (if current current "")))
          (setq mixed T)
        )
      )
      (if mixed "" (if value value ""))
    )
    ""
  )
)

(defun DT--palette-next-selection-rev ()
  (setq *DT_PALETTE_SELECTION_REV*
    (1+ (if (and (boundp '*DT_PALETTE_SELECTION_REV*)
                 (numberp *DT_PALETTE_SELECTION_REV*))
          *DT_PALETTE_SELECTION_REV*
          0)))
  (itoa *DT_PALETTE_SELECTION_REV*)
)

(defun DT--palette-publish-selection (ss / rec path state records active)
  (if (not *DT_PALETTE_SELECTION_BUSY*)
    (progn
      (setq rec (DT--palette-open-state))
      (if rec
        (progn
          (setq path  (car rec)
                state (cadr rec))
          (if (= (strcase (if (DT--palette-state-get "CONTEXT" state)
                             (DT--palette-state-get "CONTEXT" state) ""))
                 "SELECT")
            (progn
              (setq records (DT--palette-selection-records ss)
                    active (if records "1" "0")
                    state (DT--palette-state-put "SELECTION_ACTIVE" active state)
                    state (DT--palette-state-put "SELECTION_COUNT" (itoa (length records)) state)
                    state (DT--palette-state-put "SELECTION_MODE" (DT--palette-common-field records 0) state)
                    state (DT--palette-state-put "SELECTION_WIDTH" (DT--palette-common-field records 1) state)
                    state (DT--palette-state-put "SELECTION_SIDE" (DT--palette-common-field records 2) state)
                    state (DT--palette-state-put "SELECTION_HEIGHT" (DT--palette-common-field records 3) state)
                    state (DT--palette-state-put "SELECTION_LADDER_BOTTOM" (DT--palette-common-field records 4) state)
                    state (DT--palette-state-put "SELECTION_3D" (DT--palette-common-field records 5) state)
                    state (DT--palette-state-put "SELECTION_REV" (DT--palette-next-selection-rev) state))
              (DT--palette-state-write path state)
            )
          )
        )
      )
    )
  )
)

(defun DT--palette-publish-current-selection ()
  (DT--palette-publish-selection (DT--pickfirst-selection))
)

(defun DT--palette-pickfirst-modified (reactor params)
  (if (not *DT_PALETTE_SELECTION_BUSY*)
    (vl-catch-all-apply 'DT--palette-publish-current-selection '()))
  (princ)
)

(defun DT--reset-palette-selection-reactor ()
  (if (and (boundp '*DT_PALETTE_SELECTION_REACTOR*)
           *DT_PALETTE_SELECTION_REACTOR*)
    (vl-catch-all-apply 'vlr-remove (list *DT_PALETTE_SELECTION_REACTOR*)))
  (setq *DT_PALETTE_SELECTION_REACTOR*
    (vl-catch-all-apply
      'vlr-miscellaneous-reactor
      (list nil
        (list
          (cons :vlr-pickfirstModified 'DT--palette-pickfirst-modified)))))
  (if (vl-catch-all-error-p *DT_PALETTE_SELECTION_REACTOR*)
    (setq *DT_PALETTE_SELECTION_REACTOR* nil))
  *DT_PALETTE_SELECTION_REACTOR*
)

(defun DT--selection-has-resizable-p (ss / info)
  (setq info (DT--selected-info ss))
  (or (car info) (cadr info) (caddr info) (nth 3 info))
)

(defun DT--prompt-resize-width (/ s w done)
  (while (not done)
    (setq s (getstring T "\nDT: Secili tava/donus elemanlari icin yeni genislik girin <iptal=Enter>: "))
    (cond
      ((= (vl-string-trim " \t\r\n" s) "")
        (setq done T w nil))
      ((setq w (DT--parse-width s))
        (setq done T))
      (T
        (princ "\nDT: Genislik 10, 20, 30, 40 veya 50 olmali."))
    )
  )
  w
)

(defun DT--resize-center-to-width (center width / oldActive oldMode oldElevation lay oldWidth pieces meta nominal *DT_REBUILD_SOURCE_WIDTH*)
  (if (and center (entget center) (numberp width) (> width 0.0))
    (progn
      (setq oldActive    *DT_ACTIVE_LAYER*
            oldMode      *DT_ACTIVE_MODE*
            oldElevation (DT--active-elevation)
            *DT_ACTIVE_ELEVATION* (DT--entity-elevation center)
            lay       (DT--center-layer center *DT_ACTIVE_LAYER*)
            oldWidth  (DT--center-width center width)
            meta      (DT--tray-meta center))
      (DT--activate-layer-mode lay)
      (DT--set-center-width center width)
      (setq *DT_REBUILD_SOURCE_WIDTH* oldWidth)
      (setq pieces (DT--rebuild-center-pieces center width nil))
      (if meta
        (progn
          (setq nominal (DT--nominal-from-plan-width width))
          (DT--set-tray-meta center pieces nil (car meta) nominal (caddr meta) (cadddr meta))
        )
      )
      (setq *DT_ACTIVE_LAYER* oldActive
            *DT_ACTIVE_MODE*  oldMode
            *DT_ACTIVE_ELEVATION* oldElevation)
      (if pieces T nil)
    )
  )
)

(defun DT--resize-loose-visible-tray (tray width / oldActive oldMode oldElevation oldSide oldSideMm oldActive3d tray3d sideMm lay seg newTray meta nominal)
  (if (and tray (DT--visible-tray-p tray) (numberp width) (> width 0.0))
    (progn
      (setq oldActive    *DT_ACTIVE_LAYER*
            oldMode      *DT_ACTIVE_MODE*
            oldElevation (DT--active-elevation)
            oldSide      (DT--active-side-height)
            oldSideMm    (DT--active-side-height-mm)
            oldActive3d  (DT--active-3d-enabled-p)
            tray3d       (DT--entity-3d-enabled-p tray)
            *DT_ACTIVE_ELEVATION* (DT--entity-elevation tray)
            lay       (cdr (assoc 8 (entget tray)))
            seg       (DT--tray-center-seg tray)
            meta      (DT--tray-meta tray))
      (setq sideMm (if (and meta (numberp (caddr meta)) (> (caddr meta) 0.0))
                     (caddr meta)
                     oldSideMm)
            *DT_ACTIVE_SIDE_HEIGHT_MM* sideMm
            *DT_ACTIVE_SIDE_HEIGHT* (DT--plan-side-height sideMm)
            *DT_ACTIVE_3D* tray3d)
      (DT--activate-layer-mode lay)
      (if (and seg (> (distance (car seg) (cadr seg)) 0.001))
        (progn
          (setq newTray (DT--make-straight-piece (car seg) (cadr seg) width))
          (if newTray
            (progn
              (if meta
                (progn
                  (setq nominal (DT--nominal-from-plan-width width))
                  (DT--set-tray-meta-one newTray (car meta) nominal (caddr meta) (cadddr meta))
                )
              )
              (DT--set-entity-3d-mode newTray tray3d)
              (DT--safe-delete-ent tray)
              (setq tray newTray)
            )
          )
        )
      )
      (setq *DT_ACTIVE_LAYER* oldActive
            *DT_ACTIVE_MODE*  oldMode
            *DT_ACTIVE_ELEVATION* oldElevation
            *DT_ACTIVE_SIDE_HEIGHT* oldSide
            *DT_ACTIVE_SIDE_HEIGHT_MM* oldSideMm
            *DT_ACTIVE_3D* oldActive3d)
      (if newTray T nil)
    )
  )
)

(defun DT--fitting-kind (ent / ed xd rec x kind)
  (if (and ent (entget ent))
    (progn
      (setq ed (entget ent '("DT_FITTING"))
            xd (assoc -3 ed))
      (if xd
        (progn
          (setq rec (cadr xd))
          (foreach x (cdr rec)
            (if (= (car x) 1000) (setq kind (cdr x)))
          )
        )
      )
    )
  )
  kind
)

(defun DT--assoc-real (code ed def / rec)
  (setq rec (assoc code ed))
  (if (and rec (numberp (cdr rec))) (cdr rec) def)
)

(defun DT--subst-or-append (pair ed / old)
  (setq old (assoc (car pair) ed))
  (if old
    (subst pair old ed)
    (append ed (list pair))
  )
)

(defun DT--resize-fitting-insert (ent width / oldWidth factor ed sx sy sz kind meta nominal)
  (if (and ent
           (entget ent)
           (= (cdr (assoc 0 (entget ent))) "INSERT")
           (DT--fitting-insert-p ent)
           (numberp width)
           (> width 0.0))
    (progn
      (setq oldWidth (DT--fitting-insert-width ent width)
            meta     (DT--tray-meta ent))
      (if (<= oldWidth 0.0) (setq oldWidth width))
      (setq factor (/ width oldWidth)
            ed     (entget ent '("*"))
            sx     (DT--assoc-real 41 ed 1.0)
            sy     (DT--assoc-real 42 ed 1.0)
            sz     (DT--assoc-real 43 ed 1.0))
      (setq ed (DT--subst-or-append (cons 41 (* sx factor)) ed))
      (setq ed (DT--subst-or-append (cons 42 (* sy factor)) ed))
      (setq ed (DT--subst-or-append (cons 43 (* sz factor)) ed))
      (entmod ed)
      (entupd ent)
      (setq kind (DT--fitting-kind ent))
      (DT--mark-fitting-insert ent kind width)
      (if meta
        (progn
          (setq nominal (DT--nominal-from-plan-width width))
          (DT--set-tray-meta-one ent (car meta) nominal (caddr meta) (cadddr meta))
        )
      )
      T
    )
  )
)

(defun DT--resize-selected (ss width / info centers fittings looseTrays c f trayCount center fit tray)
  (setq info       (DT--selected-info ss)
        centers    (car info)
        fittings   (cadr info)
        looseTrays (caddr info)
        c 0
        f 0
        trayCount 0)
  (foreach center centers
    (if (DT--resize-center-to-width center width) (setq c (1+ c)))
  )
  (foreach tray looseTrays
    (if (DT--resize-loose-visible-tray tray width) (setq trayCount (1+ trayCount)))
  )
  (foreach fit fittings
    (if (DT--resize-fitting-insert fit width) (setq f (1+ f)))
  )
  (list c f trayCount)
)

(defun DT--route-turn-records (center width / pts corners ss rec expected expectedZ i ent ed ip kind hit out)
  (setq pts     (if center (g365_get_pts center) nil)
        corners (if pts (DT--corner-records pts width) nil)
        ss      (ssget "_X" '((0 . "INSERT"))))
  (foreach rec corners
    (setq expected  (strcase (DT--turn-kind (nth 2 rec) (nth 3 rec)))
          expectedZ (DT--center-elevation-at-point center (nth 1 rec))
          hit       nil
          i         0)
    (if ss
      (while (and (< i (sslength ss)) (null hit))
        (setq ent  (ssname ss i)
              ed   (if ent (entget ent) nil)
              ip   (if ed (cdr (assoc 10 ed)) nil)
              kind (if ent (DT--fitting-kind ent) nil))
        (if (and ip kind
                 (= (strcase kind) expected)
                 (<= (DT--distance-xy ip (nth 1 rec)) 0.01)
                 (equal (if (caddr ip) (caddr ip) 0.0) expectedZ 0.01))
          (setq hit ent)
        )
        (setq i (1+ i))
      )
    )
    (if hit (setq out (append out (list (list (car rec) hit)))))
  )
  out
)

(defun DT--palette-label-records (trays / refs tray ref seg base out)
  (setq refs (DTT--references "e_tava_etiket"))
  (foreach tray trays
    (if (and tray (entget tray))
      (progn
        (setq ref (DTT--reference-for-tray tray refs))
        (if ref
          (progn
            (setq seg  (DTT--tray-center-seg3d tray)
                  base (DTT--vla-point ref 'InsertionPoint))
            (if seg
              (setq out (append out (list (list ref seg base)))))
          )
        )
      )
    )
  )
  out
)

(defun DT--palette-seg-match-score (oldSeg newSeg / a b c d direct reverse)
  (if (and oldSeg newSeg (= (length oldSeg) 2) (= (length newSeg) 2))
    (progn
      (setq a       (car oldSeg)
            b       (cadr oldSeg)
            c       (car newSeg)
            d       (cadr newSeg)
            direct  (+ (distance a c) (distance b d))
            reverse (+ (distance a d) (distance b c)))
      (min direct reverse))
  )
)

(defun DT--palette-best-label-tray (record trays / oldSeg tray newSeg score best bestScore)
  (setq oldSeg (cadr record))
  (foreach tray trays
    (if (and tray (entget tray))
      (progn
        (setq newSeg (DTT--tray-center-seg3d tray)
              score  (DT--palette-seg-match-score oldSeg newSeg))
        (if (and (numberp score)
                 (or (null bestScore) (< score bestScore)))
          (setq best tray bestScore score))
      )
    )
  )
  best
)

(defun DT--palette-remove-ent (ent entities / item out)
  (foreach item entities
    (if (not (eq ent item)) (setq out (cons item out))))
  (reverse out)
)

(defun DT--palette-set-label-base (ref base / result)
  (if (and ref base)
    (progn
      (setq result
        (vl-catch-all-apply
          'vla-put-InsertionPoint
          (list ref (vlax-3d-point base))))
      (not (vl-catch-all-error-p result)))
  )
)

(defun DT--palette-update-label-records (records newTrays / available record ref tray seg oldBase newBase dynPos values updated)
  (setq available newTrays
        updated   0)
  (foreach record records
    (setq ref  (car record)
          tray (DT--palette-best-label-tray record available))
    (if (and ref tray (entget tray) (DTT--reference-ename ref))
      (progn
        (setq seg     (DTT--tray-center-seg3d tray)
              oldBase (caddr record)
              dynPos  (DTT--dynamic-position ref)
              newBase (if oldBase
                        (DTT--project-base-to-segment
                          oldBase seg (DT--entity-elevation tray))
                        (DTT--mid3 (car seg) (cadr seg)))
              values  (DTT--tray-att-values
                        tray (DT--palette-tray-width tray)))
        (DT--palette-set-label-base ref newBase)
        (DTT--set-reference-tray ref tray)
        (DTT--set-reference-att-values ref values)
        (if dynPos
          (DTT--align-reference-atts
            ref "e_tava_etiket" dynPos 0.0))
        (vl-catch-all-apply 'vla-Update (list ref))
        (setq available (DT--palette-remove-ent tray available)
              updated   (1+ updated))
      )
    )
  )
  updated
)

(defun DT--point-on-center-route-p (point center tolerance / pts i rec hit)
  (setq pts (if center (g365_get_pts center)))
  (if (and point pts)
    (progn
      (setq i 0)
      (while (and (< i (1- (length pts))) (null hit))
        (setq rec (g365_closest_on_seg point (nth i pts) (nth (1+ i) pts)))
        (if (and rec (<= (nth 2 rec) tolerance)) (setq hit T))
        (setq i (1+ i)))))
  hit
)

(defun DT--fittings-for-centers (centers / fitting ed point center hit out)
  (foreach fitting (DT--fitting-inserts)
    (setq ed    (if fitting (entget fitting))
          point (if ed (cdr (assoc 10 ed)))
          hit   nil)
    (foreach center centers
      (if (and (null hit)
               point
               (DT--point-on-center-route-p point center 0.05)
               (equal
                 (if (caddr point) (caddr point) 0.0)
                 (DT--center-elevation-at-point center point)
                 0.05))
        (setq hit T)))
    (if hit (setq out (DT--add-ent-unique fitting out))))
  out
)

(defun DT--apply-centers-fitting-3d-mode (centers enabled / fitting)
  (foreach fitting (DT--fittings-for-centers centers)
    (DT--apply-fitting-3d-mode fitting enabled))
)

(defun DT--palette-apply-center (center requestMode requestNominal requestSide requestHeight request3d /
    oldActive oldMode oldElevation oldSide oldSideMm oldActive3d old3d oldWidth oldMeta oldModeValue oldNominal oldSideValue oldHeight
    newMode newNominal newSide newHeight new3d newWidth newZ heightChanged oldTurns oldPieces labelRecords
    pts ends profile pieces newTurns pair newRec
    *DT_REBUILD_SOURCE_WIDTH* *DT_ACTIVE_ELEVATION* *DT_ACTIVE_SIDE_HEIGHT* *DT_ACTIVE_SIDE_HEIGHT_MM*
    *DT_BUILD_ROUTE_PTS* *DT_BUILD_START_ELEVATION* *DT_BUILD_END_ELEVATION*
    *DT_BUILD_START_TRIM* *DT_BUILD_END_TRIM* *DT_BUILD_START_LINE_ELEVATION* *DT_BUILD_END_LINE_ELEVATION*)
  (if (and center (entget center))
    (progn
      (setq oldActive    *DT_ACTIVE_LAYER*
            oldMode      *DT_ACTIVE_MODE*
            oldElevation (DT--active-elevation)
            oldSide      (DT--active-side-height)
            oldSideMm    (DT--active-side-height-mm)
            oldActive3d  (DT--active-3d-enabled-p)
            old3d        (DT--entity-3d-enabled-p center)
            oldWidth     (DT--center-width center (DT--plan-width (DT--last-width)))
            oldMeta      (DT--tray-meta center)
            oldModeValue (if (and oldMeta (car oldMeta))
                           (car oldMeta)
                           (DT--mode-from-layer (DT--center-layer center oldActive)))
            oldNominal   (if (and oldMeta (numberp (cadr oldMeta)) (> (cadr oldMeta) 0.0))
                           (cadr oldMeta)
                           (DT--nominal-from-plan-width oldWidth))
            oldSideValue (if (and oldMeta (numberp (caddr oldMeta)) (> (caddr oldMeta) 0.0))
                           (caddr oldMeta)
                           (DTT--side-height-mm oldNominal))
            oldHeight    (DT--palette-height-text center oldMeta)
            newMode      (if requestMode (DT--normalize-mode requestMode) oldModeValue)
            newNominal   (if (and (numberp requestNominal) (> requestNominal 0.0))
                           requestNominal oldNominal)
            newSide      (if (and (numberp requestSide) (> requestSide 0.0))
                           requestSide oldSideValue)
            new3d        (cond
                           ((= request3d "1") T)
                           ((= request3d "0") nil)
                           (T old3d))
            newHeight    (if (and (= (type requestHeight) 'STR)
                                  (/= (vl-string-trim " \t\r\n" requestHeight) ""))
                           (vl-string-trim " \t\r\n" requestHeight)
                           oldHeight)
            heightChanged (and (= (type requestHeight) 'STR)
                               (/= (vl-string-trim " \t\r\n" requestHeight) ""))
            newWidth     (DT--plan-width newNominal)
            pts          (g365_get_pts center)
            ends         (DT--center-end-elevations center)
            profile      (DT--center-elevation-profile center)
            oldTurns     (DT--route-turn-records center oldWidth)
            oldPieces    (DT--linked-trays center)
            labelRecords (DT--palette-label-records oldPieces))
      (DT--remember-mode newMode)
      (DT--ensure-type-layers)
      (setq *DT_ACTIVE_SIDE_HEIGHT_MM* newSide
            *DT_ACTIVE_SIDE_HEIGHT*    (DT--plan-side-height newSide)
            *DT_ACTIVE_3D*             new3d)
      (if heightChanged
        (progn
          (setq newZ (DT--tray-height-elevation newHeight)
                ends (list newZ newZ)
                profile (list 0.0 0.0 newZ newZ))
          (DT--set-center-base-elevation center newZ)
          (DT--set-center-end-elevations center newZ newZ)
          (DT--set-center-elevation-profile center 0.0 0.0 newZ newZ))
      )
      (setq *DT_ACTIVE_ELEVATION* (car ends))
      (DT--set-center-width center newWidth)
      (DT--set-center-layer center (DT--mode-layer newMode))
      (DT--set-tray-meta-one center newMode newNominal newSide newHeight)
      (DT--set-entity-3d-mode center new3d)
      (foreach pair oldTurns
        (DT--safe-delete-ent (cadr pair)))
      (setq *DT_REBUILD_SOURCE_WIDTH* oldWidth
            pieces
              (DT--rebuild-center-pieces
                center
                newWidth
                (if (eq old3d new3d) nil pts))
            *DT_BUILD_ROUTE_PTS* pts
            *DT_BUILD_START_ELEVATION* (car ends)
            *DT_BUILD_END_ELEVATION*   (cadr ends)
            *DT_BUILD_START_TRIM*      (car profile)
            *DT_BUILD_END_TRIM*        (cadr profile)
            *DT_BUILD_START_LINE_ELEVATION* (if (numberp (nth 2 profile)) (nth 2 profile) (car ends))
            *DT_BUILD_END_LINE_ELEVATION*   (if (numberp (nth 3 profile)) (nth 3 profile) (cadr ends)))
      (foreach pair oldTurns
        (setq newRec (DT--corner-at (DT--corner-records pts newWidth) (car pair)))
        (if newRec
          (progn
            (setq newRec (DT--make-turn-block newRec newWidth))
            (if newRec (setq newTurns (append newTurns (list newRec)))))
        )
      )
      (DT--set-tray-meta center pieces newTurns newMode newNominal newSide newHeight)
      (DT--set-tray-3d-mode center pieces newTurns new3d)
      (DT--apply-centers-fitting-3d-mode (list center) new3d)
      (if (and labelRecords pieces)
        (DT--palette-update-label-records labelRecords pieces))
      (setq *DT_ACTIVE_LAYER* oldActive
            *DT_ACTIVE_MODE* oldMode
            *DT_ACTIVE_ELEVATION* oldElevation
            *DT_ACTIVE_SIDE_HEIGHT* oldSide
            *DT_ACTIVE_SIDE_HEIGHT_MM* oldSideMm
            *DT_ACTIVE_3D* oldActive3d)
      (list pieces newTurns)
    )
  )
)

(defun DT--palette-apply-loose-tray (tray requestMode requestNominal requestSide requestHeight request3d /
    oldActive oldMode oldElevation oldSide oldSideMm oldActive3d old3d oldMeta oldModeValue oldWidth oldNominal oldSideValue oldHeight
    newMode newNominal newSide newHeight new3d newWidth newZ seg newTray labelRecords oldCenter oldOverride
    *DT_ACTIVE_ELEVATION* *DT_ACTIVE_SIDE_HEIGHT* *DT_ACTIVE_SIDE_HEIGHT_MM*
    *DT_BUILD_ROUTE_PTS* *DT_BUILD_START_ELEVATION* *DT_BUILD_END_ELEVATION*
    *DT_BUILD_START_TRIM* *DT_BUILD_END_TRIM* *DT_BUILD_START_LINE_ELEVATION* *DT_BUILD_END_LINE_ELEVATION*)
  (if (and tray (DT--visible-tray-p tray))
    (progn
      (setq oldActive    *DT_ACTIVE_LAYER*
            oldMode      *DT_ACTIVE_MODE*
            oldElevation (DT--active-elevation)
            oldSide      (DT--active-side-height)
            oldSideMm    (DT--active-side-height-mm)
            oldActive3d  (DT--active-3d-enabled-p)
            old3d        (DT--entity-3d-enabled-p tray)
            oldMeta      (DT--tray-meta-effective tray)
            oldModeValue (if (and oldMeta (car oldMeta))
                           (car oldMeta)
                           (DT--mode-from-layer (cdr (assoc 8 (entget tray)))))
            oldWidth     (DT--palette-tray-width tray)
            oldNominal   (if (and oldMeta (numberp (cadr oldMeta)) (> (cadr oldMeta) 0.0))
                           (cadr oldMeta)
                           (DT--nominal-from-plan-width oldWidth))
            oldSideValue (if (and oldMeta (numberp (caddr oldMeta)) (> (caddr oldMeta) 0.0))
                           (caddr oldMeta)
                           (DTT--side-height-mm oldNominal))
            oldHeight    (DT--palette-height-text tray oldMeta)
            newMode      (if requestMode (DT--normalize-mode requestMode) oldModeValue)
            newNominal   (if (and (numberp requestNominal) (> requestNominal 0.0))
                           requestNominal oldNominal)
            newSide      (if (and (numberp requestSide) (> requestSide 0.0))
                           requestSide oldSideValue)
            new3d        (cond
                           ((= request3d "1") T)
                           ((= request3d "0") nil)
                           (T old3d))
            newHeight    (if (and (= (type requestHeight) 'STR)
                                  (/= (vl-string-trim " \t\r\n" requestHeight) ""))
                           (vl-string-trim " \t\r\n" requestHeight)
                           oldHeight)
            newWidth     (DT--plan-width newNominal)
            newZ         (if (and (= (type requestHeight) 'STR)
                                  (/= (vl-string-trim " \t\r\n" requestHeight) ""))
                           (DT--tray-height-elevation newHeight)
                           (DT--entity-elevation tray))
            seg          (DT--tray-center-seg tray)
            labelRecords (DT--palette-label-records (list tray))
            oldCenter    (DT--center-for-tray tray)
            oldOverride  (DT--tray-piece-override-p tray))
      (DT--remember-mode newMode)
      (DT--ensure-type-layers)
      (setq *DT_ACTIVE_ELEVATION* newZ
            *DT_ACTIVE_SIDE_HEIGHT_MM* newSide
            *DT_ACTIVE_SIDE_HEIGHT* (DT--plan-side-height newSide)
            *DT_ACTIVE_3D* new3d
            *DT_BUILD_ROUTE_PTS* seg
            *DT_BUILD_START_ELEVATION* newZ
            *DT_BUILD_END_ELEVATION* newZ
            *DT_BUILD_START_TRIM* 0.0
            *DT_BUILD_END_TRIM* 0.0
            *DT_BUILD_START_LINE_ELEVATION* newZ
            *DT_BUILD_END_LINE_ELEVATION* newZ)
      (if (and seg (> (DT--distance-xy (car seg) (cadr seg)) 0.001))
        (setq newTray (DT--make-straight-piece (car seg) (cadr seg) newWidth)))
      (if newTray
        (progn
          (DT--set-tray-meta-one newTray newMode newNominal newSide newHeight)
          (DT--set-entity-3d-mode newTray new3d)
          (if (or oldCenter oldOverride)
            (DT--set-tray-piece-override newTray))
          (if oldCenter
            (DT--replace-linked-tray oldCenter tray newTray))
          (DT--delete-ents (list tray))
          (if labelRecords
            (DT--palette-update-label-records
              labelRecords (list newTray)))))
      (setq *DT_ACTIVE_LAYER* oldActive
            *DT_ACTIVE_MODE* oldMode
            *DT_ACTIVE_ELEVATION* oldElevation
            *DT_ACTIVE_SIDE_HEIGHT* oldSide
            *DT_ACTIVE_SIDE_HEIGHT_MM* oldSideMm
            *DT_ACTIVE_3D* oldActive3d)
      newTray
    )
  )
)

(defun DT--palette-apply-ladder
  (ladder requestMode requestNominal requestSide requestTop requestBottom /
    oldActive oldMode oldElevation oldSide oldSideMm meta placement base rotation
    newMode newNominal newSide newTop newBottom elevations newLadder)
  (setq meta      (DT--ladder-meta ladder)
        placement (DT--ladder-placement-data ladder))
  (if (and meta placement)
    (progn
      (setq oldActive    *DT_ACTIVE_LAYER*
            oldMode      *DT_ACTIVE_MODE*
            oldElevation (DT--active-elevation)
            oldSide      (DT--active-side-height)
            oldSideMm    (DT--active-side-height-mm)
            base         (car placement)
            rotation     (cadr placement)
            newMode      (if requestMode
                           (DT--normalize-mode requestMode)
                           (nth 0 meta))
            newNominal   (if (and (numberp requestNominal) (> requestNominal 0.0))
                           requestNominal
                           (nth 1 meta))
            newSide      (if (and (numberp requestSide) (> requestSide 0.0))
                           requestSide
                           (nth 2 meta))
            newTop       (if (and (= (type requestTop) 'STR)
                                  (/= (vl-string-trim " \t\r\n" requestTop) ""))
                           (distof (vl-string-translate "," "." requestTop) 2)
                           (nth 3 meta))
            newBottom    (if (and (= (type requestBottom) 'STR)
                                  (/= (vl-string-trim " \t\r\n" requestBottom) ""))
                           (distof (vl-string-translate "," "." requestBottom) 2)
                           (nth 4 meta)))
      (setq elevations (DT--ladder-normalize-elevations newTop newBottom)
            newTop     (car elevations)
            newBottom  (cadr elevations))
      (if (and (DT--find-type newMode)
               (numberp newTop)
               (numberp newBottom)
               (not (equal newTop newBottom 0.000001)))
        (progn
          (setq newLadder
            (DT--make-ladder-composite-at
              base rotation newMode newNominal newSide newTop newBottom))
          (if newLadder
            (progn
              (DT--delete-ladder-composite ladder)
              (DT--remember-mode newMode)
              (DT--remember-width newNominal)
              (DT--remember-side-height newSide)
              (DT--remember-tray-height (DEG:NUM->STR newTop))
              (DT--remember-ladder-bottom (DEG:NUM->STR newBottom)))))
      )
      (setq *DT_ACTIVE_LAYER* oldActive
            *DT_ACTIVE_MODE* oldMode
            *DT_ACTIVE_ELEVATION* oldElevation
            *DT_ACTIVE_SIDE_HEIGHT* oldSide
            *DT_ACTIVE_SIDE_HEIGHT_MM* oldSideMm)
      newLadder
    )
  )
)

(defun DT--palette-selection-set (entities / ss ent)
  (setq ss (ssadd))
  (foreach ent entities
    (if (and ent (entget ent)) (ssadd ent ss)))
  (if (> (sslength ss) 0)
    (progn
      (sssetfirst nil ss)
      ss)
  )
)

(defun DT--palette-apply-selection-values
  (ss mode nominal side height request3d /
    info centers fittings looseTrays ladders center fitting tray ladder result pieces turns
    newTray newLadder changed entities ladderBottom enabled3d)
  ;; COPY/PASTE duplicates XData handles. Normalize those local controller /
  ;; visual pairs before resolving the selected entity.
  (vl-catch-all-apply 'DT--light-repair-tray-copies '())
  (vl-catch-all-apply 'DT--light-repair-ladder-copies '())
  (setq info       (DT--selected-info ss)
        centers    (car info)
        fittings   (cadr info)
        looseTrays (caddr info)
        ladders    (nth 3 info)
        ladderBottom
          (if (and (boundp '*DT_PALETTE_REQUEST_LADDER_BOTTOM*)
                   (= (type *DT_PALETTE_REQUEST_LADDER_BOTTOM*) 'STR))
            *DT_PALETTE_REQUEST_LADDER_BOTTOM*
            "")
        changed    0)
  (foreach center centers
    (setq result (DT--palette-apply-center center mode nominal side height request3d)
          pieces (car result)
          turns  (cadr result))
    (if pieces
      (progn
        (setq changed  (1+ changed)
              entities (append entities pieces turns))))
  )
  (foreach tray looseTrays
    (setq newTray (DT--palette-apply-loose-tray tray mode nominal side height request3d))
    (if newTray
      (setq changed  (1+ changed)
            entities (append entities (list newTray)))))
  (if (member request3d '("0" "1"))
    (progn
      (setq enabled3d (= request3d "1"))
      (foreach fitting fittings
        (if (DT--apply-fitting-3d-mode fitting enabled3d)
          (setq changed  (1+ changed)
                entities (DT--add-ent-unique fitting entities))))))
  (foreach ladder ladders
    (setq newLadder
      (DT--palette-apply-ladder
        ladder mode nominal side height ladderBottom))
    (if newLadder
      (setq changed  (1+ changed)
            entities (append entities (DT--ladder-members newLadder)))))
  (if entities (DT--palette-selection-set entities))
  (list changed entities)
)

(defun DT--palette-request-value (key state / value)
  (setq value (DT--palette-state-get key state))
  (if value (vl-string-trim " \t\r\n" value) "")
)

(defun DT--palette-ladder-finish (path requestId count status / state)
  (if path
    (progn
      (setq state (DT--palette-state-read path)
            state (DT--palette-state-put "CONTEXT" "SELECT" state)
            state (DT--palette-state-put "REQUEST" "" state)
            state (DT--palette-state-put "REQUEST_DONE" (if requestId requestId "") state)
            state (DT--palette-state-put
                    "STATUS"
                    (if status
                      status
                      (strcat (itoa count) " merdiven yerlestirildi."))
                    state))
      (DT--palette-state-write path state)))
  (DT--palette-publish-current-selection)
)

(defun C:DT_PALETTE_LADDER
  (/ *error* oldCmd oldMode oldLayer oldElevation oldSide oldSideMm
    rec path state requestId modeText mode widthText nominal sideText side
    topText bottomText topElevation bottomElevation xAxis rotation point base
    elevations count valid)
  (vl-load-com)
  (setq oldCmd       (getvar "CMDECHO")
        oldMode      *DT_ACTIVE_MODE*
        oldLayer     *DT_ACTIVE_LAYER*
        oldElevation (DT--active-elevation)
        oldSide      (DT--active-side-height)
        oldSideMm    (DT--active-side-height-mm)
        count        0)
  (defun *error* (msg)
    (setvar "CMDECHO" oldCmd)
    (setq *DT_ACTIVE_MODE* oldMode
          *DT_ACTIVE_LAYER* oldLayer
          *DT_ACTIVE_ELEVATION* oldElevation
          *DT_ACTIVE_SIDE_HEIGHT* oldSide
          *DT_ACTIVE_SIDE_HEIGHT_MM* oldSideMm)
    (DT--palette-ladder-finish
      path requestId count
      (if (and msg (not (wcmatch (strcase msg) "*CANCEL*,*QUIT*,*BREAK*")))
        (strcat "Merdiven hata: " msg)
        nil))
    (if (and msg (not (wcmatch (strcase msg) "*CANCEL*,*QUIT*,*BREAK*")))
      (princ (strcat "\nDT merdiven hata: " msg)))
    (princ))
  (setvar "CMDECHO" 0)
  (setq rec (DT--palette-open-state))
  (if rec
    (progn
      (setq path            (car rec)
            state           (cadr rec)
            requestId       (DT--palette-state-get "REQUEST_ID" state)
            modeText        (DT--palette-request-value "MODE" state)
            mode            (if (DT--find-type modeText) (DT--normalize-mode modeText) nil)
            widthText       (DT--palette-request-value "WIDTH" state)
            nominal         (if (/= widthText "") (DT--parse-width widthText) nil)
            sideText        (DT--palette-request-value "SIDE" state)
            side            (if (/= sideText "")
                              (atof (vl-string-translate "," "." sideText)) nil)
            topText         (DT--palette-request-value "HEIGHT" state)
            bottomText      (DT--palette-request-value "LADDER_BOTTOM" state)
            topElevation    (if (/= topText "")
                              (distof (vl-string-translate "," "." topText) 2) nil)
            bottomElevation (if (/= bottomText "")
                              (distof (vl-string-translate "," "." bottomText) 2) nil))
      (setq elevations     (DT--ladder-normalize-elevations
                             topElevation bottomElevation)
            topElevation    (car elevations)
            bottomElevation (cadr elevations)
            topText         (if (numberp topElevation)
                              (DEG:NUM->STR topElevation) topText)
            bottomText      (if (numberp bottomElevation)
                              (DEG:NUM->STR bottomElevation) bottomText)
            valid           (and mode nominal side (> side 0.0)
                                 (numberp topElevation)
                                 (numberp bottomElevation)
                                 (not (equal topElevation bottomElevation 0.000001))))
      (if valid
        (progn
          (DT--remember-mode mode)
          (DT--remember-width nominal)
          (DT--remember-side-height side)
          (DT--remember-tray-height topText)
          (DT--remember-ladder-bottom bottomText)
          (setq state (DT--palette-state-put "HEIGHT" topText state)
                state (DT--palette-state-put "LADDER_BOTTOM" bottomText state)
                state (DT--palette-state-put "CONTEXT" "LADDER" state)
                state (DT--palette-state-put
                        "STATUS"
                        "Merdiven yerlesimi aktif: noktaya tiklayin, ESC ile bitirin."
                        state))
          (DT--palette-state-write path state)
          (DT--ensure-composite-pickstyle)
          (setq xAxis (trans '(1.0 0.0 0.0) 1 0 T)
                rotation (atan (cadr xAxis) (car xAxis)))
          (while
            (setq point
              (getpoint
                "\nDT Merdiven: ust noktanin plan konumunu tikla <Enter/ESC=bitir>: "))
            (setq base (trans point 1 0))
            (if (DT--make-ladder-composite-at
                  base rotation mode nominal side topElevation bottomElevation)
              (progn
                (setq count (1+ count))
                (princ (strcat "\nDT Merdiven: " (itoa count) " adet yerlestirildi.")))))
          (DT--palette-ladder-finish path requestId count nil))
        (DT--palette-ladder-finish
          path requestId count
          "Merdiven icin tip, genislik, yanak ve farkli ust/alt yukseklik girilmelidir.")))
    (princ "\nDT paleti acik degil."))
  (setvar "CMDECHO" oldCmd)
  (setq *DT_ACTIVE_MODE* oldMode
        *DT_ACTIVE_LAYER* oldLayer
        *DT_ACTIVE_ELEVATION* oldElevation
        *DT_ACTIVE_SIDE_HEIGHT* oldSide
        *DT_ACTIVE_SIDE_HEIGHT_MM* oldSideMm)
  (princ)
)

(defun C:DT_PALETTE_APPLY
  (/ *error* rec path state ss modeText mode widthText nominal sideText side
    height ladderBottom threeDText requestId result status info
    *DT_PALETTE_REQUEST_LADDER_BOTTOM*)
  (vl-load-com)
  (defun *error* (msg)
    (setq *DT_PALETTE_SELECTION_BUSY* nil)
    (if (and msg (not (wcmatch (strcase msg) "*CANCEL*,*QUIT*,*BREAK*")))
      (princ (strcat "\nDT palet hata: " msg)))
    (princ))
  (setq *DT_PALETTE_SELECTION_BUSY* T
        rec (DT--palette-open-state))
  (if rec
    (progn
      (vl-catch-all-apply 'DT--light-repair-tray-copies '())
      (vl-catch-all-apply 'DT--light-repair-ladder-copies '())
      (setq path      (car rec)
            state     (cadr rec)
            requestId (DT--palette-state-get "REQUEST_ID" state)
            ss        (DT--pickfirst-selection)
            modeText  (DT--palette-request-value "MODE" state)
            mode      (if (DT--find-type modeText) (DT--normalize-mode modeText) nil)
            widthText (DT--palette-request-value "WIDTH" state)
            nominal   (if (/= widthText "") (DT--parse-width widthText) nil)
            sideText  (DT--palette-request-value "SIDE" state)
            side      (if (/= sideText "")
                         (atof (vl-string-translate "," "." sideText)) nil)
             height    (DT--palette-request-value "HEIGHT" state)
             ladderBottom (DT--palette-request-value "LADDER_BOTTOM" state)
             threeDText (DT--palette-request-value "REQUEST_3D" state)
             info       (if ss (DT--selected-info ss)))
      (cond
        ((or (null ss) (null (DT--palette-selection-records ss)))
          (setq status "Secili DT tava veya merdiveni bulunamadi."))
        ((and (/= widthText "") (null nominal))
          (setq status "Gecersiz tava genisligi."))
        ((and (/= sideText "") (or (null side) (<= side 0.0)))
          (setq status "Gecersiz yanak yuksekligi."))
        ((and (/= height "")
              (null (distof (vl-string-translate "," "." height) 2)))
          (setq status "Gecersiz tava yuksekligi."))
        ((and (/= ladderBottom "")
              (null (distof (vl-string-translate "," "." ladderBottom) 2)))
          (setq status "Gecersiz merdiven alt yuksekligi."))
        (T
          (setq *DT_PALETTE_REQUEST_LADDER_BOTTOM* ladderBottom
                result
                  (DT--palette-apply-selection-values
                    ss mode nominal side height threeDText)
                status
                  (strcat
                    (itoa (car result))
                    (if (nth 3 info)
                      " DT elemani guncellendi."
                      " tava guncellendi."))))
      )
      (setq state (DT--palette-state-read path)
            state (DT--palette-state-put "REQUEST" "" state)
            state (DT--palette-state-put "REQUEST_3D" "" state)
            state (DT--palette-state-put "REQUEST_DONE" (if requestId requestId "") state)
            state (DT--palette-state-put "STATUS" status state))
      (DT--palette-state-write path state)
      (princ (strcat "\nDT palet: " status))
    )
    (princ "\nDT paleti acik degil."))
  (setq *DT_PALETTE_SELECTION_BUSY* nil)
  (DT--palette-publish-current-selection)
  (princ)
)

(defun DT--apply-global-3d-mode
  (enabled / oldBusy center tray fitting trayCount fittingCount result)
  (setq oldBusy
    (if (and (boundp '*DT_SIDEWALL_SYNC_BUSY*) *DT_SIDEWALL_SYNC_BUSY*)
      T nil))
  (setq *DT_SIDEWALL_SYNC_BUSY* T)
  (DT--remember-3d-enabled enabled)
  ;; Keep hidden route controllers authoritative so later STRETCH/rebuild
  ;; operations retain the globally selected display mode.
  (foreach center (DT--collect-center-entities-raw)
    (DT--set-entity-3d-mode center enabled))
  (foreach tray (DT--light-all-trays)
    (if (and tray (DT--entity-alive-p tray))
      (progn
        (DT--set-entity-3d-mode tray enabled)
        (setq result
          (vl-catch-all-apply 'DT--light-migrate-tray (list tray)))
        (if (not (vl-catch-all-error-p result))
          (setq trayCount (1+ (if trayCount trayCount 0)))))))
  (foreach fitting (DT--collect-fitting-inserts)
    (setq result
      (vl-catch-all-apply
        'DT--apply-fitting-3d-mode (list fitting enabled)))
    (if (and (not (vl-catch-all-error-p result)) result)
      (setq fittingCount (1+ (if fittingCount fittingCount 0)))))
  (setq *DT_SIDEWALL_SYNC_BUSY* oldBusy)
  (redraw)
  (list
    (if trayCount trayCount 0)
    (if fittingCount fittingCount 0))
)

(defun C:DT_PALETTE_GLOBAL_3D
  (/ *error* rec path state requestId enabled result status oldBusy)
  (vl-load-com)
  (setq oldBusy
    (if (and (boundp '*DT_SIDEWALL_SYNC_BUSY*) *DT_SIDEWALL_SYNC_BUSY*)
      T nil))
  (defun *error* (msg)
    (setq *DT_SIDEWALL_SYNC_BUSY* oldBusy)
    (if path
      (progn
        (setq state (DT--palette-state-read path)
              state (DT--palette-state-put "REQUEST" "" state)
              state (DT--palette-state-put "REQUEST_DONE" (if requestId requestId "") state)
              state
                (DT--palette-state-put
                  "STATUS"
                  (if msg (strcat "3D gorunum hatasi: " msg) "3D gorunum hatasi.")
                  state))
        (DT--palette-state-write path state)))
    (princ))
  (setq rec (DT--palette-open-state))
  (if rec
    (progn
      (setq path      (car rec)
            state     (cadr rec)
            requestId (DT--palette-state-get "REQUEST_ID" state)
            enabled   (/= (DT--palette-state-get "THREE_D" state) "0")
            result    (DT--apply-global-3d-mode enabled)
            status
              (strcat
                (itoa (car result)) " tava ve "
                (itoa (cadr result)) " baglanti elemani "
                (if enabled "3D" "2D") " gorunume cevrildi.")
            state     (DT--palette-state-read path)
            state     (DT--palette-state-put "REQUEST" "" state)
            state     (DT--palette-state-put "REQUEST_3D" "" state)
            state     (DT--palette-state-put "REQUEST_DONE" (if requestId requestId "") state)
            state     (DT--palette-state-put "STATUS" status state))
      (DT--palette-state-write path state)
      (princ (strcat "\nDT palet: " status)))
    (princ "\nDT paleti acik degil."))
  (princ)
)

(defun DT--resize-selection-flow (ss / inputWidth width res)
  (setq inputWidth (DT--prompt-resize-width))
  (if inputWidth
    (progn
      (DT--remember-width inputWidth)
      (setq width (DT--plan-width inputWidth))
      (setq res (DT--resize-selected ss width))
      (sssetfirst nil nil)
      (princ
        (strcat
          "\nDT genislik degisti: "
          (rtos inputWidth 2 0)
          " nominal / planda " (rtos width 2 2) ", "
          (itoa (car res)) " tava grubu, "
          (itoa (caddr res)) " tek tava, "
          (itoa (cadr res)) " donus elemani."
        )
      )
      res
    )
    (progn
      (princ "\nDT: Genislik girilmedi, islem iptal.")
      nil
    )
  )
)

(defun DT--full-maintenance (/ started)
  (setq started (getvar "MILLISECS"))
  (DT--ensure-type-layers)
  (vl-catch-all-apply 'DT--repair-existing-tray-line-layers '())
  (vl-catch-all-apply 'DT--repair-existing-fitting-line-layers '())
  (vl-catch-all-apply 'DT--cleanup-fitting-block-inner-lines '())
  (vl-catch-all-apply 'DT--repair-existing-hatch-associations '())
  (vl-catch-all-apply 'DT--remove-generated-tray-groups '())
  (vl-catch-all-apply 'DT--repair-existing-tray-sidewalls '())
  (vl-catch-all-apply 'DT--repair-existing-tray-groups '())
  (vl-catch-all-apply 'DT--light-repair-tray-copies '())
  (vl-catch-all-apply 'DT--light-clean-orphan-tray-visuals '())
  (vl-catch-all-apply 'DT--light-repair-tray-meta-from-centers '())
  (vl-catch-all-apply 'DT--light-migrate-all-ladders '())
  (vl-catch-all-apply 'DT--light-repair-ladder-copies '())
  (vl-catch-all-apply 'DT--remove-center-display-copies '())
  (DT--ensure-composite-pickstyle)
  (vl-catch-all-apply 'setvar (list "GRIPOBJLIMIT" 100))
  (princ
    (strcat
      "\nDTBAKIM tamamlandi. Sure: "
      (rtos (/ (- (getvar "MILLISECS") started) 1000.0) 2 2)
      " sn."))
  T
)

(defun C:DTBAKIM ()
  (vl-load-com)
  (princ "\nDTBAKIM: Mevcut tava, hatch, block ve secim gruplari kontrol ediliyor...")
  (DT--full-maintenance)
  (princ)
)

(defun DT_ORIG (/ *error* oldCmd oldOsm oldAutoSnap oldOsOptions drawResult ent pts inputWidth width mode oldCenters allCenters elevationScanResult elevationScan elevationContacts transitionCenters routeElevations elevationBuild elevationCount mergeResult build pieces trayCuts turnBlocks cornerCount fitCounts resizeSel resizeResult panelValues panelSideHeight panelHeight panelElevationAngle panel3d panelSession paletteActive *DT_CURRENT_TURN_BLOCKS* *DT_LIVE_PREVIEW_PIECES* *DT_LIVE_PREVIEW_BLOCKS* *DT_LIVE_OSNAP_GUIDES* *DT_LIVE_SILHOUETTE_TEMP* *DT_PALETTE_ACTIVE* *DT_PALETTE_SIDE_HEIGHT* *DT_PALETTE_TRAY_HEIGHT* *DT_PALETTE_STATE_PATH* *DT_ACTIVE_ELEVATION* *DT_ACTIVE_ELEVATION_ANGLE* *DT_ACTIVE_SIDE_HEIGHT* *DT_ACTIVE_SIDE_HEIGHT_MM* *DT_ACTIVE_3D* *DT_BUILD_ROUTE_PTS* *DT_BUILD_START_ELEVATION* *DT_BUILD_END_ELEVATION* *DT_BUILD_START_TRIM* *DT_BUILD_END_TRIM* *DT_BUILD_START_LINE_ELEVATION* *DT_BUILD_END_LINE_ELEVATION* *DT_FITTING_CACHE_ACTIVE* *DT_FITTING_CACHE* *DT_CENTER_CACHE_ACTIVE* *DT_CENTER_CACHE*)
  (vl-load-com)
  (setq *DT_CURRENT_TURN_BLOCKS* nil)
  (setq oldCmd      (getvar "CMDECHO")
        oldOsm      (getvar "OSMODE")
        oldAutoSnap (getvar "AUTOSNAP")
        oldOsOptions (getvar "OSOPTIONS"))
  (defun *error* (msg)
    (DT--live-preview-clear)
    (redraw)
    (if oldCmd (setvar "CMDECHO" oldCmd))
    (if (numberp oldOsm) (setvar "OSMODE" oldOsm))
    (if (numberp oldAutoSnap) (setvar "AUTOSNAP" oldAutoSnap))
    (if (numberp oldOsOptions) (setvar "OSOPTIONS" oldOsOptions))
    (DT--palette-set-context "SELECT")
    (DT--palette-publish-current-selection)
    (if (and msg (not (wcmatch (strcase msg) "*CANCEL*,*QUIT*,*BREAK*")))
      (princ (strcat "\nDT hata: " msg))
    )
    (princ)
  )
  (setvar "CMDECHO" 0)
  (setvar "OSMODE" (DT--drawing-osmode oldOsm))
  (setvar "AUTOSNAP" (DT--drawing-autosnap oldAutoSnap))
  (setvar "OSOPTIONS" (DT--drawing-osoptions oldOsOptions))
  (setq width (DT--last-width)
        mode (DT--last-mode))
  (DT--remember-mode mode)
  (DT--ensure-type-layers)
  ;; Full-plan migration and group rebuilding is intentionally not run here.
  ;; Use DTBAKIM only when an old or externally edited drawing needs repair.
  (DT--ensure-composite-pickstyle)
  (DT--ensure-layer (DT--layer-center) 8 T)
  (DT--cleanup-stale-centers)
  ;; DT oturumu boyunca INSERT ve centerline taramalari bir kez yapilir.
  ;; Sabit fitting block dogrulamalari ayni DWG/AutoCAD oturumunda korunur.
  (DT--ensure-fitting-definition-session-cache)
  (setq *DT_FITTING_CACHE_ACTIVE*     T
        *DT_FITTING_CACHE*            (DT--collect-fitting-inserts)
        *DT_CENTER_CACHE_ACTIVE*      T
        *DT_CENTER_CACHE*             (DT--collect-center-entities-raw))
  (setq resizeSel (DT--pickfirst-selection))
  (if (and resizeSel (DT--selection-has-resizable-p resizeSel))
    (setq resizeResult (DT--resize-selection-flow resizeSel))
    (progn
  (setq paletteActive (DT--palette-start (DT--last-mode) (DT--last-width))
        *DT_PALETTE_ACTIVE* paletteActive
        panelSession T
        panelValues
          (if paletteActive
            (DT--palette-settings (DT--last-mode) (DT--last-width))
            (DT--panel-show (DT--last-mode) (DT--last-width))))
  (while (and panelSession panelValues)
  (setq mode            (car panelValues)
        width           (cadr panelValues)
        panelSideHeight (caddr panelValues)
        panelHeight     (cadddr panelValues)
        panelElevationAngle
          (if (numberp (nth 4 panelValues))
            (nth 4 panelValues)
            (DT--last-elevation-angle))
        panel3d (if (nth 5 panelValues) T nil))
  (setq *DT_PALETTE_SIDE_HEIGHT* panelSideHeight
        *DT_PALETTE_TRAY_HEIGHT* panelHeight
        *DT_ACTIVE_ELEVATION_ANGLE* panelElevationAngle
        *DT_ACTIVE_3D* panel3d
        *DT_ACTIVE_ELEVATION* (DT--tray-height-elevation panelHeight))
  (DT--remember-mode mode)
  (DT--remember-width width)
  (setq drawResult (DT--draw-center-polyline width mode))
  (setq ent (car drawResult)
        inputWidth (cadr drawResult)
        mode (caddr drawResult))
  (if paletteActive
    (setq panelSideHeight *DT_PALETTE_SIDE_HEIGHT*
          panelHeight     *DT_PALETTE_TRAY_HEIGHT*
          panelElevationAngle *DT_ACTIVE_ELEVATION_ANGLE*
          panel3d *DT_ACTIVE_3D*)
  )
  (setq *DT_ACTIVE_SIDE_HEIGHT_MM* panelSideHeight
        *DT_ACTIVE_SIDE_HEIGHT* (DT--plan-side-height panelSideHeight))
  (DT--remember-width inputWidth)
  (setq width (DT--plan-width inputWidth))
  (DT--remember-mode mode)
  (setq panelValues
    (list mode inputWidth panelSideHeight panelHeight panelElevationAngle panel3d))
  (if (null ent)
    (progn
      (setq panelSession nil)
      (princ "\nDT: Cizim oturumu tamamlandi."))
    (progn
      (DT--cache-center-entity ent)
      (setq pts (g365_get_pts ent))
      (setq pts (DT--snap-poly-ends-to-fitting-blocks pts width))
      (setq elevationScanResult
              (DT--elevation-scan-for-center
                ent pts width (DT--layer-visible))
            elevationScan      (car elevationScanResult)
            allCenters         (cadr elevationScanResult)
            pts                (car elevationScan)
            elevationContacts (cadr elevationScan)
            transitionCenters (caddr elevationScan)
            routeElevations    (nth 3 elevationScan))
      (DT--set-center-points ent pts)
      (DT--set-center-end-elevations ent (car routeElevations) (cadr routeElevations))
      (DT--set-center-base-elevation ent (car routeElevations))
      (setq *DT_ACTIVE_ELEVATION* (car routeElevations))
      (if (or (null pts) (< (length pts) 2))
        (progn
          (entdel ent)
          (princ "\nDT: Polyline geometrisi olusturulamadi."))
        (progn
          (DT--set-center-width ent width)
          (DT--set-center-layer ent (DT--layer-visible))
          ;; Elevation gecisleri parcayi yeniden kurmadan once nominal yanak
          ;; yuksekligini merkezden okuyabilsin.
          (DT--set-tray-meta-one
            ent mode inputWidth panelSideHeight panelHeight)
          (DT--set-entity-3d-mode ent panel3d)
          (setq oldCenters
            (DT--filter-centers-near-route
              (DT--center-entities ent (DT--layer-visible))
              pts width))
          (if transitionCenters
            (setq oldCenters (DT--remove-centers-from-list oldCenters transitionCenters))
          )
          (setq mergeResult (DT--merge-collinear-bridge ent pts oldCenters width))
          (if mergeResult
            (progn
              (setq pts (car mergeResult))
              (setq oldCenters (cadr mergeResult))
            )
          )
          (setq *DT_BUILD_ROUTE_PTS* pts
                *DT_BUILD_START_ELEVATION* (car routeElevations)
                *DT_BUILD_END_ELEVATION*   (cadr routeElevations)
                *DT_BUILD_START_TRIM*      0.0
                *DT_BUILD_END_TRIM*        0.0
                *DT_BUILD_START_LINE_ELEVATION* (car routeElevations)
                *DT_BUILD_END_LINE_ELEVATION*   (cadr routeElevations)
                build (DT--build-piecewise-tray pts width))
          (setq pieces      (nth 0 build)
                turnBlocks  (nth 1 build)
                cornerCount (nth 2 build))
          ;; Eski ag taramasi yeni olusturulan dirsekleri eski fitting sanmasin.
          (setq *DT_CURRENT_TURN_BLOCKS* turnBlocks)
          (setq trayCuts (DT--plus-cuts ent))
          (if trayCuts
            (progn
              (DT--delete-ents pieces)
              (setq pieces (DT--build-straight-pieces pts width trayCuts))
            )
          )
          (if (null pieces)
            (progn
              (entdel ent)
              (princ "\nDT: Tava parcalari olusturulamadi."))
            (progn
              (DT--xdata-link-tray ent pieces)
              (setq fitCounts (DT--place-network-fittings pts oldCenters width))
              (if (or (nth 2 fitCounts) (nth 3 fitCounts) (nth 5 fitCounts) (nth 7 fitCounts))
                (setq pieces (DT--apply-junction-splits ent fitCounts width))
              )
              (setq elevationBuild (DT--apply-elevation-transitions ent elevationContacts width allCenters)
                    elevationCount (car elevationBuild))
              (if (cadr elevationBuild)
                (setq pieces (cadr elevationBuild))
              )
              (DT--set-tray-meta ent pieces turnBlocks mode inputWidth panelSideHeight panelHeight)
              (DT--set-tray-3d-mode ent pieces turnBlocks panel3d)
              (DT--refresh-connection-warnings-for-centers (list ent))
              (princ
                (strcat
                  "\nDT tamam: "
                  mode " / " (DT--layer-visible) ", "
                  (rtos inputWidth 2 0) " nominal / planda "
                  (rtos width 2 2) " genislik, "
                  (itoa (length pieces)) " tava parcasi, "
                  (itoa (+ cornerCount (nth 6 fitCounts))) " donus blocku, "
                  (itoa (car fitCounts)) " T blocku, "
                  (itoa (cadr fitCounts)) " + blocku, "
                  (itoa (nth 4 fitCounts)) " esnek block, "
                  (itoa elevationCount) " elevation blocku."
                )
              )
            )
          )
        )
      )
    )
  )
  (if (and (not paletteActive) *DT_PANEL_DCL_FAILED*) (setq panelSession nil))
  )
    )
  )
  (DT--palette-set-context "SELECT")
  (DT--palette-publish-current-selection)
  (if (numberp oldOsm) (setvar "OSMODE" oldOsm))
  (if (numberp oldAutoSnap) (setvar "AUTOSNAP" oldAutoSnap))
  (if (numberp oldOsOptions) (setvar "OSOPTIONS" oldOsOptions))
  (setvar "CMDECHO" oldCmd)
  (princ)
)
;; DTM - SECILEN ALANDA DT TAVA METRAJI VE DONUS ELEMANI ADEDI
(defun DTM--trim-number (v / s)
  (setq s (rtos (if (numberp v) v 0.0) 2 3))
  (if (vl-string-search "." s)
    (progn
      (while (and (> (strlen s) 1) (= (substr s (strlen s) 1) "0"))
        (setq s (substr s 1 (1- (strlen s))))
      )
      (if (= (substr s (strlen s) 1) ".")
        (setq s (substr s 1 (1- (strlen s))))
      )
    )
  )
  (vl-string-subst "," "." s)
)

(defun DT--entity-points3d (ent / ed typ elevation item pts v vd p)
  (if (and ent (setq ed (entget ent)))
    (progn
      (setq typ (cdr (assoc 0 ed)))
      (cond
        ((= typ "LWPOLYLINE")
          (setq elevation (if (assoc 38 ed) (cdr (assoc 38 ed)) 0.0))
          (foreach item ed
            (if (= (car item) 10)
              (setq p (cdr item)
                    pts (append pts
                          (list (list (car p) (cadr p) elevation)))))))
        ((= typ "POLYLINE")
          (setq v (entnext ent))
          (while (and v (/= (cdr (assoc 0 (entget v))) "SEQEND"))
            (setq vd (entget v))
            (if (= (cdr (assoc 0 vd)) "VERTEX")
              (progn
                (setq p (cdr (assoc 10 vd)))
                (if p (setq pts (append pts (list p))))))
            (setq v (entnext v))))
      )
    )
  )
  pts
)

(defun DTM--tray-width (tray / pts l01 l12)
  (setq pts (DT--entity-points3d tray))
  (if (and pts (>= (length pts) 4))
    (progn
      (setq l01 (distance (nth 0 pts) (nth 1 pts))
            l12 (distance (nth 1 pts) (nth 2 pts)))
      (min l01 l12)
    )
  )
)

(defun DTM--tray-length (tray / pts l01 l12)
  (setq pts (DT--entity-points3d tray))
  (if (and pts (>= (length pts) 4))
    (progn
      (setq l01 (distance (nth 0 pts) (nth 1 pts))
            l12 (distance (nth 1 pts) (nth 2 pts)))
      (max l01 l12)
    )
  )
)

(defun DTT--tray-short-code (tray / ed lay rec types code)
  (setq ed  (if tray (entget tray))
        lay (if ed (strcase (DT--base-layer-name (cdr (assoc 8 ed)))) "")
        types (DT--type-configs)
        code nil)
  (foreach rec types
    (if (= lay (strcase (cadr rec)))
      (setq code (car rec))
    )
  )
  ;; Eski genel E_TAVA layer'i icin ilk tanimli DT kisa adini kullan.
  (if (and (null code) (= lay "E_TAVA") types)
    (setq code (caar types))
  )
  (if (and code (/= code "")) code "TAVA")
)

(defun DTT--length-to-mm (v / unit)
  (setq unit (DEG:PLAN-UNIT-KEY))
  (cond
    ((= unit "cm") (* (float v) 10.0))
    ((= unit "m")  (* (float v) 1000.0))
    (T (float v))
  )
)

(defun DTT--tray-nominal-width (trayW / scale raw allowed item best bestD d)
  (setq scale (DEG:PLAN-UNIT-SCALE))
  (if (<= scale 0.0) (setq scale 1.0))
  (setq raw     (/ (float trayW) scale)
        allowed '(10.0 20.0 30.0 40.0 50.0))
  (if (setq best (DT--nominal-width raw))
    best
    (progn
      (setq best nil
            bestD nil)
      (foreach item allowed
        (setq d (abs (- raw item)))
        (if (or (null bestD) (< d bestD))
          (setq best item
                bestD d)
        )
      )
      best
    )
  )
)

(defun DTT--side-height-default (nominal)
  (if (and nominal (< nominal 50.0)) 40.0 50.0)
)

(defun DTT--side-height-mm (nominal)
  ;; Yalniz eski/metadatasiz tavalar ve DT panelinin ilk degeri icin fallback.
  ;; DTT etiketi, yeni tavada yanak yuksekligini dogrudan tava XData'sindan alir.
  (DTT--side-height-default nominal)
)

(defun DTT--label-element-p (ent)
  (and ent
       (entget ent)
       (or (DT--visible-tray-p ent) (DT--ladder-meta ent)))
)

(defun DTT--tray-mid-elevation (tray / ladderMeta pts first last sum count p)
  (setq ladderMeta (DT--ladder-meta tray))
  (if (and ladderMeta (numberp (nth 3 ladderMeta)))
    (nth 3 ladderMeta)
    (progn
      (setq pts (DT--entity-points3d tray))
      (if (and (> (length pts) 1)
               (equal (car pts) (g365_last pts) 0.000001))
        (setq pts (DT--drop-last-item pts))
      )
      (foreach p pts
        (setq sum   (+ (if sum sum 0.0) (if (and p (numberp (caddr p))) (caddr p) 0.0))
              count (1+ (if count count 0)))
      )
      (if (> (if count count 0) 0)
        (/ sum count)
        (DT--entity-elevation tray)
      )
    )
  )
)

(defun DTT--tray-att-values
  (tray trayW / ladderMeta meta code nominal widthMm sideHeight sideText elevationText)
  (setq ladderMeta (DT--ladder-meta tray))
  (if ladderMeta
    (setq code          (nth 0 ladderMeta)
          nominal       (nth 1 ladderMeta)
          sideHeight    (nth 2 ladderMeta)
          elevationText "E : -")
    (setq meta       (DT--tray-meta-effective tray)
          code       (if (and meta (car meta) (/= (car meta) ""))
                       (car meta)
                       (DTT--tray-short-code tray))
          nominal    (if (and meta (numberp (cadr meta)) (> (cadr meta) 0.0))
                       (cadr meta)
                       (DTT--tray-nominal-width trayW))
          sideHeight (if (and meta (numberp (caddr meta)) (> (caddr meta) 0.0))
                       (caddr meta)
                       (DTT--side-height-mm nominal))
          elevationText
            (strcat
              "E : "
              (DTM--trim-number (DTT--tray-mid-elevation tray))
              " "
              (DEG:LEN-UNIT-LABEL)))
  )
  (setq widthMm  (* nominal 10.0)
        sideText (strcat "H : " (DTM--trim-number sideHeight) " mm"))
  (list
    (cons "TAVA_TÝPÝ" (strcat code " - KT"))
    (cons "GENÝÞLÝK" (strcat "W : " (DTM--trim-number widthMm) " mm"))
    (cons "YANAK_YÜKSEKLÝÐÝ" sideText)
    (cons "YÜKSEKLÝK" elevationText)
  )
)

(defun DTT--label-plan-width (ent / ladderMeta)
  (setq ladderMeta (DT--ladder-meta ent))
  (if (and ladderMeta (numberp (nth 1 ladderMeta)))
    (DT--plan-width (nth 1 ladderMeta))
    (DTM--tray-width ent)
  )
)

(defun DTM--tray-type (ent lay / meta base rec hit)
  (setq meta (DT--tray-meta-effective ent))
  (if (and meta (car meta) (/= (vl-string-trim " \t\r\n" (car meta)) ""))
    (DT--normalize-mode (car meta))
    (progn
      (setq base (strcase (DT--base-layer-name lay)))
      (foreach rec (DT--type-configs)
        (if (= base (strcase (cadr rec)))
          (setq hit (car rec))))
      (if hit hit (DT--base-layer-name lay))
    )
  )
)

(defun DTM--add-tray-row (rows trayType width len / key rec)
  (setq key (strcat (strcase trayType) "|" (rtos width 2 8))
        rec (assoc key rows))
  (if rec
    (subst
      (list key (nth 1 rec) (nth 2 rec)
        (+ (nth 3 rec) len) (1+ (nth 4 rec)))
      rec rows)
    (append rows (list (list key trayType width len 1)))
  )
)

(defun DTM--fitting-label (ent / kind ed name u)
  (setq kind (DT--fitting-kind ent))
  (if (and (= (type kind) 'STR) (/= (vl-string-trim " \t\r\n" kind) ""))
    (strcase kind)
    (progn
      (setq ed   (entget ent)
            name (if ed (cdr (assoc 2 ed)) "")
            u    (strcase (if name name "")))
      (cond
        ((vl-string-search "_T_" u) "T")
        ((vl-string-search "_ART" u) "+")
        ((vl-string-search "_ESNEK" u) "ESNEK")
        (T "DONUS")
      )
    )
  )
)

(defun DTM--add-fitting-row (rows lay kind width / key rec)
  (setq key (strcat (strcase lay) "|" (strcase kind) "|" (rtos width 2 8))
        rec (assoc key rows))
  (if rec
    (subst (list key (nth 1 rec) (nth 2 rec) (nth 3 rec) (1+ (nth 4 rec))) rec rows)
    (append rows (list (list key lay kind width 1)))
  )
)

(defun DTM--ladder-key (ent meta / groupId handle)
  (setq groupId (if meta (nth 5 meta))
        handle  (if ent (DT--ent-handle ent)))
  (cond
    ((and groupId (/= groupId ""))
      (strcat "GROUP|" (strcase groupId)))
    (handle
      (strcat "ENTITY|" (strcase handle)))
  )
)

(defun DTM--add-ladder-row
  (rows meta / mode nominal topElevation bottomElevation ladderLength key rec)
  (if meta
    (progn
      (setq mode            (DT--normalize-mode (nth 0 meta))
            nominal         (nth 1 meta)
            topElevation    (nth 3 meta)
            bottomElevation (nth 4 meta)
            ladderLength    (abs (- topElevation bottomElevation))
            key             (strcat (strcase mode) "|" (DEG:NUM->STR nominal))
            rec (assoc key rows))
      (if rec
        (subst
          (list key mode nominal
                (+ (nth 3 rec) ladderLength)
                (1+ (nth 4 rec)))
          rec rows)
        (append rows
          (list
            (list key mode nominal ladderLength 1)))))
    rows)
)

(defun DTM--sort-tray-rows (rows)
  (vl-sort rows
    (function
      (lambda (a b)
        (if (= (strcase (nth 1 a)) (strcase (nth 1 b)))
          (< (nth 2 a) (nth 2 b))
          (< (strcase (nth 1 a)) (strcase (nth 1 b)))
        )
      )
    )
  )
)

(defun DTM--sort-fitting-rows (rows)
  (vl-sort rows
    (function
      (lambda (a b)
        (cond
          ((/= (strcase (nth 1 a)) (strcase (nth 1 b)))
            (< (strcase (nth 1 a)) (strcase (nth 1 b))))
          ((/= (strcase (nth 2 a)) (strcase (nth 2 b)))
            (< (strcase (nth 2 a)) (strcase (nth 2 b))))
          (T (< (nth 3 a) (nth 3 b)))
        )
      )
    )
  )
)

(defun DTM--sort-ladder-rows (rows)
  (vl-sort rows
    (function
      (lambda (a b)
        (if (= (strcase (nth 1 a)) (strcase (nth 1 b)))
          (< (nth 2 a) (nth 2 b))
          (< (strcase (nth 1 a)) (strcase (nth 1 b)))
        )
      )
    )
  )
)

(defun DTM--width-text (width unit)
  (if (and (numberp width) (> width 0.0))
    (strcat (DTM--trim-number width) " " unit)
    "-"
  )
)

(defun DTM--metre-text-1 (v / s)
  (setq s (rtos (DEG:LEN-CONVERT v) 2 1))
  (if (vl-string-search "." s)
    (vl-string-subst "," "." s)
    (strcat s ",0")
  )
)
(defun DTM--show-report
  (trayRows ladderRows fittingRows trayCount ladderCount fittingCount /
    msg row total ladderTotal unit)
  (setq unit  (DEG:LEN-UNIT-LABEL)
        total 0.0
        msg   "DTM - TAVA METRAJI\n\n")
  (if trayRows
    (progn
      (setq msg (strcat msg "TAVALAR (tip | genislik | toplam boy | parca)\n"))
      (foreach row (DTM--sort-tray-rows trayRows)
        (setq total (+ total (nth 3 row)))
        (setq msg
          (strcat msg
            (nth 1 row) " | "
            (DTM--width-text (nth 2 row) unit) " | "
            (DTM--metre-text-1 (nth 3 row)) " m | "
            (itoa (nth 4 row)) " parca\n"))
      )
      (setq msg
        (strcat msg
          "------------------------------\n"
          "TOPLAM: " (DTM--metre-text-1 total) " m"
          "  (" (itoa trayCount) " parca)\n"))
    )
    (setq msg (strcat msg "Tava bulunamadi.\n"))
  )
  (setq msg
    (strcat msg
      "\nMERDIVENLER (tip | genislik | toplam boy | parca)\n"))
  (if ladderRows
    (progn
      (setq ladderTotal 0.0)
      (foreach row (DTM--sort-ladder-rows ladderRows)
        (setq ladderTotal (+ ladderTotal (nth 3 row)))
        (setq msg
          (strcat msg
            (nth 1 row) " | "
            (DTM--width-text (DT--plan-width (nth 2 row)) unit) " | "
            (DTM--metre-text-1 (nth 3 row)) " m | "
            (itoa (nth 4 row)) " parca\n"))
      )
      (setq msg
        (strcat msg
          "------------------------------\n"
          "TOPLAM: " (DTM--metre-text-1 ladderTotal) " m"
          "  (" (itoa ladderCount) " parca)\n"))
    )
    (setq msg (strcat msg "Merdiven bulunamadi.\n"))
  )
  (setq msg (strcat msg "\nDONUS ELEMANLARI (katman | tip | genislik | adet)\n"))
  (if fittingRows
    (progn
      (foreach row (DTM--sort-fitting-rows fittingRows)
        (setq msg
          (strcat msg
            (nth 1 row) " | "
            (nth 2 row) " | "
            (DTM--width-text (nth 3 row) unit) " | "
            (itoa (nth 4 row)) " adet\n"))
      )
      (setq msg
        (strcat msg
          "------------------------------\n"
          "TOPLAM: " (itoa fittingCount) " adet"))
    )
    (setq msg (strcat msg "Donus elemani bulunamadi."))
  )
  (DEG:WIN-MESSAGE msg)
)

(defun DTT--pt3 (p)
  (list (car p) (cadr p) (if (caddr p) (caddr p) 0.0))
)

(defun DTT--move (p v d)
  (list
    (+ (car p) (* (car v) d))
    (+ (cadr p) (* (cadr v) d))
    (if (caddr p) (caddr p) 0.0)
  )
)

(defun DTT--basis (seg / a b dx dy len mid)
  (if (and seg (= (length seg) 2))
    (progn
      (setq a   (car seg)
            b   (cadr seg)
            dx  (- (car b) (car a))
            dy  (- (cadr b) (cadr a))
            len (sqrt (+ (* dx dx) (* dy dy)))
            mid (DT--pt-mid a b))
      (if (> len 0.000001)
        (progn
          ;; Polyline cizim yonunden bagimsiz, sabit bir dis taraf sec.
          (if (or (< dx -0.000000001)
                  (and (<= (abs dx) 0.000000001) (< dy 0.0)))
            (setq dx (- dx) dy (- dy))
          )
          (setq dx (/ dx len) dy (/ dy len))
          (list mid (list dx dy 0.0) (list (- dy) dx 0.0))
        )
      )
    )
  )
)

(defun DTT--make-line (a b lay)
  (entmakex
    (list
      '(0 . "LINE")
      '(100 . "AcDbEntity")
      (cons 8 lay)
      '(100 . "AcDbLine")
      (cons 10 (DTT--pt3 a))
      (cons 11 (DTT--pt3 b))
    )
  )
)

(defun DTT--block-object (name / doc blocks obj)
  (setq doc    (vla-get-ActiveDocument (vlax-get-acad-object))
        blocks (vla-get-Blocks doc)
        obj    (vl-catch-all-apply 'vla-Item (list blocks name)))
  (if (vl-catch-all-error-p obj)
    (progn
      (setq obj
        (vl-catch-all-apply
          'vla-Add
          (list blocks (vlax-3d-point '(0.0 0.0 0.0)) name)
        )
      )
      (if (vl-catch-all-error-p obj) nil obj)
    )
    obj
  )
)
(defun DTT--block-line (blk a b lay / obj)
  (setq obj
    (vl-catch-all-apply
      'vla-AddLine
      (list blk (vlax-3d-point a) (vlax-3d-point b))
    )
  )
  (if (vl-catch-all-error-p obj)
    nil
    (progn
      (vl-catch-all-apply 'vla-put-Layer (list obj lay))
      obj
    )
  )
)
(defun DTT--valid-text-style (name / rec)
  (setq rec
    (tblsearch "STYLE"
      (if (and name (/= (vl-string-trim " \t\r\n" name) ""))
        name
        "Standard")))
  (if (null rec) (setq rec (tblsearch "STYLE" "Standard")))
  (if rec (cdr (assoc 2 rec)) "Standard")
)

(defun DTT--add-attdef (blk tag pos textH textStyle lay / att)
  (setq att
    (vl-catch-all-apply
      'vla-AddAttribute
      (list
        blk
        textH
        0
        (strcat tag " degeri")
        (vlax-3d-point pos)
        tag
        ""
      )
    )
  )
  (if (vl-catch-all-error-p att)
    nil
    (progn
      (vl-catch-all-apply 'vla-put-Layer (list att lay))
      (vl-catch-all-apply 'vla-put-StyleName
        (list att (DTT--valid-text-style textStyle)))
      ;; Dinamik Move action'in ATTREF'i dikdortgenle birlikte tasimasi icin
      ;; attribute taniminin block icindeki konumu kilitli olmalidir.
      (cond
        ((vlax-property-available-p att 'LockPosition T)
         (vl-catch-all-apply 'vlax-put-property
           (list att 'LockPosition :vlax-true)))
        ((vlax-property-available-p att 'LockPositionInBlock T)
         (vl-catch-all-apply 'vlax-put-property
           (list att 'LockPositionInBlock :vlax-true)))
      )
      att
    )
  )
)

(defun DTT--attribute-layout (rectW rectH baseY textH / hw marginX marginY x topY bottomY step)
  (setq hw      (/ rectW 2.0)
        marginX (min (* rectW 0.25) (max 2.0 (* rectW 0.08)))
        marginY (min (* rectH 0.20) (max 1.5 (* rectH 0.08)))
        x       (+ (- hw) marginX)
        topY    (- (+ baseY rectH) marginY textH)
        bottomY (+ baseY marginY)
        step    (if (> topY bottomY) (/ (- topY bottomY) 3.0) 0.0))
  (list x topY (- topY step) (- topY (* 2.0 step)) bottomY)
)

(defun DTT--ensure-label-block (name rectW rectH stemLen attTextH attTextStyle lay / blk hw hh p1 p2 p3 p4 stem l1 l2 l3 l4 textH layout x y1 y2 y3 y4 a1 a2 a3 a4)
  (setq blk (DTT--block-object name))
  (if blk
    (progn
      (DT--clear-block-object blk)
      (setq hw (/ rectW 2.0)
            hh (/ rectH 2.0)
            p1 (list (- hw) stemLen 0.0)
            p2 (list hw stemLen 0.0)
            p3 (list hw (+ stemLen rectH) 0.0)
            p4 (list (- hw) (+ stemLen rectH) 0.0)
            stem (DTT--block-line blk '(0.0 0.0 0.0) (list 0.0 stemLen 0.0) lay)
            l1 (DTT--block-line blk p1 p2 lay)
            l2 (DTT--block-line blk p2 p3 lay)
            l3 (DTT--block-line blk p3 p4 lay)
            l4 (DTT--block-line blk p4 p1 lay))
      (if (and stem l1 l2 l3 l4)
        (progn
          (setq textH   (if (and (numberp attTextH) (> attTextH 0.0)) attTextH 8.0)
                layout  (DTT--attribute-layout rectW rectH stemLen textH)
                x       (nth 0 layout)
                y1      (nth 1 layout)
                y2      (nth 2 layout)
                y3      (nth 3 layout)
                y4      (nth 4 layout)
                a1      (DTT--add-attdef blk "TAVA_TÝPÝ" (list x y1 0.0) textH attTextStyle lay)
                a2      (DTT--add-attdef blk "GENÝÞLÝK" (list x y2 0.0) textH attTextStyle lay)
                a3      (DTT--add-attdef blk "YANAK_YÜKSEKLÝÐÝ" (list x y3 0.0) textH attTextStyle lay)
                a4      (DTT--add-attdef blk "YÜKSEKLÝK" (list x y4 0.0) textH attTextStyle lay))
          (if (and a1 a2 a3 a4)
            (progn
              (setq *DTT--stem-object* stem
                    *DTT--move-objects* (list l1 l2 l3 l4 a1 a2 a3 a4))
              blk
            )
            nil
          )
        )
      )
    )
  )
)

(defun DTT--mid3 (a b)
  (list (/ (+ (car a) (car b)) 2.0)
        (/ (+ (cadr a) (cadr b)) 2.0)
        (/ (+ (if (caddr a) (caddr a) 0.0)
              (if (caddr b) (caddr b) 0.0)) 2.0))
)

(defun DTT--ladder-placement-safe
  (tray / control meta pts p0 p1 frontMid sidePlan u normal base
          cap point sumX sumY count)
  (setq control
    (cond
      ((DT--light-ladder-control-p tray) tray)
      ((DT--light-ladder-visual-p tray)
        (DT--light-ladder-controller tray))))
  (if control
    (progn
      (setq pts (DT--entity-points3d control)
            p0  (if pts (nth 0 pts))
            p1  (if pts (nth 1 pts))
            meta (DT--ladder-meta control))
      (if (and p0 p1)
        (progn
          (setq frontMid (DTT--mid3 p0 p1)
                sidePlan (if meta (DT--plan-side-height (nth 2 meta)) 0.0)
                u        (DT--seg-unit p0 p1)
                normal   (if u (DT--perp u))
                base     (if normal
                           (DT--pt-shift-xy frontMid normal (/ sidePlan 2.0))
                           frontMid))
          (list
            base
            (atan (- (cadr p1) (cadr p0))
                  (- (car p1) (car p0)))))))
    (progn
      (setq cap (DT--ladder-top-cap tray)
            pts (if cap (g365_get_pts cap))
            p0  (if pts (car pts))
            p1  (if pts (cadr pts))
            meta (DT--ladder-meta tray))
      (if (and p0 p1)
        (progn
          (foreach point pts
            (setq sumX (+ (if sumX sumX 0.0) (car point))
                  sumY (+ (if sumY sumY 0.0) (cadr point))
                  count (1+ (if count count 0))))
          (list
            (list
              (/ sumX (float count))
              (/ sumY (float count))
              (if (and meta (numberp (nth 3 meta)))
                (nth 3 meta)
                (DTT--tray-mid-elevation tray)))
            (atan (- (cadr p1) (cadr p0))
                  (- (car p1) (car p0))))))))
)

(defun DTT--tray-center-seg3d
  (tray / ladderMeta placement base angle half p0 p1 pts p2 p3 l01 l12)
  (setq ladderMeta (DT--ladder-meta tray))
  (if ladderMeta
    (progn
      (setq placement (DTT--ladder-placement-safe tray)
            base      (if placement (car placement))
            angle     (if placement (cadr placement))
            half      (if (numberp (nth 1 ladderMeta))
                        (/ (DT--plan-width (nth 1 ladderMeta)) 2.0)
                        0.0))
      (if (and base (numberp angle) (> half 0.0))
        (progn
          (setq p0 (polar base (+ angle pi) half)
                p1 (polar base angle half))
          (list
            (list (car p0) (cadr p0) (DTT--tray-mid-elevation tray))
            (list (car p1) (cadr p1) (DTT--tray-mid-elevation tray))))))
    (progn
      (setq pts (DT--tray-corner-points-3d tray))
      (if (= (length pts) 4)
        (progn
          (setq p0  (nth 0 pts)
                p1  (nth 1 pts)
                p2  (nth 2 pts)
                p3  (nth 3 pts)
                l01 (distance p0 p1)
                l12 (distance p1 p2))
          (if (>= l01 l12)
            (list (DTT--mid3 p0 p3) (DTT--mid3 p1 p2))
            (list (DTT--mid3 p0 p1) (DTT--mid3 p3 p2)))))))
)

(defun DTT--placement-record (handle / ent seg basis mid tang)
  (setq ent   (if handle (handent handle))
        seg   (if (DTT--label-element-p ent)
                (DTT--tray-center-seg3d ent))
        basis (if seg (DTT--basis seg)))
  (if basis
    (progn
      (setq mid
              (list
                (car (nth 0 basis))
                (cadr (nth 0 basis))
                (DTT--tray-mid-elevation ent))
            tang (nth 1 basis))
      (list handle mid tang)))
)

(defun DTT--placement-record-less-p (a b / ma mb ax bx ay by tol)
  (setq ma  (cadr a)
        mb  (cadr b)
        ax  (car ma)
        bx  (car mb)
        ay  (cadr ma)
        by  (cadr mb)
        tol 0.000001)
  (cond
    ((< ax (- bx tol)) T)
    ((> ax (+ bx tol)) nil)
    ((< ay (- by tol)) T)
    ((> ay (+ by tol)) nil)
    (T
      (vl-string-lessp
        (strcase (if (car a) (car a) ""))
        (strcase (if (car b) (car b) "")))))
)

(defun DTT--placement-records (handles / handle record records)
  (foreach handle handles
    (setq record (DTT--placement-record handle))
    (if record (setq records (append records (list record)))))
  (vl-sort records 'DTT--placement-record-less-p)
)

(defun DTT--preferred-end-sign
  (record records rectW rectH
   / handle mid tang tx ty nx ny tangentSpan normalSpan alongLimit crossLimit
     other otherMid otherTang parallel dx dy along cross weight bias)
  (if record
    (progn
      (setq handle      (car record)
            mid         (cadr record)
            tang        (caddr record)
            tx          (car tang)
            ty          (cadr tang)
            nx          (- ty)
            ny          tx
            tangentSpan (+ (* (abs tx) rectW) (* (abs ty) rectH))
            normalSpan  (+ (* (abs nx) rectW) (* (abs ny) rectH))
            alongLimit  (* 4.0 (max tangentSpan 0.001))
            crossLimit  (* 2.5 (max normalSpan 0.001))
            bias        0.0)
      (foreach other records
        (if (not (equal handle (car other)))
          (progn
            (setq otherMid  (cadr other)
                  otherTang (caddr other)
                  parallel
                    (abs
                      (+ (* tx (car otherTang))
                         (* ty (cadr otherTang))))
                  dx    (- (car otherMid) (car mid))
                  dy    (- (cadr otherMid) (cadr mid))
                  along (+ (* dx tx) (* dy ty))
                  cross (abs (+ (* dx nx) (* dy ny))))
            (if (and (>= parallel 0.94)
                     (> (abs along) 0.000001)
                     (<= (abs along) alongLimit)
                     (<= cross crossLimit))
              (progn
                ;; Yakin komsular daha agir basar. Bias komsularin bulundugu
                ;; tava ucu yonudur; etiket bunun tersindeki dis uca kayar.
                (setq weight
                        (/ 1.0
                           (max 0.001
                                (+ (abs along) (* 0.5 cross))))
                      bias
                        (+ bias
                           (* (if (> along 0.0) 1.0 -1.0)
                              weight))))))))
      (cond
        ((> bias 0.000000001) -1)
        ((< bias -0.000000001) 1)
      )))
)

(defun DTT--set-definition-att-height (name textH / btr en d obj)
  (setq btr (tblobjname "BLOCK" name))
  (if (and btr (numberp textH) (> textH 0.0))
    (progn
      (setq en (entnext btr))
      (while (and en (/= (cdr (assoc 0 (entget en))) "ENDBLK"))
        (setq d (entget en))
        (if (= (cdr (assoc 0 d)) "ATTDEF")
          (progn
            (setq obj (vl-catch-all-apply 'vlax-ename->vla-object (list en)))
            (if (not (vl-catch-all-error-p obj))
              (vl-catch-all-apply 'vla-put-Height (list obj textH))
            )
          )
        )
        (setq en (entnext en))
      )
      T
    )
    nil
  )
)

(defun DTT--set-reference-att-height (ref textH / att)
  (if (and ref (numberp textH) (> textH 0.0))
    (foreach att (degk--att-list ref)
      (vl-catch-all-apply 'vla-put-Height (list att textH))
    )
  )
  ref
)

(defun DTT--set-all-reference-att-height (name textH / ref)
  (foreach ref (DTT--references name)
    (DTT--set-reference-att-height ref textH)
  )
  T
)

(defun DTT--set-definition-att-style (name textStyle / btr en d obj style)
  (setq btr   (tblobjname "BLOCK" name)
        style (DTT--valid-text-style textStyle))
  (if btr
    (progn
      (setq en (entnext btr))
      (while (and en (/= (cdr (assoc 0 (entget en))) "ENDBLK"))
        (setq d (entget en))
        (if (= (cdr (assoc 0 d)) "ATTDEF")
          (progn
            (setq obj (vl-catch-all-apply 'vlax-ename->vla-object (list en)))
            (if (not (vl-catch-all-error-p obj))
              (vl-catch-all-apply 'vla-put-StyleName (list obj style))
            )
          )
        )
        (setq en (entnext en))
      )
      T
    )
    nil
  )
)

(defun DTT--set-reference-att-style (ref textStyle / att style)
  (setq style (DTT--valid-text-style textStyle))
  (if ref
    (foreach att (degk--att-list ref)
      (vl-catch-all-apply 'vla-put-StyleName (list att style))
    )
  )
  ref
)

(defun DTT--set-all-reference-att-style (name textStyle / ref)
  (foreach ref (DTT--references name)
    (DTT--set-reference-att-style ref textStyle)
  )
  T
)
(defun DTT--current-space (/ doc)
  (setq doc (vla-get-ActiveDocument (vlax-get-acad-object)))
  (if (= (getvar "CVPORT") 1)
    (vla-get-PaperSpace doc)
    (vla-get-ModelSpace doc)
  )
)

(defun DTT--ss-from-vla-list (objs / ss obj en)
  (setq ss (ssadd))
  (foreach obj objs
    (if (and obj (= (type obj) 'VLA-OBJECT))
      (progn
        (setq en (vl-catch-all-apply 'vlax-vla-object->ename (list obj)))
        (if (and (not (vl-catch-all-error-p en)) en)
          (ssadd en ss)
        )
      )
    )
  )
  ss
)

(defun DTT--block-editor-active-p (/ v)
  (setq v (vl-catch-all-apply 'getvar (list "BLOCKEDITOR")))
  (and (not (vl-catch-all-error-p v)) (= v 1))
)

(defun DTT--run-cmd (args / r)
  (setq r (vl-catch-all-apply 'vl-cmdf args))
  (not (vl-catch-all-error-p r))
)

(defun DTT--editor-geometry-sets (stemLen rectW rectH / all i en d typ p q moveSS stemSS hw)
  (setq moveSS (ssadd)
        stemSS (ssadd)
        hw (/ rectW 2.0)
        ;; Yalniz Block Editor'daki mevcut DTT geometrisini sec. "_X"
        ;; tum block tanimlarindaki eski LINE/ATTDEF'leri de action'a aliyordu.
        all
          (ssget "_C"
            (list (- (- hw) 2.0) -2.0 0.0)
            (list (+ hw 2.0) (+ stemLen rectH 2.0) 0.0)
            '((0 . "LINE,ATTDEF"))))
  (if all
    (progn
      (setq i 0)
      (while (< i (sslength all))
        (setq en  (ssname all i)
              d   (entget en)
              typ (cdr (assoc 0 d)))
        (cond
          ((= typ "ATTDEF")
           (ssadd en moveSS))
          ((= typ "LINE")
           (setq p (cdr (assoc 10 d)) q (cdr (assoc 11 d)))
           (if (or (DTT--near-p p '(0.0 0.0 0.0) 0.000001)
                   (DTT--near-p q '(0.0 0.0 0.0) 0.000001))
             (ssadd en stemSS)
             (ssadd en moveSS)
           ))
        )
        (setq i (1+ i))
      )
    )
  )
  (list moveSS stemSS)
)

(defun DTT--author-dynamic (name stemLen rectW rectH / oldFiledia oldEcho oldLock entered before rectParam leaderParam sets moveSS stemSS f1 f2 actionPt leaderMoveActionPt leaderActionPt okMove okLeaderMove okStretch doc queued paramLabel leaderLabel)
  (setq oldFiledia (getvar "FILEDIA")
        oldEcho    (getvar "CMDECHO")
        oldLock    (vl-catch-all-apply 'getvar (list "BLOCKEDITLOCK"))
        entered    nil
        okMove     nil
        okLeaderMove nil
        okStretch  nil)
  (setvar "FILEDIA" 0)
  (setvar "CMDECHO" 0)
  (if (and (not (vl-catch-all-error-p oldLock)) (= oldLock 1))
    (vl-catch-all-apply 'setvar (list "BLOCKEDITLOCK" 0))
  )
  (if (DTT--run-cmd (list "_.BEDIT" name))
    (setq entered (DTT--block-editor-active-p))
  )
  (if entered
    (progn
      (setq paramLabel (list (+ (/ rectW 2.0) 6.0) stemLen 0.0)
            leaderLabel (list (+ (/ rectW 2.0) 12.0) stemLen 0.0))
      (setq before (entlast))
      (if (DTT--run-cmd
             (list "_.BPARAMETER" "_Point"
                   (list 0.0 stemLen 0.0)
                   paramLabel
                   "0"))
        (setq rectParam (entlast))
      )
      (if (and rectParam (not (eq rectParam before)))
        (progn
          (setq sets     (DTT--editor-geometry-sets stemLen rectW rectH)
                moveSS   (car sets)
                stemSS   (cadr sets)
                f1       (list -1.0 (- stemLen 1.0) 0.0)
                f2       (list 1.0 (+ stemLen 1.0) 0.0)
                actionPt (list (+ (/ rectW 2.0) 8.0) (+ stemLen rectH 8.0) 0.0))
          (if (> (sslength moveSS) 0)
            (setq okMove
              (DTT--run-cmd
                (list "_.BACTIONTOOL" "_Move" rectParam
                      (list 0.0 stemLen 0.0)
                      moveSS "" actionPt)))
          )
          (setq before (entlast))
          (if (DTT--run-cmd
                (list "_.BPARAMETER" "_Point"
                      (list 0.0 stemLen 0.0)
                      leaderLabel
                      "1"))
            (setq leaderParam (entlast)))
           (if (and leaderParam (not (eq leaderParam before)))
             (progn
               (setq leaderMoveActionPt
                 (list (+ (/ rectW 2.0) 14.0) (+ stemLen rectH 12.0) 0.0)
                     leaderActionPt
                 (list (+ (/ rectW 2.0) 20.0) (+ stemLen rectH 18.0) 0.0))
               (if (> (sslength moveSS) 0)
                 (setq okLeaderMove
                   (DTT--run-cmd
                     (list "_.BACTIONTOOL" "_Move" leaderParam
                           (list 0.0 stemLen 0.0)
                           moveSS "" leaderMoveActionPt))))
               (if (> (sslength stemSS) 0)
                 (setq okStretch
                  (DTT--run-cmd
                    (list "_.BACTIONTOOL" "_sTretch" leaderParam
                      (list 0.0 stemLen 0.0)
                      f1 f2 stemSS "" leaderActionPt))))
            )
          )
        )
      )
    )
  )
  (setvar "FILEDIA" oldFiledia)
  (setvar "CMDECHO" oldEcho)
  (if (not (vl-catch-all-error-p oldLock))
    (vl-catch-all-apply 'setvar (list "BLOCKEDITLOCK" oldLock))
  )
  (setq *DTT--pending-dynamic-ok* (and okMove okLeaderMove okStretch)
        *DTT--resume-queued* nil)
  ;; BCLOSE mevcut Lisp cagrisini sonlandirir. Kaydet/kapat ve devam
  ;; islemlerini komut kuyruguna birakiyoruz.
  (if entered
    (progn
      (setq doc (vla-get-ActiveDocument (vlax-get-acad-object))
            queued
              (vl-catch-all-apply
                'vla-SendCommand
                (list doc "_.BSAVE\n_.BCLOSE\n(DTT--resume)\n")))
      (if (not (vl-catch-all-error-p queued))
        (setq *DTT--resume-queued* T)
      )
    )
  )
  (and okMove okLeaderMove okStretch)
)

(defun DTT--reference-name (obj / n)
  (setq n (degk--blockname obj))
  (if n (strcase n) "")
)

(defun DTT--references (name / ss i en obj out target)
  (setq target (strcase name)
        out nil
        ss (ssget "_X" '((0 . "INSERT"))))
  (if ss
    (progn
      (setq i 0)
      (while (< i (sslength ss))
        (setq en  (ssname ss i)
              obj (vl-catch-all-apply 'vlax-ename->vla-object (list en)))
        (if (and (not (vl-catch-all-error-p obj))
                 (= (DTT--reference-name obj) target))
          (setq out (cons obj out))
        )
        (setq i (1+ i))
      )
    )
  )
  (reverse out)
)

(defun DTT--reference-bases (name / refs ref ip out)
  (setq refs (DTT--references name)
        out nil)
  (foreach ref refs
    (setq ip (DTT--vla-point ref 'InsertionPoint))
    (if ip (setq out (cons ip out)))
  )
  out
)

(defun DTT--near-xy-p (a b tol)
  (and a b
       (<= (distance (list (car a) (cadr a) 0.0)
                     (list (car b) (cadr b) 0.0)) tol))
)

(defun DTT--reference-at-base (pt refs tol / hit ref ip fallback fallbackDz dz)
  (while (and refs (null hit))
    (setq ref  (car refs)
          refs (cdr refs)
          ip   (DTT--vla-point ref 'InsertionPoint))
    (if (and ip (DTT--near-p pt ip tol))
      (setq hit ref)
      (if (and ip (DTT--near-xy-p pt ip tol))
        (progn
          (setq dz (abs (- (if (caddr pt) (caddr pt) 0.0)
                           (if (caddr ip) (caddr ip) 0.0))))
          (if (or (null fallbackDz) (< dz fallbackDz))
            (setq fallback ref fallbackDz dz))))
    )
  )
  (if hit hit fallback)
)

(defun DTT--reference-ename (ref / en)
  (setq en (if ref (vl-catch-all-apply 'vlax-vla-object->ename (list ref))))
  (if (or (null en) (vl-catch-all-error-p en)) nil en)
)

(defun DTT--set-reference-tray (ref tray / app en handle ed payload)
  (setq app    "DTT_TRAY_REF"
        en     (DTT--reference-ename ref)
        handle (if tray (cdr (assoc 5 (entget tray)))))
  (if (and en handle)
    (progn
      (if (not (tblsearch "APPID" app)) (regapp app))
      (setq payload (list app (cons 1000 handle))
            ed      (entget en '("*"))
            ed      (DT--xdata-set-app ed app payload))
      (entmod ed)
      (entupd en)
      ref)
  )
)

(defun DTT--reference-tray-handle (ref / app en ed xd rec item handle)
  (setq app "DTT_TRAY_REF"
        en  (DTT--reference-ename ref))
  (if en
    (progn
      (setq ed (entget en (list app))
            xd (assoc -3 ed))
      (if xd
        (progn
          (setq rec (cadr xd))
          (foreach item (cdr rec)
            (if (= (car item) 1000) (setq handle (cdr item))))))))
  handle
)

(defun DTT--reference-for-tray (tray refs / handle ref hit)
  (setq handle (if tray (cdr (assoc 5 (entget tray)))))
  (while (and handle refs (null hit))
    (setq ref  (car refs)
          refs (cdr refs))
    (if (= (strcase handle)
           (strcase (if (DTT--reference-tray-handle ref)
                      (DTT--reference-tray-handle ref) "")))
      (setq hit ref)))
  hit
)

(defun DTT--near-any-point-p (pt points tol / found p)
  (setq found nil)
  (while (and points (not found))
    (setq p (car points)
          points (cdr points))
    (if (DTT--near-p pt p tol) (setq found T))
  )
  found
)

(defun DTT--vla-point (obj prop / v)
  (setq v (vl-catch-all-apply 'vlax-get-property (list obj prop)))
  (if (vl-catch-all-error-p v)
    nil
    (cond
      ((= (type v) 'VARIANT)  (vlax-safearray->list (vlax-variant-value v)))
      ((= (type v) 'SAFEARRAY) (vlax-safearray->list v))
      ((listp v) v)
      (T nil)
    )
  )
)

(defun DTT--att-local-x (ref att / ip ap rot dx dy)
  (setq ip  (DTT--vla-point ref 'InsertionPoint)
        ap  (DTT--vla-point att 'InsertionPoint)
        rot (vl-catch-all-apply 'vla-get-Rotation (list ref)))
  (if (vl-catch-all-error-p rot) (setq rot 0.0))
  (if (and ip ap)
    (progn
      (setq dx (- (car ap) (car ip))
            dy (- (cadr ap) (cadr ip)))
      (+ (* dx (cos rot)) (* dy (sin rot)))
    )
    0.0
  )
)

(defun DTT--cleanup-reference-atts (ref / atts groups att tag pair group keep minX x keepVal val en removed)
  (setq atts (degk--att-list ref)
        groups nil
        removed nil)
  (foreach att atts
    (setq tag (vl-catch-all-apply 'vla-get-TagString (list att)))
    (if (not (vl-catch-all-error-p tag))
      (progn
        (setq tag (strcase tag)
              pair (assoc tag groups))
        (if pair
          (setq groups (subst (cons tag (cons att (cdr pair))) pair groups))
          (setq groups (cons (list tag att) groups))
        )
      )
    )
  )
  (foreach group groups
    (setq keep nil minX nil keepVal "")
    (foreach att (cdr group)
      (setq x   (DTT--att-local-x ref att)
            val (vl-catch-all-apply 'vla-get-TextString (list att)))
      (if (and (not (vl-catch-all-error-p val)) (/= val "") (= keepVal ""))
        (setq keepVal val)
      )
      (if (or (null minX) (< x minX))
        (setq minX x keep att)
      )
    )
    (if keep
      (progn
        (if (/= keepVal "")
          (vl-catch-all-apply 'vla-put-TextString (list keep keepVal))
        )
        (foreach att (cdr group)
          (if (not (eq att keep))
            (progn
              (vl-catch-all-apply 'vla-Delete (list att))
              (setq removed T)
            )
          )
        )
      )
    )
  )
  ;; Konum sifirlama yalniz eski kopya ATTREF silindiyse gerekir. Aksi halde
  ;; dinamik Move action ile tasinan attribute'lari eski yerlerine geri ceker.
  (if removed
    (progn
      (setq en (vl-catch-all-apply 'vlax-vla-object->ename (list ref)))
      (if (and (not (vl-catch-all-error-p en)) en)
        (degk--reset-insert-attrs en)
      )
    )
  )
  ref
)

(defun DTT--cleanup-all-reference-atts (name / refs ref)
  (setq refs (DTT--references name))
  (foreach ref refs (DTT--cleanup-reference-atts ref))
  refs
)

(defun DTT--near-p (a b tol)
  (and a b (<= (distance (DTT--pt3 a) (DTT--pt3 b)) tol))
)

(defun DTT--block-version-marker (name / app btr ed xd rec item value)
  (setq app "DTT_LABEL_VERSION"
        btr (tblobjname "BLOCK" name))
  (if btr
    (progn
      (setq ed (entget btr (list app))
            xd (assoc -3 ed))
      (if xd
        (progn
          (setq rec (cadr xd))
          (foreach item (cdr rec)
            (if (= (car item) 1000) (setq value (cdr item))))))))
  value
)

(defun DTT--block-clean-version-value (name / blk v marker)
  (setq blk (DTT--block-object name))
  (if (and blk (vlax-property-available-p blk 'Comments))
    (setq v (vl-catch-all-apply 'vla-get-Comments (list blk)))
  )
  (setq marker (DTT--block-version-marker name))
  (cond
    (marker marker)
    ((and (not (vl-catch-all-error-p v)) (= (type v) 'STR) (/= v "")) v)
    (T ""))
)

(defun DTT--block-clean-version-p (name)
  (= (DTT--block-clean-version-value name)
     "DTT_LABEL_WORLD0_V7_LEADER_GRIP")
)

(defun DTT--set-block-clean-version (name / app version blk r btr ed payload markerOK)
  (setq app     "DTT_LABEL_VERSION"
        version "DTT_LABEL_WORLD0_V7_LEADER_GRIP")
  (setq blk (DTT--block-object name))
  (if (and blk (vlax-property-available-p blk 'Comments T))
    (progn
      (setq r
        (vl-catch-all-apply
          'vla-put-Comments
          (list blk version))))
  )
  (setq btr (tblobjname "BLOCK" name))
  (if btr
    (progn
      (if (not (tblsearch "APPID" app)) (regapp app))
      (setq payload (list app (cons 1000 version))
            ed      (entget btr '("*"))
            ed      (DT--xdata-set-app ed app payload)
            markerOK (entmod ed))))
  (or markerOK (and r (not (vl-catch-all-error-p r))))
)

(defun DTT--reference-leader-grip-version-p (ref / name)
  (setq name (if ref (DTT--reference-name ref) ""))
  (= (DTT--block-clean-version-value name)
     "DTT_LABEL_WORLD0_V7_LEADER_GRIP")
)

(defun DTT--definition-v2-p (name / btr en d p q found)
  (setq btr (tblobjname "BLOCK" name)
        found nil)
  (if btr
    (progn
      (setq en (entnext btr))
      (while (and en (not found) (/= (cdr (assoc 0 (entget en))) "ENDBLK"))
        (setq d (entget en))
        (if (= (cdr (assoc 0 d)) "LINE")
          (progn
            (setq p (cdr (assoc 10 d)) q (cdr (assoc 11 d)))
            (if (or (and (DTT--near-p p '(0.0 0.0 0.0) 0.000001)
                         (> (distance p q) 0.000001))
                    (and (DTT--near-p q '(0.0 0.0 0.0) 0.000001)
                         (> (distance p q) 0.000001)))
              (setq found T)
            )
          )
        )
        (setq en (entnext en))
      )
    )
  )
  found
)

(defun DTT--definition-size-p (name rectW rectH / btr en d p q a minX minY maxX maxY w h)
  (setq btr (tblobjname "BLOCK" name))
  (if btr
    (progn
      (setq en (entnext btr))
      (while (and en (/= (cdr (assoc 0 (entget en))) "ENDBLK"))
        (setq d (entget en))
        (if (= (cdr (assoc 0 d)) "LINE")
          (progn
            (setq p (cdr (assoc 10 d)) q (cdr (assoc 11 d)))
            ;; Base noktasindan baslayan stem cizgisi dikdortgen olcusune girmez.
            (if (not (or (DTT--near-p p '(0.0 0.0 0.0) 0.000001)
                         (DTT--near-p q '(0.0 0.0 0.0) 0.000001)))
              (foreach a (list p q)
                (if a
                  (progn
                    (setq minX (if minX (min minX (car a)) (car a))
                          minY (if minY (min minY (cadr a)) (cadr a))
                          maxX (if maxX (max maxX (car a)) (car a))
                          maxY (if maxY (max maxY (cadr a)) (cadr a)))
                  )
                )
              )
            )
          )
        )
        (setq en (entnext en))
      )
    )
  )
  (if (and minX minY maxX maxY)
    (progn
      (setq w (- maxX minX) h (- maxY minY))
      (and (<= (abs (- w rectW)) 0.0001)
           (<= (abs (- h rectH)) 0.0001))
    )
    nil
  )
)

(defun DTT--resize-map-value (v oldMin oldMax newMin newMax)
  (cond
    ((equal v oldMin 0.0001) newMin)
    ((equal v oldMax 0.0001) newMax)
    (T v)
  )
)

(defun DTT--resize-map-point (p oldMinX oldMaxX newMinX newMaxX oldMinY oldMaxY newMinY newMaxY)
  (list
    (DTT--resize-map-value (car p) oldMinX oldMaxX newMinX newMaxX)
    (DTT--resize-map-value (cadr p) oldMinY oldMaxY newMinY newMaxY)
    (if (caddr p) (caddr p) 0.0)
  )
)

(defun DTT--resize-label-definition (name rectW rectH textH textStyle / btr en d p q a minX minY maxX maxY newMinX newMaxX newMinY newMaxY np nq obj tag layout x y)
  (setq btr (tblobjname "BLOCK" name))
  (if btr
    (progn
      ;; Dinamik action referanslarini korumak icin mevcut LINE/ATTDEF
      ;; objeleri silmeden yalnizca geometrilerini guncelle.
      (setq en (entnext btr))
      (while (and en (/= (cdr (assoc 0 (entget en))) "ENDBLK"))
        (setq d (entget en))
        (if (= (cdr (assoc 0 d)) "LINE")
          (progn
            (setq p (cdr (assoc 10 d)) q (cdr (assoc 11 d)))
            (if (not (or (DTT--near-p p '(0.0 0.0 0.0) 0.000001)
                         (DTT--near-p q '(0.0 0.0 0.0) 0.000001)))
              (foreach a (list p q)
                (setq minX (if minX (min minX (car a)) (car a))
                      minY (if minY (min minY (cadr a)) (cadr a))
                      maxX (if maxX (max maxX (car a)) (car a))
                      maxY (if maxY (max maxY (cadr a)) (cadr a)))
              )
            )
          )
        )
        (setq en (entnext en))
      )
      (if (and minX minY maxX maxY (> rectW 0.0) (> rectH 0.0))
        (progn
          (setq newMinX (- (/ rectW 2.0))
                newMaxX (/ rectW 2.0)
                newMinY minY
                newMaxY (+ minY rectH)
                textH   (if (and (numberp textH) (> textH 0.0)) textH 8.0)
                layout  (DTT--attribute-layout rectW rectH newMinY textH)
                en      (entnext btr))
          (while (and en (/= (cdr (assoc 0 (entget en))) "ENDBLK"))
            (setq d (entget en))
            (cond
              ((= (cdr (assoc 0 d)) "LINE")
               (setq p (cdr (assoc 10 d)) q (cdr (assoc 11 d)))
               (if (not (or (DTT--near-p p '(0.0 0.0 0.0) 0.000001)
                            (DTT--near-p q '(0.0 0.0 0.0) 0.000001)))
                 (progn
                   (setq np (DTT--resize-map-point p minX maxX newMinX newMaxX minY maxY newMinY newMaxY)
                         nq (DTT--resize-map-point q minX maxX newMinX newMaxX minY maxY newMinY newMaxY)
                         d  (subst (cons 10 np) (assoc 10 d) d)
                         d  (subst (cons 11 nq) (assoc 11 d) d))
                   (entmod d)
                   (entupd en)
                 )
               )
              )
              ((= (cdr (assoc 0 d)) "ATTDEF")
               (setq tag (DTT--normalize-att-tag (cdr (assoc 2 d)))
                     x   (nth 0 layout)
                     y   (cond
                           ((= tag "TAVA_TÝPÝ") (nth 1 layout))
                           ((= tag "GENÝÞLÝK") (nth 2 layout))
                           ((= tag "YANAK_YÜKSEKLÝÐÝ") (nth 3 layout))
                           ((= tag "YÜKSEKLÝK") (nth 4 layout))
                           (T nil)))
               (if y
                 (progn
                   (setq obj (vl-catch-all-apply 'vlax-ename->vla-object (list en)))
                   (if (not (vl-catch-all-error-p obj))
                     (progn
                       (vl-catch-all-apply 'vla-put-InsertionPoint
                         (list obj (vlax-3d-point (list x y 0.0))))
                       (vl-catch-all-apply 'vla-put-Height (list obj textH))
                       (vl-catch-all-apply 'vla-put-StyleName
                         (list obj (DTT--valid-text-style textStyle)))
                     )
                   )
                   (entupd en)
                 )
               )
              )
            )
            (setq en (entnext en))
          )
          (entupd btr)
          (DTT--definition-size-p name rectW rectH)
        )
        nil
      )
    )
    nil
  )
)

(defun DTT--definition-attdefs-ok-p (name / btr en d tag tags leftOK)
  (setq btr (tblobjname "BLOCK" name)
        tags nil
        leftOK T)
  (if btr
    (progn
      (setq en (entnext btr))
      (while (and en (/= (cdr (assoc 0 (entget en))) "ENDBLK"))
        (setq d (entget en))
        (if (= (cdr (assoc 0 d)) "ATTDEF")
          (progn
            (setq tag (cdr (assoc 2 d)))
            (if tag (setq tags (cons (strcase tag) tags)))
            (if (or (null (assoc 10 d)) (>= (car (cdr (assoc 10 d))) -0.000001))
              (setq leftOK nil)
            )
          )
        )
        (setq en (entnext en))
      )
    )
  )
  (and leftOK
       (= (length tags) 4)
       (member "TAVA_TÝPÝ" tags)
       (member "GENÝÞLÝK" tags)
       (member "YANAK_YÜKSEKLÝÐÝ" tags)
       (member "YÜKSEKLÝK" tags))
)

(defun DTT--block-dynamic-p (name / blk v refs)
  (setq blk (DTT--block-object name)
        v nil)
  (if (and blk (vlax-property-available-p blk 'IsDynamicBlock))
    (setq v (vl-catch-all-apply 'vla-get-IsDynamicBlock (list blk)))
  )
  (if (and (not (vl-catch-all-error-p v)) (= v :vlax-true))
    T
    (progn
      (setq refs (DTT--references name))
      (if refs
        (progn
          (setq v (vl-catch-all-apply 'vla-get-IsDynamicBlock (list (car refs))))
          (and (not (vl-catch-all-error-p v)) (= v :vlax-true))
        )
        nil
      )
    )
  )
)

(defun DTT--old-stem-line (ref rectH lay / ip rot norm expected ss i en d p q best bestD dd other)
  (setq ip  (DTT--vla-point ref 'InsertionPoint)
        rot (vl-catch-all-apply 'vla-get-Rotation (list ref)))
  (if (vl-catch-all-error-p rot) (setq rot 0.0))
  (if ip
    (progn
      (setq norm (list (- (sin rot)) (cos rot) 0.0)
            expected (DTT--move ip norm (- (/ rectH 2.0)))
            ss (ssget "_X" (list '(0 . "LINE") (cons 8 lay)))
            i 0
            best nil
            bestD nil)
      (if ss
        (while (< i (sslength ss))
          (setq en (ssname ss i)
                d  (entget en)
                p  (cdr (assoc 10 d))
                q  (cdr (assoc 11 d)))
          (if (and p q)
            (progn
              (if (< (distance p expected) (distance q expected))
                (setq dd (distance p expected) other q)
                (setq dd (distance q expected) other p)
              )
              (if (and (< dd 0.5) (or (null bestD) (< dd bestD)))
                (setq best (list en other (distance other expected)) bestD dd)
              )
            )
          )
          (setq i (1+ i))
        )
      )
    )
  )
  best
)

(defun DTT--upgrade-old-references (name rectH lay fallbackStem / refs ref hit ip rot norm base stem out)
  (setq refs (DTT--references name)
        out nil)
  (foreach ref refs
    (setq hit (DTT--old-stem-line ref rectH lay))
    (if hit
      (progn
        (setq base (cadr hit)
              stem (caddr hit))
        (entdel (car hit))
      )
      (progn
        (setq ip  (DTT--vla-point ref 'InsertionPoint)
              rot (vl-catch-all-apply 'vla-get-Rotation (list ref)))
        (if (vl-catch-all-error-p rot) (setq rot 0.0))
        (setq norm (list (- (sin rot)) (cos rot) 0.0)
              stem fallbackStem
              base (DTT--move ip norm (- (+ stem (/ rectH 2.0)))))
      )
    )
    (if base
      (progn
        (vl-catch-all-apply 'vla-put-InsertionPoint (list ref (vlax-3d-point base)))
        (setq out (cons (list ref (list 0.0 stem)) out))
      )
    )
  )
  (reverse out)
)

(defun DTT--dynamic-axis-key (name / up compact digits i ch axis key)
  (if name
    (progn
      (setq up      (strcase (vl-string-trim " \t" name))
            compact ""
            digits  ""
            i       1)
      (while (<= i (strlen up))
        (setq ch (substr up i 1))
        (if (not (member ch '(" " "\t" "_" "-")))
          (setq compact (strcat compact ch)))
        (if (member ch '("0" "1" "2" "3" "4" "5" "6" "7" "8" "9"))
          (setq digits (strcat digits ch)))
        (setq i (1+ i)))
      (cond
        ((wcmatch compact "*POSITION*X*,*KONUM*X*") (setq axis "X"))
        ((wcmatch compact "*POSITION*Y*,*KONUM*Y*") (setq axis "Y")))
      (if axis
        (progn
          ;; AutoCAD: Position1 X; bazi GstarCAD surumleri: Position X1.
          ;; Her iki yazimi da ayni Point parametre grubuna indir.
          (setq key (strcat "P" (if (= digits "") "0" digits)))
          (list key axis)))))
)

(defun DTT--dynamic-point-groups (ref / props prop propName parsed key axis pair groups namedGroups xProps yProps ordered index)
  ;; Point parametrelerini adlariyla eslestir. ActiveX'in property liste sirasi
  ;; block varyasyonlarinda degisebildigi icin "birinci/ikinci gorulen" kullanilmaz.
  (setq props (vl-catch-all-apply 'vlax-invoke (list ref 'GetDynamicBlockProperties))
        groups nil)
  (if (not (vl-catch-all-error-p props))
    (foreach prop props
      (setq propName (vl-catch-all-apply 'vla-get-PropertyName (list prop))
            parsed
              (if (vl-catch-all-error-p propName)
                nil
                (DTT--dynamic-axis-key propName)))
      (if parsed
        (progn
          (setq key  (car parsed)
                axis (cadr parsed)
                pair (assoc key groups))
          (if (= axis "X")
            (setq xProps (append xProps (list prop)))
            (setq yProps (append yProps (list prop))))
          (if pair
            (setq groups
              (subst
                (if (= axis "X")
                  (list key prop (caddr pair))
                  (list key (cadr pair) prop))
                pair groups))
            (setq groups
              (cons
                (if (= axis "X")
                  (list key prop nil)
                  (list key nil prop))
                groups))))))
  )
  (setq namedGroups
    (vl-remove-if
      '(lambda (item) (or (null (cadr item)) (null (caddr item))))
      groups))
  (setq namedGroups
    (vl-sort namedGroups
      '(lambda (a b)
         (< (atoi (substr (car a) 2)) (atoi (substr (car b) 2))))))
  ;; Bazi CAD surumleri iki Point parametresine de ayni gorunen adi verir.
  ;; Bu durumda isim gruplari birlesir; eski ve calisan X/Y olusma sirasi
  ;; yedek yol olarak iki parametreyi yeniden eslestirir.
  (if (>= (length namedGroups) 2)
    namedGroups
    (progn
      (setq ordered nil index 0)
      (while (and xProps yProps)
        (setq ordered
          (append ordered
            (list (list (strcat "O" (itoa index))
                        (car xProps) (car yProps))))
              xProps (cdr xProps)
              yProps (cdr yProps)
              index  (1+ index)))
      ordered))
)

(defun DTT--dynamic-point-value (ref index / group x y)
  (setq group (nth index (DTT--dynamic-point-groups ref)))
  (if group
    (progn
      (setq x (vlax-variant-value (vla-get-Value (cadr group)))
            y (vlax-variant-value (vla-get-Value (caddr group))))
      (if (and (numberp x) (numberp y)) (list x y))))
)

(defun DTT--leader-grip-hidden-pos (rectPos leaderPos defaultY)
  (list (- (car rectPos) (car leaderPos))
        (+ (- (cadr rectPos) (cadr leaderPos)) defaultY))
)

(defun DTT--leader-grip-rect-pos (hiddenPos leaderPos defaultY)
  (list (+ (car hiddenPos) (car leaderPos))
        (- (+ (cadr hiddenPos) (cadr leaderPos)) defaultY))
)

(defun DTT--dynamic-default-y (ref / name y)
  (setq name (if ref (DTT--reference-name ref) "")
        y    (if (/= name "") (DTT--definition-rect-base-y name)))
  (if (numberp y) y 0.0)
)

(defun DTT--dynamic-position (ref / hidden leader defaultY)
  (setq hidden (DTT--dynamic-point-value ref 0))
  (if (and hidden (DTT--reference-leader-grip-version-p ref))
    (progn
      (setq leader   (DTT--dynamic-point-value ref 1)
            defaultY (DTT--dynamic-default-y ref))
      (if leader
        (DTT--leader-grip-rect-pos hidden leader defaultY)
        hidden))
    hidden)
)

(defun DTT--capture-reference-positions (name fallbackStem / refs ref pos out)
  (setq refs (DTT--references name) out nil)
  (foreach ref refs
    (setq pos (DTT--dynamic-position ref))
    (if (null pos) (setq pos (list 0.0 fallbackStem)))
    (setq out (cons (list ref pos) out))
  )
  (reverse out)
)

(defun DTT--put-dynamic-value (prop value / old typ r)
  (setq old (vla-get-Value prop)
        typ (vlax-variant-type old)
        r   (vl-catch-all-apply 'vla-put-Value
              (list prop (vlax-make-variant value typ))))
  (not (vl-catch-all-error-p r))
)

(defun DTT--set-dynamic-point-value (ref index pos / group gotX gotY)
  (setq group (nth index (DTT--dynamic-point-groups ref)))
  (if (and group pos)
    (progn
      (setq gotX (DTT--put-dynamic-value (cadr group) (car pos))
            gotY (DTT--put-dynamic-value (caddr group) (cadr pos)))
      (and gotX gotY)))
)

(defun DTT--set-dynamic-position (ref pos / leader hidden defaultY)
  (if (DTT--reference-leader-grip-version-p ref)
    (progn
      (setq leader   (DTT--dynamic-point-value ref 1)
            defaultY (DTT--dynamic-default-y ref))
      (if leader
        (progn
          (setq hidden (DTT--leader-grip-hidden-pos pos leader defaultY))
          (DTT--set-dynamic-point-value ref 0 hidden))
        (DTT--set-dynamic-point-value ref 0 pos)))
    (DTT--set-dynamic-point-value ref 0 pos))
)

(defun DTT--dynamic-leader-position (ref)
  (DTT--dynamic-point-value ref 1)
)

(defun DTT--set-dynamic-leader-position (ref pos / rect leaderOK rectOK)
  (if (DTT--reference-leader-grip-version-p ref)
    (progn
      ;; Gorunen grip cizgi ucunda kalir; leader stretch olurken gizli
      ;; parametre dikdortgenin mevcut konumunu telafi eder.
      (setq rect      (DTT--dynamic-position ref)
            leaderOK (DTT--set-dynamic-point-value ref 1 pos)
            rectOK   (if rect (DTT--set-dynamic-position ref rect) T))
      (and leaderOK rectOK))
    (DTT--set-dynamic-point-value ref 1 pos))
)

(defun DTT--dynamic-reference-p (ref / v groups)
  (setq v      (vl-catch-all-apply 'vla-get-IsDynamicBlock (list ref))
        groups (DTT--dynamic-point-groups ref))
  (or (and (not (vl-catch-all-error-p v)) (= v :vlax-true))
      (>= (length groups) 2))
)

(defun DTT--set-dynamic-label-geometry (ref rectPos leaderPos / groups defaultY hidden ok)
  ;; Referansi patlatmadan ayni dinamik INSERT uzerindeki iki Point
  ;; parametresini guncelle; islem sonrasinda da dinamikligi dogrula.
  (setq groups (DTT--dynamic-point-groups ref))
  (if (>= (length groups) 2)
    (if (DTT--reference-leader-grip-version-p ref)
      (progn
        (setq defaultY (DTT--dynamic-default-y ref)
              hidden   (DTT--leader-grip-hidden-pos rectPos leaderPos defaultY)
              ;; Once gorunen grip/leader, sonra gizli konum telafisi.
              ok       (and (DTT--set-dynamic-point-value ref 1 leaderPos)
                            (DTT--set-dynamic-point-value ref 0 hidden)))
        (and ok
             (DTT--near-p (DTT--dynamic-position ref) rectPos 0.000001)
             (DTT--near-p (DTT--dynamic-leader-position ref) leaderPos 0.000001)))
      (and (DTT--set-dynamic-position ref rectPos)
           (DTT--set-dynamic-leader-position ref leaderPos)))
    nil)
)

(defun DTT--restore-reference-positions (items / item)
  (foreach item items
    (DTT--set-dynamic-position (car item) (cadr item))
  )
)

(defun DTT--normalize-att-tag (tag / up)
  (setq up (strcase tag))
  (cond
    ((or (= up "1") (= up "TAVA_TÝPÝ") (= up "TAVA_TIPI")) "TAVA_TÝPÝ")
    ((or (= up "2") (= up "GENÝÞLÝK") (= up "GENISLIK")) "GENÝÞLÝK")
    ((or (= up "3") (= up "YANAK_YÜKSEKLÝÐÝ") (= up "YANAK_YUKSEKLIGI")) "YANAK_YÜKSEKLÝÐÝ")
    ((or (= up "4") (= up "YÜKSEKLÝK") (= up "YUKSEKLIK")
         (= up "TAVA_YÜKSEKLÝÐÝ") (= up "TAVA_YUKSEKLIGI")) "YÜKSEKLÝK")
    (T up)
  )
)

(defun DTT--reference-att-values (ref / atts att tag val pair out)
  (setq atts (degk--att-list ref)
        out nil)
  (foreach att atts
    (setq tag (vl-catch-all-apply 'vla-get-TagString (list att))
          val (vl-catch-all-apply 'vla-get-TextString (list att)))
    (if (and (not (vl-catch-all-error-p tag))
             (not (vl-catch-all-error-p val)))
      (progn
        (setq tag (DTT--normalize-att-tag tag)
              pair (assoc tag out))
        (cond
          ((null pair) (setq out (cons (cons tag val) out)))
          ((and (= (cdr pair) "") (/= val ""))
           (setq out (subst (cons tag val) pair out)))
        )
      )
    )
  )
  out
)

(defun DTT--set-reference-att-values (ref values / att tag pair)
  (foreach att (degk--att-list ref)
    (setq tag (vl-catch-all-apply 'vla-get-TagString (list att)))
    (if (not (vl-catch-all-error-p tag))
      (progn
        (setq pair (assoc (DTT--normalize-att-tag tag) values))
        (if pair
          (vl-catch-all-apply 'vla-put-TextString (list att (cdr pair)))
        )
      )
    )
  )
  ref
)

(defun DTT--set-reference-att-rotation (ref angle / att)
  (if (and ref (numberp angle))
    (foreach att (degk--att-list ref)
      (vl-catch-all-apply 'vla-put-Rotation (list att angle))
    )
  )
  ref
)

(defun DTT--definition-att-points (name / btr en d tag pt out)
  (setq btr (tblobjname "BLOCK" name)
        out nil)
  (if btr
    (progn
      (setq en (entnext btr))
      (while (and en (/= (cdr (assoc 0 (entget en))) "ENDBLK"))
        (setq d (entget en))
        (if (= (cdr (assoc 0 d)) "ATTDEF")
          (progn
            (setq tag (cdr (assoc 2 d))
                  pt  (cdr (assoc 10 d)))
            (if (and tag pt)
              (setq out
                (cons (cons (DTT--normalize-att-tag tag) (DTT--pt3 pt)) out))
            )
          )
        )
        (setq en (entnext en))
      )
    )
  )
  out
)

(defun DTT--definition-rect-base-y (name / btr en d p q y best)
  (setq btr (tblobjname "BLOCK" name)
        best nil)
  (if btr
    (progn
      (setq en (entnext btr))
      (while (and en (/= (cdr (assoc 0 (entget en))) "ENDBLK"))
        (setq d (entget en))
        (if (= (cdr (assoc 0 d)) "LINE")
          (progn
            (setq p (cdr (assoc 10 d))
                  q (cdr (assoc 11 d)))
            (if (and p q
                     (> (distance p q) 0.001)
                     (equal (cadr p) (cadr q) 0.000001))
              (progn
                (setq y (cadr p))
                (if (or (null best) (< y best)) (setq best y))
              )
            )
          )
        )
        (setq en (entnext en))
      )
    )
  )
  best
)

(defun DTT--align-reference-atts (ref blockName dynPos defaultY / defs base baseY rot xs ys dx dy att tag rec local world)
  (setq defs (DTT--definition-att-points blockName)
        base (DTT--vla-point ref 'InsertionPoint)
        baseY (DTT--definition-rect-base-y blockName)
        rot  (DTT--vla-number-or ref 'Rotation 0.0)
        xs   (DTT--vla-number-or ref 'XScaleFactor 1.0)
        ys   (DTT--vla-number-or ref 'YScaleFactor 1.0)
        dx   (if (and dynPos (numberp (car dynPos))) (car dynPos) 0.0)
        dy   (if (and dynPos (numberp (cadr dynPos)))
               (- (cadr dynPos) (if (numberp baseY) baseY defaultY))
               0.0))
  (if (and ref base defs)
    (foreach att (degk--att-list ref)
      (setq tag (vl-catch-all-apply 'vla-get-TagString (list att)))
      (if (not (vl-catch-all-error-p tag))
        (progn
          (setq rec (assoc (DTT--normalize-att-tag tag) defs))
          (if rec
            (progn
              (setq local (cdr rec)
                    world
                      (DTT--local-to-world
                        base rot
                        (+ (car local) dx)
                        (+ (cadr local) dy)
                        xs ys))
              (vl-catch-all-apply
                'vla-put-InsertionPoint (list att (vlax-3d-point world)))
              (if (vlax-property-available-p att 'TextAlignmentPoint T)
                (vl-catch-all-apply
                  'vla-put-TextAlignmentPoint (list att (vlax-3d-point world)))
              )
              (vl-catch-all-apply 'vla-put-Rotation (list att rot))
            )
          )
        )
      )
    )
  )
  ref
)

(defun DTT--angles-equal-p (a b tol)
  (and (numberp a)
       (numberp b)
       (equal (sin a) (sin b) tol)
       (equal (cos a) (cos b) tol))
)

(defun DTT--vla-number-or (obj prop fallback / v)
  (setq v (vl-catch-all-apply 'vlax-get-property (list obj prop)))
  (if (and (not (vl-catch-all-error-p v)) (numberp v)) v fallback)
)

(defun DTT--migrate-reference (ref newName dynPos / en ed ownerEn owner ip rot xs ys zs lay vals obj atts att trayHandle tray)
  (setq en (vl-catch-all-apply 'vlax-vla-object->ename (list ref)))
  (if (and (not (vl-catch-all-error-p en)) en)
    (progn
      (setq ed      (entget en)
            ownerEn (cdr (assoc 330 ed))
            owner   (if ownerEn
                      (vl-catch-all-apply 'vlax-ename->vla-object (list ownerEn))
                      nil)
            ip      (DTT--vla-point ref 'InsertionPoint)
            rot     (DTT--vla-number-or ref 'Rotation 0.0)
            xs      (DTT--vla-number-or ref 'XScaleFactor 1.0)
            ys      (DTT--vla-number-or ref 'YScaleFactor 1.0)
            zs      (DTT--vla-number-or ref 'ZScaleFactor 1.0)
            lay     (vl-catch-all-apply 'vla-get-Layer (list ref))
            vals    (DTT--reference-att-values ref)
            trayHandle (DTT--reference-tray-handle ref))
      (if (or (vl-catch-all-error-p owner) (null owner))
        (setq owner (DTT--current-space))
      )
      (if (vl-catch-all-error-p lay) (setq lay "0"))
      (if ip
        (setq obj
          (vl-catch-all-apply
            'vla-InsertBlock
            (list owner (vlax-3d-point ip) newName xs ys zs rot)))
      )
      (if (and obj (not (vl-catch-all-error-p obj)))
        (progn
          (vl-catch-all-apply 'vla-put-Layer (list obj lay))
          (if (= (vla-get-HasAttributes obj) :vlax-true)
            (progn
              (setq atts (vlax-invoke obj 'GetAttributes))
              (foreach att atts
                (vl-catch-all-apply 'vla-put-Layer (list att lay))
              )
            )
          )
          (DTT--set-reference-att-values obj vals)
          (if dynPos (DTT--set-dynamic-position obj dynPos))
          (if (and trayHandle (setq tray (handent trayHandle)))
            (DTT--set-reference-tray obj tray))
          (vl-catch-all-apply 'vla-Delete (list ref))
          obj
        )
        nil
      )
    )
    nil
  )
)

(defun DTT--migrate-legacy-references (legacyName newName items / item made blk)
  (setq made 0)
  (foreach item items
    (if (DTT--migrate-reference (car item) newName (cadr item))
      (setq made (1+ made))
    )
  )
  (setq blk (DTT--block-object legacyName))
  (if blk (vl-catch-all-apply 'vla-Delete (list blk)))
  made
)

(defun DTT--reference-atts-complete-p (ref / att tag tags)
  (foreach att (degk--att-list ref)
    (setq tag (vl-catch-all-apply 'vla-get-TagString (list att)))
    (if (not (vl-catch-all-error-p tag))
      (setq tags (cons (DTT--normalize-att-tag tag) tags))))
  (and (member "TAVA_TÝPÝ" tags)
       (member "GENÝÞLÝK" tags)
       (member "YANAK_YÜKSEKLÝÐÝ" tags)
       (member "YÜKSEKLÝK" tags))
)

(defun DTT--repair-incomplete-references (name fallbackStem / refs ref pos repaired)
  ;; Onceki basarisiz dinamik olusturmadan kalan bos/eksik etiketleri ayni
  ;; block tanimindan yeniden ekle; finish asamasi degerleri tekrar doldurur.
  (setq refs (DTT--references name)
        repaired 0)
  (foreach ref refs
    (if (not (DTT--reference-atts-complete-p ref))
      (progn
        (setq pos (DTT--dynamic-position ref))
        (if (null pos) (setq pos (list 0.0 fallbackStem)))
        (if (DTT--migrate-reference ref name pos)
          (setq repaired (1+ repaired))))))
  repaired
)

(defun DTT--insert-label-block (space name base ang lay / obj atts att)
  (setq obj
    (vl-catch-all-apply
      'vla-InsertBlock
      (list space (vlax-3d-point (DTT--pt3 base)) name 1.0 1.0 1.0 ang)
    )
  )
  (if (vl-catch-all-error-p obj)
    nil
    (progn
      (vl-catch-all-apply 'vla-put-Layer (list obj lay))
      (if (= (vla-get-HasAttributes obj) :vlax-true)
        (progn
          (setq atts (vlax-invoke obj 'GetAttributes))
          (foreach att atts
            (vl-catch-all-apply 'vla-put-Layer (list att lay))
          )
        )
      )
      obj
    )
  )
)

(defun DTT--ladder-key (ent / meta groupId)
  (setq meta    (DT--ladder-meta ent)
        groupId (if meta (nth 5 meta)))
  (cond
    ((and groupId (/= groupId "") (DT--ladder-attached-group-p ent))
      (strcase groupId))
    ((and ent (DT--ladder-top-cap-entity-p ent))
      (DT--ent-handle ent))
  )
)

(defun DTT--selection-handles
  (ss / i en h out ladderMeta ladderKey representative ladderSeen attached)
  (setq i 0 out nil)
  (if ss
    (while (< i (sslength ss))
      (setq en (ssname ss i)
            ladderMeta (DT--ladder-meta en)
            attached (if ladderMeta (DT--ladder-attached-group-p en)))
      (if ladderMeta
        (if (or attached (DT--ladder-top-cap-entity-p en))
          (progn
            (setq ladderKey (DTT--ladder-key en))
            (if (not (member ladderKey ladderSeen))
              (progn
                (setq ladderSeen
                        (cons ladderKey ladderSeen)
                      representative
                        (if attached
                          (DT--ladder-top-cap en)
                          en)
                      h
                        (if representative
                          (cdr (assoc 5 (entget representative)))))
                (if h (setq out (cons h out)))))))
        (progn
          (setq h (cdr (assoc 5 (entget en))))
          (if h (setq out (cons h out)))))
      (setq i (1+ i))
    )
  )
  (reverse out)
)

(defun DTT--reference-ladder-data (ref / handle tray meta representative key)
  (setq handle (DTT--reference-tray-handle ref)
        tray   (if handle (handent handle))
        meta   (if tray (DT--ladder-meta tray)))
  (if meta
    (progn
      (setq representative
              (if (DT--ladder-top-cap tray)
                (DT--ladder-top-cap tray)
                tray)
            key (DTT--ladder-key representative))
      (list key representative))
  )
)

(defun DTT--dedupe-ladder-references (refs / seen out ref data key representative)
  (foreach ref refs
    (setq data           (DTT--reference-ladder-data ref)
          key            (if data (car data))
          representative (if data (cadr data)))
    (if (and key (member key seen))
      (vl-catch-all-apply 'vla-Delete (list ref))
      (progn
        (if key
          (progn
            (setq seen (cons key seen))
            (if representative
              (DTT--set-reference-tray ref representative))))
        (setq out (append out (list ref)))))
  )
  out
)

(defun DTT--local-to-world (base angle x y xScale yScale / lx ly ca sa)
  (setq lx (* x xScale)
        ly (* y yScale)
        ca (cos angle)
        sa (sin angle))
  (list
    (+ (car base) (- (* lx ca) (* ly sa)))
    (+ (cadr base) (+ (* lx sa) (* ly ca)))
    (if (caddr base) (caddr base) 0.0)
  )
)

(defun DTT--world-to-local (base angle point xScale yScale / dx dy ca sa)
  (setq dx (- (car point) (car base))
        dy (- (cadr point) (cadr base))
        ca (cos angle)
        sa (sin angle))
  (if (or (null xScale) (equal xScale 0.0 0.000000001))
    (setq xScale 1.0))
  (if (or (null yScale) (equal yScale 0.0 0.000000001))
    (setq yScale 1.0))
  (list
    (/ (+ (* dx ca) (* dy sa)) xScale)
    (/ (+ (* (- dx) sa) (* dy ca)) yScale)
  )
)

(defun DTT--label-box (base angle pos rectW rectH xScale yScale / x y hw p1 p2 p3 p4 xs ys)
  (setq x  (car pos)
        y  (cadr pos)
        hw (/ rectW 2.0)
        p1 (DTT--local-to-world base angle (- x hw) y xScale yScale)
        p2 (DTT--local-to-world base angle (+ x hw) y xScale yScale)
        p3 (DTT--local-to-world base angle (+ x hw) (+ y rectH) xScale yScale)
        p4 (DTT--local-to-world base angle (- x hw) (+ y rectH) xScale yScale)
        xs (mapcar 'car (list p1 p2 p3 p4))
        ys (mapcar 'cadr (list p1 p2 p3 p4)))
  (list (apply 'min xs) (apply 'min ys) (apply 'max xs) (apply 'max ys))
)

(defun DTT--rotate-relative-pos (pos angle / ca sa)
  (setq ca (cos angle) sa (sin angle))
  (list (- (* (car pos) ca) (* (cadr pos) sa))
        (+ (* (car pos) sa) (* (cadr pos) ca)))
)

(defun DTT--world0-label-box (base pos rectW rectH xScale yScale / cx y0 hw h x1 x2 y1 y2)
  (setq cx (+ (car base) (* (car pos) xScale))
        y0 (+ (cadr base) (* (cadr pos) yScale))
        hw (/ (* rectW (abs xScale)) 2.0)
        h  (* rectH (abs yScale))
        x1 (- cx hw)
        x2 (+ cx hw)
        y1 (min y0 (+ y0 h))
        y2 (max y0 (+ y0 h)))
  (list x1 y1 x2 y2)
)

(defun DTT--nearest-rect-edge-pos (pos rectW rectH / x y hw edges edge best bestD d)
  (setq x  (car pos)
        y  (cadr pos)
        hw (/ rectW 2.0)
        edges
          (list
            (list x y)
            (list x (+ y rectH))
            (list (- x hw) (+ y (/ rectH 2.0)))
            (list (+ x hw) (+ y (/ rectH 2.0)))))
  (foreach edge edges
    (setq d (distance '(0.0 0.0 0.0) (list (car edge) (cadr edge) 0.0)))
    (if (or (null bestD) (< d bestD))
      (setq best edge bestD d)))
  best
)

(defun DTT--world0-placement-if-free
  (base pos rectW rectH occupied clearance xScale yScale / box leader)
  (setq box (DTT--world0-label-box base pos rectW rectH xScale yScale))
  (if (not (DTT--box-conflict-p box occupied clearance))
    (progn
      (setq leader (DTT--nearest-rect-edge-pos pos rectW rectH))
      (list pos box 0.0 leader)))
)

(defun DTT--world0-opposite-pos (pos rectH)
  ;; Dikdortgen merkezini block base noktasinin tam karsisina aynalar.
  (list (- (car pos)) (- (- (cadr pos)) rectH))
)

(defun DTT--world0-initial-pos (tang stemLen rectW rectH side / nx ny support centerD)
  (setq nx (- (cadr tang))
        ny (car tang)
        support (+ (* (abs nx) (/ rectW 2.0))
                   (* (abs ny) (/ rectH 2.0)))
        centerD (* side (+ stemLen support)))
  (list (* nx centerD)
        (- (* ny centerD) (/ rectH 2.0)))
)

(defun DTT--world0-side-positions
  (tang stemLen rectW rectH rawStartPos labelAngle
   / canonical opposite rawWorld canonicalPt oppositePt rawPt)
  (setq canonical
          (DTT--world0-initial-pos
            tang stemLen rectW rectH 1.0)
        opposite
          (DTT--world0-opposite-pos canonical rectH))
  (if rawStartPos
    (progn
      (setq rawWorld
              (DTT--rotate-relative-pos rawStartPos labelAngle)
            canonicalPt
              (list (car canonical) (cadr canonical) 0.0)
            oppositePt
              (list (car opposite) (cadr opposite) 0.0)
            rawPt
              (list (car rawWorld) (cadr rawWorld) 0.0))
      ;; Mevcut etiketten yalniz tava tarafi secimini koru. Serbest X/Y
      ;; uzakligi tekrar kullanilmaz; boyuna kayma block base'i ile yapilir.
      (if (< (distance rawPt oppositePt)
             (distance rawPt canonicalPt))
        (list opposite canonical)
        (list canonical opposite)))
    (list canonical opposite))
)

(defun DTT--world0-placement-at-base
  (base primaryPos oppositePos rectW rectH occupied clearance xScale yScale / placement)
  (setq placement
    (DTT--world0-placement-if-free
      base primaryPos rectW rectH occupied clearance xScale yScale))
  (if (null placement)
    (setq placement
      (DTT--world0-placement-if-free
        base oppositePos rectW rectH occupied clearance xScale yScale)))
  (if placement (cons base placement))
)

(defun DTT--box-center2d (box)
  (list (/ (+ (nth 0 box) (nth 2 box)) 2.0)
        (/ (+ (nth 1 box) (nth 3 box)) 2.0)
        0.0)
)

(defun DTT--world0-placement-score
  (placement idealBox idealBase xScale yScale / box leader center idealCenter leaderLen baseLen)
  (setq box         (nth 2 placement)
        leader      (nth 4 placement)
        center      (DTT--box-center2d box)
        idealCenter (DTT--box-center2d idealBox)
        leaderLen   (distance '(0.0 0.0 0.0)
                       (list (* (car leader) xScale)
                             (* (cadr leader) yScale) 0.0))
        baseLen     (distance (DTT--pt3 (car placement))
                              (DTT--pt3 idealBase)))
  ;; Once ideal konuma en yakin dikdortgen, sonra en kisa leader ve en az
  ;; base kaymasi secilir.
  (list (distance center idealCenter) leaderLen baseLen)
)

(defun DTT--score-less-p (a b / tol)
  (setq tol 0.000001)
  (cond
    ((< (nth 0 a) (- (nth 0 b) tol)) T)
    ((> (nth 0 a) (+ (nth 0 b) tol)) nil)
    ((< (nth 1 a) (- (nth 1 b) tol)) T)
    ((> (nth 1 a) (+ (nth 1 b) tol)) nil)
    (T (< (nth 2 a) (- (nth 2 b) tol))))
)

(defun DTT--closer-world0-placement
  (best candidate idealBox idealBase xScale yScale / bestScore candidateScore)
  (cond
    ((null candidate) best)
    ((null best) candidate)
    (T
      (setq bestScore
              (DTT--world0-placement-score
                best idealBox idealBase xScale yScale)
            candidateScore
              (DTT--world0-placement-score
                candidate idealBox idealBase xScale yScale))
      (if (DTT--score-less-p candidateScore bestScore) candidate best)))
)

(defun DTT--world0-free-position
  (base primaryPos oppositePos rectW rectH occupied clearance xScale yScale
   / best ring dx dy stepX stepY anchor candidate trial idealBox)
  (setq stepX    (+ rectW clearance)
        stepY    (+ rectH clearance)
        idealBox (DTT--world0-label-box
                   base primaryPos rectW rectH xScale yScale)
        ring     0)
  ;; Ayni halkadaki tum bos adaylari karsilastir; tarama sirasinda ilk
  ;; gorulen konum artik sonucu belirlemez.
  (while (and (null best) (<= ring 100))
    (foreach anchor (list primaryPos oppositePos)
      (setq dy (- ring))
      (while (<= dy ring)
        (setq dx (- ring))
        (while (<= dx ring)
          (if (= (max (abs dx) (abs dy)) ring)
            (progn
              (setq candidate
                      (list (+ (car anchor) (* dx stepX))
                            (+ (cadr anchor) (* dy stepY)))
                    trial
                      (DTT--world0-placement-if-free
                        base candidate rectW rectH occupied clearance xScale yScale))
              (if trial
                (setq best
                  (DTT--closer-world0-placement
                    best (cons base trial) idealBox base xScale yScale)))))
          (setq dx (1+ dx)))
        (setq dy (1+ dy))))
    (setq ring (1+ ring)))
  best
)

(defun DTT--world0-free-position-along-tray
  (seg primaryPos oppositePos rectW rectH occupied clearance xScale yScale
   idealBox idealBase tang preferredEndSign
   / a b dx dy len ux uy tangentLen abDot negativeEnd positiveEnd endpoints
     labelW labelH projected step ring endpoint direction base pos trial best)
  (if (and seg (= (length seg) 2))
    (progn
      (setq a   (DTT--pt3 (car seg))
            b   (DTT--pt3 (cadr seg))
            dx  (- (car b) (car a))
            dy  (- (cadr b) (cadr a))
            len (sqrt (+ (* dx dx) (* dy dy))))
      (if (> len 0.000001)
        (progn
          (setq tangentLen
                  (if tang
                    (sqrt (+ (* (car tang) (car tang))
                             (* (cadr tang) (cadr tang))))
                    0.0)
                ux
                  (if (> tangentLen 0.000001)
                    (/ (car tang) tangentLen)
                    (/ dx len))
                uy
                  (if (> tangentLen 0.000001)
                    (/ (cadr tang) tangentLen)
                    (/ dy len))
                abDot      (+ (* dx ux) (* dy uy))
                negativeEnd (if (>= abDot 0.0) a b)
                positiveEnd (if (>= abDot 0.0) b a)
                endpoints
                  (if (and (numberp preferredEndSign)
                           (= preferredEndSign 1))
                    (list (list positiveEnd 1.0)
                          (list negativeEnd -1.0))
                    (list (list negativeEnd -1.0)
                          (list positiveEnd 1.0)))
                labelW    (* rectW (abs xScale))
                labelH    (* rectH (abs yScale))
                projected (+ (* (abs ux) labelW)
                             (* (abs uy) labelH))
                step      (max clearance (/ projected 3.0) 0.001)
                ring      1)
          ;; Tava uzerindeki standart adaylar doluysa etiketi yalniz tavanin
          ;; boyuna ekseninde iki uctan disari tasir. Enine serbest X/Y aramasi
          ;; baska bir tava grubuna atlamaya neden oldugu icin burada kullanilmaz.
          (while (and (null best) (<= ring 200))
            (foreach endpoint endpoints
              (setq direction (cadr endpoint)
                    base
                      (list
                        (+ (car (car endpoint))
                           (* direction ring step ux))
                        (+ (cadr (car endpoint))
                           (* direction ring step uy))
                        (caddr (car endpoint))))
              (foreach pos (list primaryPos oppositePos)
                (setq trial
                  (DTT--world0-placement-if-free
                    base pos rectW rectH occupied clearance xScale yScale))
                (if trial
                  (setq best
                    (DTT--closer-world0-placement
                      best (cons base trial)
                      idealBox idealBase xScale yScale)))))
            (setq ring (1+ ring))))))
  )
  best
)

(defun DTT--segment-point-at (seg ratio / a b)
  (setq a (DTT--pt3 (car seg))
        b (DTT--pt3 (cadr seg)))
  (list (+ (car a) (* (- (car b) (car a)) ratio))
        (+ (cadr a) (* (- (cadr b) (cadr a)) ratio))
        (+ (caddr a) (* (- (caddr b) (caddr a)) ratio)))
)

(defun DTT--unique-point-add (pt points tol)
  (if (or (null pt) (DTT--near-any-point-p pt points tol))
    points
    (cons pt points))
)

(defun DTT--tray-base-samples
  (seg preferredBase mid rectW rectH clearance / projected len step divisions i points)
  (setq projected
          (if preferredBase
            (DTT--project-base-to-segment preferredBase seg (caddr mid)))
        len  (distance (DTT--pt3 (car seg)) (DTT--pt3 (cadr seg)))
        step (max clearance (/ (min rectW rectH) 2.0) 0.001)
        divisions
          (if (> len 0.000001)
            (min 120 (max 20 (fix (+ (/ len step) 0.999999))))
            1)
        points nil)
  (setq points (DTT--unique-point-add projected points 0.000001)
        points (DTT--unique-point-add mid points 0.000001)
        i 0)
  (while (<= i divisions)
    (setq points
      (DTT--unique-point-add
        (DTT--segment-point-at seg (/ (float i) divisions))
        points 0.000001)
          i (1+ i)))
  (if (null projected) (setq projected mid))
  (vl-sort points
    '(lambda (a b)
       (< (distance (DTT--pt3 a) (DTT--pt3 projected))
          (distance (DTT--pt3 b) (DTT--pt3 projected)))))
)

(defun DTT--preferred-base-order
  (bases idealBase tang preferredEndSign / tol)
  (setq tol 0.000001)
  (if (and (numberp preferredEndSign)
           (/= preferredEndSign 0)
           idealBase tang)
    (vl-sort
      bases
      '(lambda (a b / da db pa pb)
         (setq da (distance (DTT--pt3 a) (DTT--pt3 idealBase))
               db (distance (DTT--pt3 b) (DTT--pt3 idealBase)))
         (cond
           ((< da (- db tol)) T)
           ((> da (+ db tol)) nil)
           (T
             (setq pa
                     (* preferredEndSign
                        (+ (* (- (car a) (car idealBase)) (car tang))
                           (* (- (cadr a) (cadr idealBase)) (cadr tang))))
                   pb
                     (* preferredEndSign
                        (+ (* (- (car b) (car idealBase)) (car tang))
                           (* (- (cadr b) (cadr idealBase)) (cadr tang)))))
             (cond
               ((> pa (+ pb tol)) T)
               ((< pa (- pb tol)) nil)
               ((< (car a) (- (car b) tol)) T)
               ((> (car a) (+ (car b) tol)) nil)
               (T (< (cadr a) (cadr b))))))))
    bases)
)

(defun DTT--free-world0-placement-on-tray
  (seg mid tang preferredBase primaryPos oppositePos rectW rectH occupied clearance xScale yScale preferredEndSign
   / bases idealBase idealBox base pos trial best fallback)
  (setq bases
          (DTT--tray-base-samples
            seg preferredBase mid rectW rectH clearance)
        idealBase (if bases (car bases) mid)
        bases
          (DTT--preferred-base-order
            bases idealBase tang preferredEndSign)
        idealBox
          (DTT--world0-label-box
            idealBase primaryPos rectW rectH xScale yScale))
  ;; Tava boyunca iki taraftaki tum yakin adaylari puanla. Boylece secim,
  ;; polyline yonune veya dongunun ilk buldugu noktaya bagli kalmaz.
  (foreach base bases
    (foreach pos (list primaryPos oppositePos)
      (setq trial
        (DTT--world0-placement-if-free
          base pos rectW rectH occupied clearance xScale yScale))
      (if trial
        (setq best
          (DTT--closer-world0-placement
            best (cons base trial) idealBox idealBase xScale yScale)))))
  ;; Standart iki tarafta yer yoksa yalniz kendi tava ekseni boyunca ara.
  ;; Boylece etiket baska bir tava grubunun uzak tarafina sicrama yapmaz.
  (if (null best)
    (setq fallback
            (DTT--world0-free-position-along-tray
              seg primaryPos oppositePos rectW rectH
              occupied clearance xScale yScale idealBox idealBase
              tang preferredEndSign)
          best
            (DTT--closer-world0-placement
              best fallback idealBox idealBase xScale yScale)))
  (if best
    (DTT--reanchor-world0-placement
      best seg rectW rectH xScale yScale)
  )
)

(defun DTT--boxes-overlap-p (a b clearance)
  (and a b
       (< (- (nth 0 a) clearance) (nth 2 b))
       (> (+ (nth 2 a) clearance) (nth 0 b))
       (< (- (nth 1 a) clearance) (nth 3 b))
       (> (+ (nth 3 a) clearance) (nth 1 b)))
)

(defun DTT--box-conflict-p (box occupied clearance / hit other)
  (while (and occupied (not hit))
    (setq other    (car occupied)
          occupied (cdr occupied))
    (if (DTT--boxes-overlap-p box other clearance) (setq hit T))
  )
  hit
)

(defun DTT--placement-if-free (base angle pos rectW rectH occupied clearance xScale yScale / box)
  (setq box (DTT--label-box base angle pos rectW rectH xScale yScale))
  (if (not (DTT--box-conflict-p box occupied clearance))
    (list pos box angle)
  )
)

(defun DTT--free-label-position (base angle startPos rectW rectH occupied clearance xScale yScale / x y oppositeAngle oppositePos placement ring dx dy stepX stepY candidate)
  (setq x             (car startPos)
        y             (cadr startPos)
        oppositeAngle (+ angle pi)
        oppositePos   (list (- x) y)
        stepX         (+ rectW clearance)
        stepY         (+ rectH clearance))
  ;; 1) Mevcut konum, 2) ayni mesafeyle tavanin tam karsi tarafi.
  (setq placement
    (DTT--placement-if-free
      base angle startPos rectW rectH occupied clearance xScale yScale))
  (if (null placement)
    (setq placement
      (DTT--placement-if-free
        base oppositeAngle oppositePos rectW rectH occupied clearance xScale yScale))
  )
  ;; Iki taraf da doluysa iki yonde genisleyen X/Y kare halkalarini tara.
  (setq ring 1)
  (while (and (null placement) (<= ring 1000))
    (setq dy 0)
    (while (and (null placement) (<= dy ring))
      (setq dx (- ring))
      (while (and (null placement) (<= dx ring))
        (if (= (max (abs dx) dy) ring)
          (progn
            (setq candidate
              (list (+ x (* dx stepX)) (+ y (* dy stepY))))
            (setq placement
              (DTT--placement-if-free
                base angle candidate rectW rectH occupied clearance xScale yScale))
            (if (null placement)
              (setq placement
                (DTT--placement-if-free
                  base oppositeAngle (list (- (car candidate)) (cadr candidate))
                  rectW rectH occupied clearance xScale yScale))
            )
          )
        )
        (setq dx (1+ dx))
      )
      (setq dy (1+ dy))
    )
    (setq ring (1+ ring))
  )
  placement
)

(defun DTT--project-base-to-segment (pt seg z / a b dx dy len2 ratio za zb)
  (if (and pt seg (= (length seg) 2))
    (progn
      (setq a    (car seg)
            b    (cadr seg)
            dx   (- (car b) (car a))
            dy   (- (cadr b) (cadr a))
            len2 (+ (* dx dx) (* dy dy))
            za   (if (caddr a) (caddr a) z)
            zb   (if (caddr b) (caddr b) z))
      (if (> len2 0.000000001)
        (progn
          (setq ratio
            (/ (+ (* (- (car pt) (car a)) dx)
                  (* (- (cadr pt) (cadr a)) dy))
               len2)
                ratio (max 0.0 (min 1.0 ratio)))
          (list (+ (car a) (* dx ratio))
                (+ (cadr a) (* dy ratio))
                (+ za (* (- zb za) ratio))))))
  )
)

(defun DTT--reanchor-world0-placement
  (placement seg rectW rectH xScale yScale /
    oldBase oldPos angle worldPos worldCenter newBase localPos leaderPos
    worldLeader projected iteration box)
  (if (and placement seg (= (length seg) 2))
    (progn
      (setq oldBase (nth 0 placement)
            oldPos  (nth 1 placement)
            angle   (nth 3 placement))
      (if (null angle) (setq angle 0.0))
      ;; Etiketin dunya konumunu koru; yalniz tava tarafindaki base noktasini
      ;; etiketin en yakin kenarina gore orta eksen boyunca kaydir.
      (setq worldPos
              (DTT--local-to-world
                oldBase angle (car oldPos) (cadr oldPos) xScale yScale)
            worldCenter
              (DTT--local-to-world
                oldBase angle
                (car oldPos) (+ (cadr oldPos) (/ rectH 2.0))
                xScale yScale)
            newBase
              (DTT--project-base-to-segment
                worldCenter seg (caddr oldBase))
            iteration 0)
      (if (null newBase) (setq newBase oldBase))
      ;; Kutuya en yakin kenar degisebildigi icin projeksiyonu birkac kez
      ;; yinele; base her zaman sinirli orta-hat segmentinde kalir.
      (while (< iteration 4)
        (setq localPos
                (DTT--world-to-local
                  newBase angle worldPos xScale yScale)
              leaderPos
                (DTT--nearest-rect-edge-pos localPos rectW rectH)
              worldLeader
                (DTT--local-to-world
                  newBase angle
                  (car leaderPos) (cadr leaderPos) xScale yScale)
              projected
                (DTT--project-base-to-segment
                  worldLeader seg (caddr newBase)))
        (if projected (setq newBase projected))
        (setq iteration (1+ iteration)))
      (setq localPos
              (DTT--world-to-local
                newBase angle worldPos xScale yScale)
            leaderPos
              (DTT--nearest-rect-edge-pos localPos rectW rectH)
            box
              (DTT--label-box
                newBase angle localPos rectW rectH xScale yScale))
      (list newBase localPos box angle leaderPos)
    )
    placement
  )
)

(defun DTT--placement-at-base
  (base angle startPos rectW rectH occupied clearance xScale yScale / placement)
  (setq placement
    (DTT--placement-if-free
      base angle startPos rectW rectH occupied clearance xScale yScale))
  (if (null placement)
    (setq placement
      (DTT--placement-if-free
        base (+ angle pi) (list (- (car startPos)) (cadr startPos))
        rectW rectH occupied clearance xScale yScale)))
  (if placement (cons base placement))
)

(defun DTT--free-label-placement-on-tray
  (seg mid tang preferredBase angle startPos rectW rectH occupied clearance xScale yScale
   / placement projected halfLen step i candidate fallback)
  ;; Once mevcut/orta base, sonra tava boyunca orta eksende iki yone tara.
  (setq projected
    (if preferredBase
      (DTT--project-base-to-segment preferredBase seg (caddr mid))))
  (if projected
    (setq placement
      (DTT--placement-at-base
        projected angle startPos rectW rectH occupied clearance xScale yScale)))
  (if (and (null placement)
           (or (null projected) (not (DTT--near-p projected mid 0.000001))))
    (setq placement
      (DTT--placement-at-base
        mid angle startPos rectW rectH occupied clearance xScale yScale)))
  (setq halfLen (/ (distance (car seg) (cadr seg)) 2.0)
        step    (/ halfLen 20.0)
        i       1)
  (while (and (null placement) (<= i 20))
    (setq candidate
            (DTT--project-base-to-segment
              (DTT--move mid tang (* step i)) seg (caddr mid))
          placement
            (DTT--placement-at-base
              candidate angle startPos rectW rectH occupied clearance xScale yScale))
    (if (null placement)
      (progn
        (setq candidate
                (DTT--project-base-to-segment
                  (DTT--move mid tang (* -1.0 step i)) seg (caddr mid))
              placement
                (DTT--placement-at-base
                  candidate angle startPos rectW rectH occupied clearance xScale yScale))))
    (setq i (1+ i)))
  ;; Tava boyunca yer bulunamazsa onceki serbest X/Y aramasini koru.
  (if (null placement)
    (progn
      (setq fallback
        (DTT--free-label-position
          mid angle startPos rectW rectH occupied clearance xScale yScale))
      (if fallback (setq placement (cons mid fallback)))))
  placement
)

(defun DTT--selected-tray-bases (handles / h ent seg basis out)
  (foreach h handles
    (setq ent (handent h))
    (if (DTT--label-element-p ent)
      (progn
        (setq seg   (DTT--tray-center-seg3d ent)
              basis (DTT--basis seg))
        (if basis
          (setq out
            (cons
              (list (car (nth 0 basis))
                    (cadr (nth 0 basis))
                    (DTT--tray-mid-elevation ent))
              out)))
      )
    )
  )
  (reverse out)
)

(defun DTT--object-key (obj / h)
  (setq h (vl-catch-all-apply 'vla-get-Handle (list obj)))
  (if (vl-catch-all-error-p h) nil h)
)

(defun DTT--moving-label-keys (handles refs / h tray seg basis base ref key out)
  (foreach h handles
    (setq tray (handent h)
          ref  (if tray (DTT--reference-for-tray tray refs)))
    (if (and tray (null ref))
      (progn
        (setq seg   (DTT--tray-center-seg3d tray)
              basis (DTT--basis seg)
              base  (if basis
                      (list (car (nth 0 basis))
                            (cadr (nth 0 basis))
                            (DTT--tray-mid-elevation tray))))
        (if base (setq ref (DTT--reference-at-base base refs 0.001)))))
    (if (and ref (setq key (DTT--object-key ref)) (not (member key out)))
      (setq out (cons key out))
    )
  )
  out
)

(defun DTT--reference-label-box (ref rectW rectH fallbackY / base angle pos xs ys)
  (setq base  (DTT--vla-point ref 'InsertionPoint)
        angle (DTT--vla-number-or ref 'Rotation 0.0)
        pos   (DTT--dynamic-position ref)
        xs    (DTT--vla-number-or ref 'XScaleFactor 1.0)
        ys    (DTT--vla-number-or ref 'YScaleFactor 1.0))
  (if (null pos) (setq pos (list 0.0 fallbackY)))
  (if base (DTT--label-box base angle pos rectW rectH xs ys))
)

(defun DTT--fixed-label-boxes (refs movingKeys rectW rectH fallbackY / ref key box out)
  (foreach ref refs
    (setq key (DTT--object-key ref))
    (if (not (member key movingKeys))
      (progn
        (setq box (DTT--reference-label-box ref rectW rectH fallbackY))
        (if box (setq out (cons box out)))
      )
    )
  )
  out
)

(defun DTT--tray-plan-box (tray / pts xs ys)
  (setq pts (if tray (DT--entity-points3d tray)))
  (if pts
    (progn
      (setq xs (mapcar 'car pts)
            ys (mapcar 'cadr pts))
      (list (apply 'min xs) (apply 'min ys)
            (apply 'max xs) (apply 'max ys)))
  )
)

(defun DTT--all-tray-plan-boxes (/ ss i tray box out)
  ;; Plan gorunusunde etiket dikdortgeni hicbir DT tavasinin ustune gelmesin.
  (setq ss (ssget "_X" '((-3 ("DT_TRAY_HATCH"))))
        i 0)
  (if ss
    (while (< i (sslength ss))
      (setq tray (ssname ss i)
            box  (if (DT--visible-tray-p tray) (DTT--tray-plan-box tray)))
      (if box (setq out (cons box out)))
      (setq i (1+ i))))
  out
)

(defun DTT--clear-pending ()
  (setq *DTT--pending-active* nil
        *DTT--pending-handles* nil
        *DTT--pending-gap* nil
        *DTT--pending-rectW* nil
        *DTT--pending-rectH* nil
        *DTT--pending-att-text-height* nil
        *DTT--pending-att-text-style* nil
        *DTT--pending-layer* nil
        *DTT--pending-block-name* nil
        *DTT--pending-legacy-groups* nil
        *DTT--pending-saved-refs* nil
        *DTT--pending-dynamic-ok* nil
        *DTT--resume-queued* nil)
  nil
)

(defun DTT--finish-pending (/ handles gap rectW rectH attTextH attTextStyle lay blockName legacyGroups group dynamicOK savedRefs space h ent seg trayW basis mid tang stemLen angle labelAngle targetAngle oldAngle ins made skipped migrated repaired labelBases labelRefs existingRef attValues existingCount selectedBases movingKeys occupied clearance startPos rawStartPos sidePositions primaryPos oppositePos leaderPos oldLeaderPos placement pos box xScale yScale positionOK rotationOK movedCount oldBase chosenBase preferredBase oldBox placementRecords currentRecord preferredEndSign)
  (if *DTT--pending-active*
    (progn
      (setq handles   *DTT--pending-handles*
            gap       *DTT--pending-gap*
            rectW     *DTT--pending-rectW*
            rectH     *DTT--pending-rectH*
            attTextH  *DTT--pending-att-text-height*
            attTextStyle *DTT--pending-att-text-style*
            lay       *DTT--pending-layer*
            blockName *DTT--pending-block-name*
            legacyGroups *DTT--pending-legacy-groups*
            dynamicOK *DTT--pending-dynamic-ok*
            savedRefs *DTT--pending-saved-refs*
            migrated  0)
      (if dynamicOK
        (DTT--set-block-clean-version blockName)
      )
      (if legacyGroups
        (foreach group legacyGroups
          (setq migrated
            (+ migrated
               (DTT--migrate-legacy-references
                 (car group) blockName (cadr group))))
        )
        (if (and dynamicOK savedRefs)
          (DTT--restore-reference-positions savedRefs)
        )
      )
       ;; Eski merkez ATTREF kopyalarini temizle; dort attribute'u birlikte koru.
       (DTT--cleanup-all-reference-atts blockName)
       (setq repaired (DTT--repair-incomplete-references blockName gap))
       (DTT--set-definition-att-height blockName attTextH)
      (DTT--set-definition-att-style blockName attTextStyle)
      (DTT--set-all-reference-att-height blockName attTextH)
      (DTT--set-all-reference-att-style blockName attTextStyle)
      (setq space   (DTT--current-space)
            made    0
            skipped 0
            existingCount 0
            placementRecords (DTT--placement-records handles)
            handles (mapcar 'car placementRecords)
            labelRefs (DTT--dedupe-ladder-references
                        (DTT--references blockName))
            labelBases (DTT--reference-bases blockName)
            selectedBases (DTT--selected-tray-bases handles)
            movingKeys (DTT--moving-label-keys handles labelRefs)
            clearance (max 0.001 (* rectH 0.05))
            occupied
              (append
                (DTT--fixed-label-boxes labelRefs movingKeys rectW rectH gap)
                (DTT--all-tray-plan-boxes))
            movedCount 0)
      (foreach h handles
        (setq ent (handent h))
        (if (DTT--label-element-p ent)
          (progn
            (setq seg   (DTT--tray-center-seg3d ent)
                  trayW (DTT--label-plan-width ent)
                  basis (DTT--basis seg))
            (if (and basis trayW (> trayW 0.0))
              (progn
                (setq mid     (list (car (nth 0 basis))
                                    (cadr (nth 0 basis))
                                    (DTT--tray-mid-elevation ent))
                      tang    (nth 1 basis)
                      stemLen (+ (/ trayW 2.0) gap)
                      angle   (atan (cadr tang) (car tang))
                      attValues (DTT--tray-att-values ent trayW)
                      existingRef (DTT--reference-for-tray ent labelRefs))
                (if (null existingRef)
                  (setq existingRef (DTT--reference-at-base mid labelRefs 0.001)))
                (setq oldBase (if existingRef
                                (DTT--vla-point existingRef 'InsertionPoint)
                                mid))
                (if (null oldBase) (setq oldBase mid))
                (setq preferredBase (if existingRef oldBase mid))
                (setq labelAngle (if existingRef
                                   (DTT--vla-number-or existingRef 'Rotation angle)
                                   0.0)
                      xScale     (if existingRef
                                   (DTT--vla-number-or existingRef 'XScaleFactor 1.0)
                                   1.0)
                      yScale     (if existingRef
                                   (DTT--vla-number-or existingRef 'YScaleFactor 1.0)
                                   1.0)
                      rawStartPos (if existingRef (DTT--dynamic-position existingRef) nil)
                      oldLeaderPos (if existingRef
                                     (DTT--dynamic-leader-position existingRef)
                                     nil)
                      oldBox (if existingRef
                               (DTT--reference-label-box
                                 existingRef rectW rectH stemLen)
                               nil))
                (setq sidePositions
                        (DTT--world0-side-positions
                          tang stemLen rectW rectH rawStartPos labelAngle)
                      primaryPos (car sidePositions)
                      oppositePos (cadr sidePositions)
                      startPos primaryPos
                      currentRecord (assoc h placementRecords)
                      preferredEndSign
                        (DTT--preferred-end-sign
                          currentRecord placementRecords rectW rectH))
                (setq placement
                  (DTT--free-world0-placement-on-tray
                    seg mid tang preferredBase primaryPos oppositePos
                    rectW rectH occupied clearance xScale yScale
                    preferredEndSign))
                (if (null placement)
                  (setq skipped (1+ skipped))
                  (progn
                    (setq chosenBase  (nth 0 placement)
                          pos         (nth 1 placement)
                          box         (nth 2 placement)
                          targetAngle (nth 3 placement)
                          leaderPos   (nth 4 placement))
                    (if existingRef
                      (progn
                        ;; Base noktasi tava merkez ekseni boyunca secilen bos konuma tasinir.
                        (vl-catch-all-apply
                          'vla-put-InsertionPoint
                          (list existingRef (vlax-3d-point chosenBase)))
                        (setq oldAngle labelAngle
                              rotationOK
                                (not
                                  (vl-catch-all-error-p
                                    (vl-catch-all-apply
                                      'vla-put-Rotation
                                      (list existingRef targetAngle)))))
                         (setq positionOK
                           (and rotationOK
                                dynamicOK
                                (DTT--set-dynamic-label-geometry
                                  existingRef pos leaderPos)))
                        (if positionOK
                          (progn
                            (DTT--set-reference-att-values existingRef attValues)
                            (DTT--set-reference-att-height existingRef attTextH)
                            (DTT--set-reference-att-style existingRef attTextStyle)
                            (DTT--align-reference-atts
                              existingRef blockName pos stemLen)
                            (DTT--set-reference-tray existingRef ent)
                            (setq occupied (cons box occupied)
                                  existingCount (1+ existingCount))
                            (if (or (not (DTT--near-p pos startPos 0.000001))
                                    (not (DTT--angles-equal-p targetAngle oldAngle 0.000001))
                                    (not (DTT--near-p chosenBase oldBase 0.000001)))
                              (setq movedCount (1+ movedCount))
                            )
                          )
                          (progn
                            (if rotationOK
                              (vl-catch-all-apply
                                'vla-put-Rotation (list existingRef oldAngle))
                            )
                            (if (and dynamicOK rawStartPos)
                              (DTT--set-dynamic-position existingRef rawStartPos)
                            )
                            (if (and dynamicOK oldLeaderPos)
                              (DTT--set-dynamic-leader-position
                                existingRef oldLeaderPos))
                            (if oldBase
                              (vl-catch-all-apply
                                'vla-put-InsertionPoint
                                (list existingRef (vlax-3d-point oldBase))))
                            (setq occupied
                              (if oldBox (cons oldBox occupied) occupied))
                            (setq skipped (1+ skipped))
                          )
                        )
                      )
                      (progn
                        (setq ins
                          (DTT--insert-label-block
                            space blockName chosenBase targetAngle lay))
                        (if ins
                          (progn
                             (setq positionOK
                               (and dynamicOK
                                    (DTT--set-dynamic-label-geometry
                                      ins pos leaderPos)))
                            (if positionOK
                              (progn
                                (DTT--set-reference-att-values ins attValues)
                                (DTT--set-reference-att-height ins attTextH)
                                (DTT--set-reference-att-style ins attTextStyle)
                                (DTT--cleanup-reference-atts ins)
                                (DTT--align-reference-atts
                                  ins blockName pos stemLen)
                                (DTT--set-reference-tray ins ent)
                                (setq labelRefs (cons ins labelRefs)
                                      labelBases (cons chosenBase labelBases)
                                      occupied (cons box occupied)
                                      made (1+ made))
                                (if (or (not (DTT--near-p pos startPos 0.000001))
                                        (not (DTT--angles-equal-p targetAngle angle 0.000001))
                                        (not (DTT--near-p chosenBase mid 0.000001)))
                                  (setq movedCount (1+ movedCount))
                                )
                              )
                              (progn
                                (vl-catch-all-apply 'vla-Delete (list ins))
                                (setq skipped (1+ skipped))
                              )
                            )
                          )
                          (setq skipped (1+ skipped))
                        )
                      )
                    )
                  )
                )
              )
              (setq skipped (1+ skipped))
            )
          )
          (setq skipped (1+ skipped))
        )
      )
      (DTT--clear-pending)
      (princ
        (strcat "\nDTT tamam. Tava: " (itoa made)
                ", block: " (itoa made)
                ", block ici cizgi: " (itoa made)
                (if dynamicOK ", hareketli uc: aktif" ", hareketli uc: olusturulamadi")
                (if legacyGroups (strcat ", eski block aktarildi: " (itoa migrated)) "")
                (if (> repaired 0) (strcat ", eksik etiket onarildi: " (itoa repaired)) "")
                (if (> existingCount 0) (strcat ", mevcut etiket: " (itoa existingCount)) "")
                (if (> movedCount 0) (strcat ", cakisma icin kaydirilan: " (itoa movedCount)) "")
                (if (> skipped 0) (strcat ", atlanan: " (itoa skipped)) "")
                "."))
    )
  )
  (princ)
)

(defun DTT--resume ()
  (if *DTT--pending-active* (DTT--finish-pending))
  (princ)
)

(defun DTT--unique-upgrade-block-name (/ base name index)
  (setq base  "e_tava_etiket_3ATT_ESKI"
        name  base
        index 1)
  (while (tblsearch "BLOCK" name)
    (setq name  (strcat base "_" (itoa index))
          index (1+ index))
  )
  name
)

(defun DTT--rename-block-definition (oldName newName / blk result)
  (if (and (tblsearch "BLOCK" oldName) (not (tblsearch "BLOCK" newName)))
    (progn
      (setq blk    (DTT--block-object oldName)
            result (if blk
                     (vl-catch-all-apply 'vla-put-Name (list blk newName))
                     nil))
      (and blk (not (vl-catch-all-error-p result)) (tblsearch "BLOCK" newName))
    )
  )
)

(defun DTT_ORIG (/ ss i ent trayW gap rectW rectH attTextH attTextStyle firstStem lay blockName legacySources legacySource legacyGroups wasV2 existingDynamic attDefsOK cleanOK upgradeName upgradeRefs renamed sizeOK resizeRefs item reuseDef savedRefs blockDef dynamicOK)
  (vl-load-com)
  (setq gap       (DEG:CFG-DTT-NUM-OR 'DTT_OUTSIDE_GAP 15.0)
        rectW     (DEG:CFG-DTT-NUM-OR 'DTT_RECT_WIDTH 70.0)
        rectH     (DEG:CFG-DTT-NUM-OR 'DTT_RECT_HEIGHT 40.0)
        attTextH  (DEG:CFG-DTT-NUM-OR 'DTT_ATT_TEXT_HEIGHT 8.0)
        attTextStyle (DTT--valid-text-style (DEG:CFG-GET 'DTT_ATT_TEXT_STYLE))
        lay       "E_TAVA_ETÝKET"
        blockName "e_tava_etiket"
        legacySources
          (list "e_DTT_ETIKET_CLEAN_V2" "e_DTT_ETIKET_CLEAN" "e_DTT_ETIKET"))
  (DT--ensure-layer lay 7 nil)
  (prompt "\nDTT: Tavalari iceren alani secin (pencere/capraz secim): ")
  (setq ss (ssget '((0 . "LWPOLYLINE,POLYLINE,INSERT"))))
  (if (null ss)
    (princ "\nDTT: Secim yapilmadi.")
    (progn
      (setq i 0 firstStem nil)
      (while (and (< i (sslength ss)) (null firstStem))
        (setq ent (ssname ss i))
        (if (DTT--label-element-p ent)
          (progn
            (setq trayW (DTT--label-plan-width ent))
            (if (and trayW (> trayW 0.0))
              (setq firstStem (+ (/ trayW 2.0) gap))
            )
          )
        )
        (setq i (1+ i))
      )
      (if (null firstStem) (setq firstStem gap))
      (setq legacyGroups nil)
      (foreach legacySource legacySources
        (if (tblsearch "BLOCK" legacySource)
          (setq legacyGroups
            (cons
              (list legacySource
                    (DTT--capture-reference-positions legacySource firstStem))
              legacyGroups))
        )
      )
      (setq legacyGroups (reverse legacyGroups))
      (setq savedRefs nil
            wasV2   (DTT--definition-v2-p blockName)
            existingDynamic (DTT--block-dynamic-p blockName)
            attDefsOK (DTT--definition-attdefs-ok-p blockName)
            cleanOK (DTT--block-clean-version-p blockName)
            sizeOK (DTT--definition-size-p blockName rectW rectH))
      ;; Eski 3-attribute dinamik tanimi yerinde degistirmek, mevcut Move
      ;; action'ina yeni attribute'u katmaz. Tanimi gecici ada alip dortlu
      ;; tanimi bastan kur; referanslar konumlariyla birlikte asagida tasinir.
      (if (and existingDynamic (or (not attDefsOK) (not cleanOK)))
        (progn
          (setq upgradeName (DTT--unique-upgrade-block-name)
                upgradeRefs (DTT--capture-reference-positions blockName firstStem)
                renamed     (DTT--rename-block-definition blockName upgradeName))
          (if renamed
            (progn
              (setq legacyGroups
                (append legacyGroups (list (list upgradeName upgradeRefs))))
              (setq wasV2 nil
                    existingDynamic nil
                    attDefsOK nil
                    cleanOK nil
                    sizeOK nil))
          )
        )
      )
      (if (and wasV2
               existingDynamic
               attDefsOK
               (not sizeOK))
        (progn
          (setq resizeRefs (DTT--capture-reference-positions blockName firstStem)
                sizeOK (DTT--resize-label-definition
                         blockName rectW rectH attTextH attTextStyle))
          (if sizeOK
            (foreach item resizeRefs
              ;; Ayni isimle yeniden eklemek ATTREF konumlarini yeni tanimla senkronlar.
              (DTT--migrate-reference (car item) blockName (cadr item))
            )
          )
        )
      )
      (setq reuseDef (and wasV2
                          sizeOK
                          attDefsOK
                          cleanOK
                          existingDynamic))
      (if reuseDef
        (progn
          (setq blockDef (DTT--block-object blockName)
                dynamicOK T)
          (DTT--set-definition-att-height blockName attTextH)
          (DTT--set-definition-att-style blockName attTextStyle)
          (DTT--set-all-reference-att-height blockName attTextH)
          (DTT--set-all-reference-att-style blockName attTextStyle)
        )
        (progn
          (if existingDynamic
            (setq blockDef nil)
            (progn
              (if (and (null legacyGroups) wasV2)
                (setq savedRefs (DTT--capture-reference-positions blockName firstStem))
                (if (null legacyGroups)
                  (setq savedRefs
                    (DTT--upgrade-old-references blockName rectH lay firstStem))
                )
              )
              (setq blockDef
                (DTT--ensure-label-block
                  blockName rectW rectH firstStem attTextH attTextStyle lay))
            )
          )
        )
      )
      (if (null blockDef)
        (DEG:WIN-MESSAGE "DTT\n\nTemiz etiket blocku olusturulamadi veya olculeri degismis dinamik tanim bulundu.")
        (progn
          (setq *DTT--pending-active* T
                *DTT--pending-handles* (DTT--selection-handles ss)
                *DTT--pending-gap* gap
                *DTT--pending-rectW* rectW
                *DTT--pending-rectH* rectH
                *DTT--pending-att-text-height* attTextH
                *DTT--pending-att-text-style* attTextStyle
                *DTT--pending-layer* lay
                *DTT--pending-block-name* blockName
                *DTT--pending-legacy-groups* legacyGroups
                *DTT--pending-saved-refs* savedRefs
                *DTT--pending-dynamic-ok* nil
                *DTT--resume-queued* nil)
          (if reuseDef
            (progn
              (setq *DTT--pending-dynamic-ok* T)
              (DTT--resume)
            )
            (progn
              (setq dynamicOK (DTT--author-dynamic blockName firstStem rectW rectH))
              ;; Normal durumda BSAVE/BCLOSE sonrasi kuyruktaki DTT--resume
              ;; devam eder. Kuyruk kurulamadiysa ve editor kapaliysa burada bitir.
              (if (not *DTT--resume-queued*)
                (if (DTT--block-editor-active-p)
                  (DEG:WIN-MESSAGE "DTT\n\nDinamik block editoru kapatilamadi. BSAVE ve BCLOSE sonrasi (DTT--resume) yazin.")
                  (progn
                    (setq *DTT--pending-dynamic-ok* dynamicOK)
                    (DTT--resume)
                  )
                )
              )
            )
          )
        )
      )
    )
  )
  (princ)
)
(defun DTM_ORIG
  (/ ss i ent ed lay seg len width kind trayType trayRows ladderRows fittingRows
    trayCount ladderCount fittingCount ladderMeta ladderKey ladderSeen)
  (vl-load-com)
  (prompt "\nDTM: Metraj alinacak alani secin (pencere/capraz secim): ")
  (setq ss
    (ssget
      '((0 . "LWPOLYLINE,POLYLINE,INSERT,3DFACE,HATCH,LINE"))))
  (if (null ss)
    (princ "\nDTM: Secim yapilmadi.")
    (progn
      (setq i 0 trayCount 0 ladderCount 0 fittingCount 0)
      (while (< i (sslength ss))
        (setq ent (ssname ss i)
              ed  (entget ent '("DT_FITTING"))
              lay (if ed (cdr (assoc 8 ed)) ""))
        (cond
          ((setq ladderMeta (DT--ladder-meta ent))
            (setq ladderKey (DTM--ladder-key ent ladderMeta))
            (if (and ladderKey (not (member ladderKey ladderSeen)))
              (setq ladderSeen  (cons ladderKey ladderSeen)
                    ladderRows  (DTM--add-ladder-row ladderRows ladderMeta)
                    ladderCount (1+ ladderCount))))
          ((DT--visible-tray-p ent)
            (setq seg   (DT--tray-center-seg ent)
                  width (DTM--tray-width ent)
                  trayType (DTM--tray-type ent lay))
            (if (and seg width (> width 0.0))
              (progn
                (setq len (DTM--tray-length ent))
                (if (> len 0.001)
                  (progn
                    (setq trayRows
                      (DTM--add-tray-row
                        trayRows trayType width len))
                    (setq trayCount (1+ trayCount))
                  )
                )
              )
            ))
          ((and (= (cdr (assoc 0 ed)) "INSERT") (DT--fitting-insert-p ent))
            (setq kind  (DTM--fitting-label ent)
                  width (DT--fitting-insert-width ent 0.0)
                  fittingRows (DTM--add-fitting-row fittingRows lay kind width)
                  fittingCount (1+ fittingCount)))
        )
        (setq i (1+ i))
      )
      (if (or trayRows ladderRows fittingRows)
        (DTM--show-report
          trayRows ladderRows fittingRows
          trayCount ladderCount fittingCount)
        (DEG:WIN-MESSAGE
          "DTM\n\nSecilen alanda DT tavasi, merdiven veya donus elemani bulunamadi.")
      )
    )
  )
  (princ)
)
(defun DD_ORIG (/ sel crv0 ss prepRes snapLimit *DEGZ_PRE_COMMON_TARGET_MAP*)
  (vl-load-com)
  (prompt "\nDD: Ana hat icin bir polyline sec (tikla): ")
  (setq sel (entsel))
  (if (null sel)
    (princ "\nSecim yok.")
    (progn
      (setq crv0 (car sel))
      (prompt "\nDD: Ana hatta baglanacak BLOCK'lari sec (INSERT): ")
      (setq ss (ssget '((0 . "INSERT"))))
      (if (null ss)
        (princ "\nBlock secimi yok.")
        (progn
          (princ "\nDEG_R326 RUNNING (DD)")
          (setq *DEGZ_PRE_COMMON_TARGET_MAP* nil
                snapLimit (DEG:CFG-DDDZ-NUM-OR 'DD_OFFSET 10.0))
          (if (<= snapLimit 0.0)
            (setq snapLimit (* 10.0 (DEG:PLAN-UNIT-SCALE))))
          (setq prepRes (DEGZ--preprocess-perp-row-chain crv0 ss 'DD)
                crv0 (car prepRes)
                ss (cadr prepRes))
          (if (> (sslength ss) 0)
            (setq crv0 (DEGDD--APPLY crv0 ss)))
          (if (and crv0 (entget crv0))
            (setq crv0 (DEGZ--snap-close-double-turn-entity crv0 snapLimit)))
          (princ "\nDD tamam.")
        )
      )
    )
  )
  (princ)
)

(defun DF_ORIG (/ *error* sel crv0 pick ss prepRes snapLimit
                  *DEG_DD_MODE* *DEG_DF_GUIDE* *DEGZ_PRE_COMMON_TARGET_MAP*)
  (vl-load-com)
  (setq *DEG_DD_MODE* 'DF
        *DEG_DF_GUIDE* nil)

  (defun *error* (msg)
    (if (and *DEG_DF_GUIDE* (entget *DEG_DF_GUIDE*))
      (entdel *DEG_DF_GUIDE*))
    (setq *DEG_DF_GUIDE* nil)
    (if (and msg (not (wcmatch (strcase msg) "*CANCEL*,*QUIT*,*BREAK*")))
      (princ (strcat "\nDF hata: " msg)))
    (princ)
  )

  (prompt "\nDF: Baglanti alinacak polyline segmentine tikla: ")
  (setq sel (entsel))
  (if (null sel)
    (princ "\nSecim yok.")
    (progn
      (setq crv0 (car sel)
            pick (cadr sel)
            *DEG_DF_GUIDE* (DEGDF--clicked-segment crv0 pick))
      (if (not (and *DEG_DF_GUIDE* (entget *DEG_DF_GUIDE*)))
        (princ "\nDF: Tiklanan iki nokta arasindaki polyline segmenti okunamadi.")
        (progn
          (prompt "\nDF: Ana hatta baglanacak BLOCK'lari sec (INSERT): ")
          (setq ss (ssget '((0 . "INSERT"))))
          (if (null ss)
            (princ "\nBlock secimi yok.")
            (progn
              (princ "\nDEG_R326 RUNNING (DF - SECILI SEGMENT)")
              (setq *DEGZ_PRE_COMMON_TARGET_MAP* nil
                    snapLimit (DEG:CFG-DDDZ-NUM-OR 'DF_OFFSET 10.0))
              (if (<= snapLimit 0.0)
                (setq snapLimit (* 10.0 (DEG:PLAN-UNIT-SCALE))))
              (setq prepRes (DEGZ--preprocess-perp-row-chain crv0 ss 'DF)
                    crv0 (car prepRes)
                    ss (cadr prepRes))
              (if (> (sslength ss) 0)
                (setq crv0 (DEGDD--APPLY crv0 ss)))
              (if (and crv0 (entget crv0))
                (setq crv0
                  (DEGZ--snap-close-double-turn-entity crv0 snapLimit)))
              (princ "\nDF tamam.")
            )
          )
        )
      )
    )
  )
  (if (and *DEG_DF_GUIDE* (entget *DEG_DF_GUIDE*))
    (entdel *DEG_DF_GUIDE*))
  (setq *DEG_DF_GUIDE* nil)
  (princ)
)

;; ---------------------------------------------------------------------------
;; DT lightweight composites
;;
;; A legacy tray contains roughly 28 model-space entities and a ladder can
;; contain hundreds. AutoCAD GROUP selection expands every member into the
;; pickset. The lightweight representation keeps one editable controller plus
;; one visual block reference, so normal window selection, MOVE, COPY, ERASE
;; and DT commands stay proportional to logical object count.
;; ---------------------------------------------------------------------------

(defun DT--light-app-present-p (ent app / ed)
  (and ent
       app
       (setq ed (entget ent (list app)))
       (assoc -3 ed))
)

(defun DT--light-linked-entity (ent app / ed xd rec item linked)
  (if (and ent app (setq ed (entget ent (list app))))
    (progn
      (setq xd  (assoc -3 ed)
            rec (if xd (cadr xd) nil))
      (if (and rec (= (car rec) app))
        (foreach item (cdr rec)
          (if (and (= (car item) 1005) (null linked))
            (setq linked (handent (cdr item))))))
    )
  )
  (if (DT--entity-alive-p linked) linked)
)

(defun DT--light-set-link (ent app linked / ed payload handle)
  (if (not (tblsearch "APPID" app)) (regapp app))
  (if (and ent (entget ent))
    (progn
      (setq handle (if linked (DT--ent-handle linked))
            payload (if handle (list app (cons 1005 handle)) (list app))
            ed      (entget ent '("*"))
            ed      (DT--xdata-set-app ed app payload))
      (entmod ed)
      (entupd ent)))
  ent
)

(defun DT--light-clear-app (ent app / ed)
  (if (and ent (setq ed (entget ent '("*"))))
    (progn
      (entmod (DT--xdata-remove-app ed app))
      (entupd ent)))
  ent
)

(defun DT--light-tray-visual (tray)
  (DT--light-linked-entity tray "DT_TRAY_VISUAL")
)

(defun DT--light-tray-visual-p (ent)
  (DT--light-app-present-p ent "DT_TRAY_VISUAL_MEMBER")
)

(defun DT--light-tray-visual-owner (visual)
  (DT--light-linked-entity visual "DT_TRAY_VISUAL_MEMBER")
)

(defun DT--light-tray-frame
  (tray / pts p0 p1 p2 p3 start finish z0 z1 len width rotation dz half local)
  (setq pts (DT--tray-corner-points-3d tray))
  (if (= (length pts) 4)
    (progn
      (setq p0     (nth 0 pts)
            p1     (nth 1 pts)
            p2     (nth 2 pts)
            p3     (nth 3 pts)
            start  (list
                     (/ (+ (car p0) (car p3)) 2.0)
                     (/ (+ (cadr p0) (cadr p3)) 2.0)
                     (/ (+ (if (caddr p0) (caddr p0) 0.0)
                           (if (caddr p3) (caddr p3) 0.0)) 2.0))
            finish (list
                     (/ (+ (car p1) (car p2)) 2.0)
                     (/ (+ (cadr p1) (cadr p2)) 2.0)
                     (/ (+ (if (caddr p1) (caddr p1) 0.0)
                           (if (caddr p2) (caddr p2) 0.0)) 2.0))
            z0     (caddr start)
            z1     (caddr finish)
            len    (DT--distance-xy start finish)
            width  (distance p0 p3)
            rotation (angle start finish)
            dz     (- z1 z0)
            half   (/ width 2.0)
            local  (list
                     (list 0.0 half 0.0)
                     (list len half dz)
                     (list len (- half) dz)
                     (list 0.0 (- half) 0.0)))
      (if (and (> len 0.000001) (> width 0.000001))
        (list start rotation len width dz local)))
  )
)

(defun DT--light-tray-block-name (tray frame mode sidePlan / token)
  (setq token
    (strcat
      (DT--name-safe (DT--normalize-mode mode))
      "$LAY" (DT--name-safe
               (DT--base-layer-name (cdr (assoc 8 (entget tray)))))
      "$W"  (DT--width-name (nth 3 frame))
      "$L"  (DT--width-name (nth 2 frame))
      "$DZ" (DT--width-name (nth 4 frame))
      "$H"  (DT--width-name sidePlan)
      (if (DT--entity-3d-enabled-p tray) "$D3" "$D2")
      (DT--shell-style-token)))
  (strcat "DT$TAVAHAFIF$SH4$" token)
)

(defun DT--light-block-token-number (name startToken endToken / start finish token)
  (if name
    (progn
      (setq start (vl-string-search startToken name))
      (if start
        (setq finish
          (vl-string-search endToken name (+ start (strlen startToken)))))
      (if (and start finish (> finish (+ start (strlen startToken))))
        (progn
          (setq token
            (substr
              name
              (+ start (strlen startToken) 1)
              (- finish (+ start (strlen startToken)))))
          (atof (vl-string-translate "_m" ".-" token))))))
)

(defun DT--light-legacy-bad-side-meta-p
  (tray frame meta / visual name expectedPlan visualPlan)
  (setq visual (DT--light-tray-visual tray)
        name   (if (and visual (assoc 2 (entget visual)))
                 (strcase (cdr (assoc 2 (entget visual)))))
        expectedPlan
          (if (and meta (numberp (caddr meta)) (> (caddr meta) 0.0))
            (DT--plan-side-height (caddr meta))
            0.0)
        visualPlan (DT--light-block-token-number name "$H" "$T"))
  ;; SH2 could retain a visual built with the total elevation delta even after
  ;; its center/tray metadata was repaired. Compare the block's H token with
  ;; the authoritative metadata and rebuild only the mismatching legacy tray.
  (and frame
       name
       (wcmatch name "DT$TAVAHAFIF$SH2$*")
       (numberp visualPlan)
       (> expectedPlan 0.0)
       (not (equal visualPlan expectedPlan 0.000001)))
)

(defun DT--light-create-tray-block-def
  (name frame / local pts boundary hatch made
    *DT_BLOCK_FACE_UNASSOC* *DT_BLOCK_HATCH_ASSOC_MARKER*)
  (setq pts (nth 5 frame)
        ;; AutoCAD can access-violate while associating a hatch to a 3DFACE
        ;; inside an existing drawing's new block definition. The visual block
        ;; is rebuilt when its controller stretches, so all internal hatches
        ;; can be safely non-associative and still follow every tray edit.
        *DT_BLOCK_FACE_UNASSOC* T
        *DT_BLOCK_HATCH_ASSOC_MARKER* (<= (abs (nth 4 frame)) 0.000001))
  (if (and name pts (not (tblsearch "BLOCK" name)))
    (progn
      (entmake
        (list
          '(0 . "BLOCK")
          (cons 2 name)
          '(70 . 0)
          '(10 0.0 0.0 0.0)))
      (setq boundary (DT--make-poly3d (DT--layer-linework) pts T))
      (if boundary
        (progn
          (setq hatch
            (if *DT_BLOCK_FACE_UNASSOC*
              (DT--make-plane-hatch-unassoc (DT--layer-visible) pts)
              (DT--make-assoc-hatch-plane
                boundary
                (DT--layer-visible)
                pts
                (DT--mode-hatch-pattern *DT_ACTIVE_MODE*)
                (DT--mode-hatch-color *DT_ACTIVE_MODE*))))
          (if (vl-string-search "$D3$" (strcase name))
            (DT--make-tray-sidewalls
              boundary (nth 0 pts) (nth 1 pts) (nth 2 pts) (nth 3 pts)))
          (setq made T)))
      (entmake '((0 . "ENDBLK")))
      (if made
        (progn
          ;; These lightweight visual hatches are intentionally internal and
          ;; non-associative. Do not run the ActiveX association pass here;
          ;; it is unnecessary and can abort migration inside LOAD.
          (DT--set-block-linework-050 name)))
      made)
    (if (tblsearch "BLOCK" name) T nil))
)

(defun DT--light-create-tray-visual
  (tray / frame meta baseLayer mode nominal inferredHeight legacyBad sideMm sidePlan name insert
    *DT_ACTIVE_MODE* *DT_ACTIVE_LAYER* *DT_ACTIVE_ELEVATION*
    *DT_ACTIVE_SIDE_HEIGHT* *DT_ACTIVE_SIDE_HEIGHT_MM* *DT_ACTIVE_3D*)
  (setq frame     (DT--light-tray-frame tray)
        meta      (DT--tray-meta-effective tray)
        baseLayer (DT--base-layer-name (cdr (assoc 8 (entget tray))))
        mode      (DT--normalize-mode
                    (if (and meta (car meta))
                      (car meta)
                      (DT--mode-from-layer baseLayer)))
        nominal   (if (and meta (numberp (cadr meta)) (> (cadr meta) 0.0))
                    (cadr meta)
                    (/ (nth 3 frame)
                       (max 0.000000001 (DEG:PLAN-UNIT-SCALE))))
        inferredHeight (DT--linked-sidewall-height tray)
        legacyBad (DT--light-legacy-bad-side-meta-p tray frame meta)
        sideMm
          (cond
            ((and meta
                  (numberp (caddr meta))
                  (> (caddr meta) 0.0))
              (caddr meta))
            ((> inferredHeight 0.000001)
              (/ (* inferredHeight 10.0)
                 (max 0.000000001 (DEG:PLAN-UNIT-SCALE))))
            (T (DT--last-side-height nominal)))
        sidePlan  (DT--plan-side-height sideMm)
        *DT_ACTIVE_MODE* mode
        *DT_ACTIVE_LAYER* baseLayer
        *DT_ACTIVE_ELEVATION* (if frame (caddr (car frame)) 0.0)
        *DT_ACTIVE_SIDE_HEIGHT_MM* sideMm
        *DT_ACTIVE_SIDE_HEIGHT* sidePlan
        *DT_ACTIVE_3D* (DT--entity-3d-enabled-p tray))
  (if (and frame (> sidePlan 0.0))
    (progn
      ;; Loose/legacy trays may not have route metadata. Persist the values
      ;; before deleting their model-space sidewalls so later STRETCH rebuilds
      ;; do not have to infer height from geometry that no longer exists.
      (if (null meta)
        (DT--set-tray-meta-one
          tray
          mode
          nominal
          sideMm
          (DEG:NUM->STR (caddr (car frame)))))
      (DT--ensure-type-layers)
      (setq name (DT--light-tray-block-name tray frame mode sidePlan))
      (if (DT--light-create-tray-block-def name frame)
        (setq insert
          (entmakex
            (list
              '(0 . "INSERT")
              (cons 2 name)
              (cons 8 (DT--layer-visible))
              (cons 10 (car frame))
              '(41 . 1.0)
              '(42 . 1.0)
              '(43 . 1.0)
              (cons 50 (cadr frame))))))
      (if insert
        (progn
          (DT--light-set-link tray "DT_TRAY_VISUAL" insert)
          (DT--light-set-link insert "DT_TRAY_VISUAL_MEMBER" tray)))
      insert))
)

(defun DT--light-delete-legacy-tray-geometry (tray / entities ent handle)
  (setq entities
    (DT--unique-alive-entities
      (append (DT--linked-hatches tray) (DT--linked-sidewalls tray))))
  (foreach ent entities
    (if (and ent (entget ent))
      (progn
        (setq handle (DT--ent-handle ent))
        (vl-catch-all-apply 'entdel (list ent))
        (if handle (DT--remember-deleted-handle handle)))))
  (DT--light-clear-app tray "DT_TRAY_HATCH")
  (DT--light-clear-app tray "DT_TRAY_SIDEWALL")
  (length entities)
)

(defun DT--light-delete-tray-composite (tray / visual)
  (if (and tray (DT--entity-alive-p tray))
    (progn
      (setq visual (DT--light-tray-visual tray))
      (DT--delete-tray-group tray)
      (DT--light-clear-app tray "DT_TRAY_VISUAL")
      (if (and visual (DT--entity-alive-p visual))
        (progn
          (DT--light-clear-app visual "DT_TRAY_VISUAL_MEMBER")
          (DT--safe-delete-ent visual)))
      (DT--safe-delete-ent tray)
      T))
)

(defun DT--delete-ents (ents / ent owner)
  ;; Rebuild/merge operations must remove both halves of a lightweight tray.
  ;; Deleting only the controller leaves its visual INSERT behind and produces
  ;; the double-layer tray seen after a junction is created.
  (foreach ent ents
    (cond
      ((and (DT--visible-tray-p ent)
            (DT--light-tray-visual ent))
        (DT--light-delete-tray-composite ent))
      ((DT--light-tray-visual-p ent)
        (setq owner (DT--light-tray-visual-owner ent))
        (if (and owner (DT--entity-alive-p owner))
          (DT--light-delete-tray-composite owner)
          (DT--safe-delete-ent ent)))
      (T (DT--safe-delete-ent ent))))
)

(defun DT--light-clean-orphan-tray-visuals (/ ss i visual owner count)
  (if (tblsearch "APPID" "DT_TRAY_VISUAL_MEMBER")
    (setq ss
      (ssget "_X"
        '((0 . "INSERT") (-3 ("DT_TRAY_VISUAL_MEMBER"))))))
  (if ss
    (progn
      (setq i 0)
      (while (< i (sslength ss))
        (setq visual (ssname ss i)
              owner  (DT--light-tray-visual-owner visual))
        (if (not
              (and owner
                   (DT--entity-alive-p owner)
                   (eq visual (DT--light-tray-visual owner))))
          (progn
            (DT--safe-delete-ent visual)
            (setq count (1+ (if count count 0)))))
        (setq i (1+ i)))))
  (if count count 0)
)

(defun DT--light-valid-tray-visual-p (tray visual / name expected3d)
  (if (and tray
           visual
           (DT--entity-alive-p visual)
           (eq tray (DT--light-tray-visual-owner visual)))
    (progn
      (setq name
        (strcase
          (if (assoc 2 (entget visual))
            (cdr (assoc 2 (entget visual)))
            ""))
            expected3d (if (DT--entity-3d-enabled-p tray) "$D3$" "$D2$"))
      (or
        (and
          (wcmatch name "DT$TAVAHAFIF$SH4$*")
          (vl-string-search expected3d name))
        (and
          (DT--entity-3d-enabled-p tray)
          (wcmatch name "DT$TAVAHAFIF$SH3$*"))
        (and
          (wcmatch name "DT$TAVAHAFIF$SH2$*")
          (DT--entity-3d-enabled-p tray)
          (not
            (DT--light-legacy-bad-side-meta-p
              tray
              (DT--light-tray-frame tray)
              (DT--tray-meta-effective tray)))))))
)

(defun DT--tray-group-entities (tray / visual)
  (setq visual (DT--light-tray-visual tray))
  (if (DT--light-valid-tray-visual-p tray visual)
    (DT--unique-alive-entities (list tray visual))
    (DT--unique-alive-entities
      (append (list tray)
              (DT--linked-hatches tray)
              (DT--linked-sidewalls tray))))
)

(defun DT--refresh-tray-group (tray / name entities)
  (if (and tray (DT--visible-tray-p tray))
    (progn
      (setq name (DT--tray-group-name tray))
      (DT--delete-tray-group tray)
      (setq entities (DT--tray-group-entities tray))
      (if (and name (> (length entities) 1))
        (DT--make-group-object name entities))))
)

(defun DT--light-migrate-tray (tray / visual newVisual)
  (if (and tray (DT--visible-tray-p tray))
    (progn
      (setq visual (DT--light-tray-visual tray))
      (if (DT--light-valid-tray-visual-p tray visual)
        (progn
          (DT--refresh-tray-group tray)
          tray)
        (progn
          (setq newVisual (DT--light-create-tray-visual tray))
          (if newVisual
            (progn
              (if (and visual
                       (DT--entity-alive-p visual)
                       (not (eq visual newVisual)))
                (progn
                  (DT--light-clear-app visual "DT_TRAY_VISUAL_MEMBER")
                  (DT--safe-delete-ent visual)))
              (DT--light-delete-legacy-tray-geometry tray)
              (DT--refresh-tray-group tray)
              tray)))))))

(defun DT--light-all-trays (/ app ss i ent out)
  (foreach app '("DT_TRAY_VISUAL" "DT_TRAY_HATCH")
    (if (tblsearch "APPID" app)
      (progn
        (setq ss
          (ssget "_X"
            (list
              (cons 0 "LWPOLYLINE,POLYLINE")
              (list -3 (list app)))))
        (if ss
          (progn
            (setq i 0)
            (while (< i (sslength ss))
              (setq ent (ssname ss i))
              (if (and (DT--visible-tray-p ent)
                       (not (DT--entity-in-list-p ent out)))
                (setq out (append out (list ent))))
              (setq i (1+ i))))))))
  out
)

(defun DT--light-migrate-all-trays (/ tray count)
  (foreach tray (DT--light-all-trays)
    (if (DT--light-migrate-tray tray)
      (setq count (1+ (if count count 0)))))
  (if count count 0)
)

(defun DT--repair-existing-tray-sidewalls ()
  (DT--light-migrate-all-trays)
)

(defun DT--repair-existing-tray-groups (/ tray count)
  (foreach tray (DT--light-all-trays)
    (if (DT--refresh-tray-group tray)
      (setq count (1+ (if count count 0)))))
  (if count count 0)
)

(defun DT--rebuild-tray-sidewall-geometry (tray / oldVisual newVisual)
  (if (and tray (DT--visible-tray-p tray))
    (progn
      (setq oldVisual (DT--light-tray-visual tray))
      (if oldVisual
        (progn
          (DT--light-clear-app oldVisual "DT_TRAY_VISUAL_MEMBER")
          (vl-catch-all-apply 'entdel (list oldVisual))))
      (DT--light-clear-app tray "DT_TRAY_VISUAL")
      (setq newVisual (DT--light-create-tray-visual tray))
      (if newVisual
        (progn
          (DT--refresh-tray-group tray)
          T))))
)

(defun DT--light-legacy-make-straight
  (a b width / u n h p1 p2 p3 p4 ent hatch pts zA zB oldElevation)
  (if (> (distance a b) 0.001)
    (progn
      (setq u  (DT--seg-unit a b)
            n  (DT--perp u)
            h  (/ width 2.0)
            zA (DT--build-elevation-at-point a)
            zB (DT--build-elevation-at-point b)
            p1 (DT--point-at-elevation (DT--pt+ a n h) zA)
            p2 (DT--point-at-elevation (DT--pt+ b n h) zB)
            p3 (DT--point-at-elevation (DT--pt+ b n (- h)) zB)
            p4 (DT--point-at-elevation (DT--pt+ a n (- h)) zA)
            pts (list p1 p2 p3 p4))
      (if (equal zA zB 0.000001)
        (progn
          (setq oldElevation        (DT--active-elevation)
                *DT_ACTIVE_ELEVATION* zA
                ent                 (DT--make-poly (DT--layer-linework) pts T))
          (if ent
            (setq hatch
              (DT--make-assoc-hatch
                ent
                (DT--layer-visible)
                pts
                (DT--mode-hatch-pattern *DT_ACTIVE_MODE*)
                (DT--mode-hatch-color *DT_ACTIVE_MODE*))))
          (setq *DT_ACTIVE_ELEVATION* oldElevation))
        (progn
          (setq ent (DT--make-poly3d (DT--layer-linework) pts T))
          (if ent
            (setq hatch
              (DT--make-assoc-hatch-plane
                ent
                (DT--layer-visible)
                pts
                (DT--mode-hatch-pattern *DT_ACTIVE_MODE*)
                (DT--mode-hatch-color *DT_ACTIVE_MODE*))))))
      (if (and ent hatch) (DT--xdata-link-hatch ent hatch))
      (if ent
        (progn
          (DT--make-tray-sidewalls ent p1 p2 p3 p4)
          (DT--refresh-tray-group ent)))
      ent))
)

(defun DT--light-preview-make-straight
  (a b width / u n h p1 p2 p3 p4 pts zA zB oldElevation ent)
  (if (> (distance a b) 0.001)
    (progn
      (setq u  (DT--seg-unit a b)
            n  (DT--perp u)
            h  (/ width 2.0)
            zA (DT--build-elevation-at-point a)
            zB (DT--build-elevation-at-point b)
            p1 (DT--point-at-elevation (DT--pt+ a n h) zA)
            p2 (DT--point-at-elevation (DT--pt+ b n h) zB)
            p3 (DT--point-at-elevation (DT--pt+ b n (- h)) zB)
            p4 (DT--point-at-elevation (DT--pt+ a n (- h)) zA)
            pts (list p1 p2 p3 p4))
      (if (equal zA zB 0.000001)
        (progn
          (setq oldElevation          (DT--active-elevation)
                *DT_ACTIVE_ELEVATION* zA
                ent                   (DT--make-poly (DT--layer-linework) pts T)
                *DT_ACTIVE_ELEVATION* oldElevation))
        (setq ent (DT--make-poly3d (DT--layer-linework) pts T)))
      ent))
)

(defun DT--make-straight-piece (a b width / tray)
  (if (and (boundp '*DT_LIVE_PREVIEW_LIGHTWEIGHT*)
           *DT_LIVE_PREVIEW_LIGHTWEIGHT*)
    (setq tray (DT--light-preview-make-straight a b width))
    (progn
      (setq tray (DT--light-legacy-make-straight a b width))
      (if tray
        (progn
          (DT--set-entity-3d-mode tray (DT--active-3d-enabled-p))
          (DT--light-migrate-tray tray)))))
  tray
)

(defun DT--light-insert-point (ent / ed)
  (setq ed (if ent (entget ent)))
  (if (and ed (= (cdr (assoc 0 ed)) "INSERT")) (cdr (assoc 10 ed)))
)

(defun DT--light-insert-angle (ent / ed)
  (setq ed (if ent (entget ent)))
  (if ed (if (assoc 50 ed) (cdr (assoc 50 ed)) 0.0))
)

(defun DT--light-owned-visual-p (visual / owner)
  (setq owner (DT--light-tray-visual-owner visual))
  (and owner (eq visual (DT--light-tray-visual owner)))
)

(defun DT--light-entity-reactor-groups (ent / ed item candidate out)
  (if (and ent (setq ed (entget ent '("*"))))
    (foreach item ed
      (if (= (car item) 330)
        (progn
          (setq candidate (cdr item))
          (if (and candidate
                   (entget candidate)
                   (= (cdr (assoc 0 (entget candidate))) "GROUP")
                   (not (DT--entity-in-list-p candidate out)))
            (setq out (append out (list candidate))))))))
  out
)

(defun DT--light-group-name-for-object (group / dictionary record item name hit)
  (setq dictionary (DT--existing-group-dictionary))
  (if (and dictionary group)
    (progn
      (setq record (entget dictionary)
            name   nil)
      (foreach item record
        (cond
          ((= (car item) 3) (setq name (cdr item)))
          ((and name (member (car item) '(350 360)))
            (if (eq (cdr item) group) (setq hit name))
            (setq name nil))))))
  hit
)

(defun DT--light-remove-extra-groups (entities keepName / entity group name seen)
  (foreach entity entities
    (foreach group (DT--light-entity-reactor-groups entity)
      (if (not (DT--entity-in-list-p group seen))
        (progn
          (setq seen (append seen (list group))
                name (DT--light-group-name-for-object group))
          (if (and name
                   (or (null keepName) (/= (strcase name) (strcase keepName))))
            (DT--delete-group-by-name name))))))
  T
)

(defun DT--light-group-members-object (group / ed item members)
  (if (and group (setq ed (entget group)))
    (foreach item ed
      (if (and (= (car item) 340) (DT--entity-alive-p (cdr item)))
        (setq members (append members (list (cdr item)))))))
  members
)

(defun DT--light-actual-ladder-group (ent / group members hit)
  (foreach group (DT--light-entity-reactor-groups ent)
    (if (null hit)
      (progn
        (setq members (DT--light-group-members-object group))
        (if (and (> (length members) 1)
                 (DT--entity-in-list-p ent members)
                 (DT--ladder-meta (car members)))
          (setq hit group)))))
  hit
)

(defun DT--ladder-members (ent / named group members)
  (setq named (DT--ladder-named-members ent))
  (cond
    (named named)
    ((setq group (DT--light-actual-ladder-group ent))
      (setq members (DT--light-group-members-object group))
      (if members members (list ent)))
    ((and ent (entget ent)) (list ent)))
)

(defun DT--ladder-attached-group-p (ent)
  (> (length (DT--ladder-members ent)) 1)
)

(defun DT--ladder-selection-key (ent / control group)
  (cond
    ((DT--light-ladder-control-p ent)
      (DT--ent-handle ent))
    ((DT--light-ladder-visual-p ent)
      (setq control (DT--light-ladder-controller ent))
      (if control (DT--ent-handle control) (DT--ent-handle ent)))
    ((setq group (DT--light-actual-ladder-group ent))
      (DT--ent-handle group))
    (T (DT--ent-handle ent)))
)

(defun DTT--ladder-key (ent)
  (DT--ladder-selection-key ent)
)

(defun DTM--ladder-key (ent meta / key)
  (setq key (DT--ladder-selection-key ent))
  (if key (strcat "LADDER|" (strcase key)))
)

(defun DT--delete-ladder-composite (ent / members entity handle)
  (setq members (DT--ladder-members ent))
  (DT--light-remove-extra-groups members nil)
  (foreach entity members
    (if (and entity (entget entity))
      (progn
        (setq handle (DT--ent-handle entity))
        (vl-catch-all-apply 'entdel (list entity))
        (if handle (DT--remember-deleted-handle handle)))))
  T
)

(defun DT--light-find-copy-visual
  (tray / frame staleVisual staleEd expectedName ss i candidate ed point rotation hit)
  (setq frame (DT--light-tray-frame tray))
  (if frame
    (progn
      ;; COPY keeps the old visual handle in controller XData. That old insert
      ;; still gives the exact reusable block definition, even on legacy trays
      ;; that do not carry DT_META yet.
      (setq staleVisual  (DT--light-tray-visual tray)
            staleEd      (if staleVisual (entget staleVisual))
            expectedName (if staleEd (cdr (assoc 2 staleEd))))
      (if (tblsearch "APPID" "DT_TRAY_VISUAL_MEMBER")
        (setq ss
          (ssget "_X"
            '((0 . "INSERT") (-3 ("DT_TRAY_VISUAL_MEMBER"))))))
      (if ss
        (progn
          (setq i 0)
          (while (and (< i (sslength ss)) (null hit))
            (setq candidate (ssname ss i)
                  ed        (entget candidate)
                  point     (cdr (assoc 10 ed))
                  rotation  (if (assoc 50 ed) (cdr (assoc 50 ed)) 0.0))
            (if (and expectedName
                     (= (strcase (cdr (assoc 2 ed))) (strcase expectedName))
                     (equal point (car frame) 0.001)
                     (equal rotation (cadr frame) 0.000001)
                     (not (DT--light-owned-visual-p candidate)))
              (setq hit candidate))
            (setq i (1+ i))))))
  )
  hit
)

(defun DT--light-repair-tray-copies (/ tray visual candidate count)
  (foreach tray (DT--light-all-trays)
    (setq visual (DT--light-tray-visual tray))
    (if (not (DT--light-valid-tray-visual-p tray visual))
      (progn
        (setq candidate (DT--light-find-copy-visual tray))
        (if candidate
          (progn
            (DT--light-set-link tray "DT_TRAY_VISUAL" candidate)
            (DT--light-set-link candidate "DT_TRAY_VISUAL_MEMBER" tray)
            (DT--light-remove-extra-groups
              (list tray candidate) (DT--tray-group-name tray))
            (DT--refresh-tray-group tray)
            (setq count (1+ (if count count 0))))
          (if (DT--light-migrate-tray tray)
            (setq count (1+ (if count count 0))))))))
  (if count count 0)
)

;; Ladder lightweight controller + visual INSERT.
(defun DT--light-ladder-control-p (ent)
  (DT--light-app-present-p ent "DT_LADDER_CONTROL")
)

(defun DT--light-ladder-visual-p (ent)
  (DT--light-app-present-p ent "DT_LADDER_VISUAL")
)

(defun DT--light-ladder-visual (control)
  (DT--light-linked-entity control "DT_LADDER_CONTROL")
)

(defun DT--light-ladder-controller (visual)
  (DT--light-linked-entity visual "DT_LADDER_VISUAL")
)

(defun DT--light-ladder-controller-points
  (base rotation nominal side topElevation bottomElevation /
    planWidth sidePlan half front local)
  (setq planWidth (DT--plan-width nominal)
        sidePlan  (DT--plan-side-height side)
        half      (/ planWidth 2.0)
        front     (- (/ sidePlan 2.0))
        local
          (list
            (list (- half) front 0.0)
            (list half front 0.0)
            (list half front (- bottomElevation topElevation))
            (list (- half) front (- bottomElevation topElevation))))
  (mapcar
    '(lambda (point)
       (DT--ladder-world-point
         (DT--point-at-elevation base topElevation) rotation point))
    local)
)

(defun DT--light-make-ladder-controller
  (base rotation mode nominal side topElevation bottomElevation / pts control)
  (setq pts
    (DT--light-ladder-controller-points
      base rotation nominal side topElevation bottomElevation))
  (if pts
    (setq control
      (DT--make-poly3d
        (DT--line-layer-name (cadr (DT--find-type mode))) pts T)))
  control
)

(defun DT--make-ladder-composite-at
  (base rotation mode nominal side topElevation bottomElevation /
    visual control groupId groupName)
  (setq visual
    (DT--make-ladder-block-at
      base rotation mode nominal side topElevation bottomElevation))
  (if visual
    (setq control
      (DT--light-make-ladder-controller
        base rotation mode nominal side topElevation bottomElevation)))
  (if (and visual control)
    (progn
      (setq groupId   (DT--ent-handle control)
            groupName (DT--ladder-group-name groupId))
      (DT--set-ladder-meta
        control mode nominal side topElevation bottomElevation groupId)
      (DT--set-ladder-meta
        visual mode nominal side topElevation bottomElevation groupId)
      (DT--light-set-link control "DT_LADDER_CONTROL" visual)
      (DT--light-set-link visual "DT_LADDER_VISUAL" control)
      (DT--make-group-object groupName (list control visual))
      (DT--ensure-composite-pickstyle)
      control)
    (progn
      (if visual (vl-catch-all-apply 'entdel (list visual)))
      (if control (vl-catch-all-apply 'entdel (list control)))
      nil))
)

(defun DT--light-legacy-ladder-top-cap-entity-p
  (ent / meta top ed typ elevation)
  (setq meta      (DT--ladder-meta ent)
        top       (if meta (nth 3 meta))
        ed        (if ent (entget ent))
        typ       (if ed (cdr (assoc 0 ed)))
        elevation (if ed (DT--ladder-entity-vertex-elevation ent)))
  (and
    meta
    (member typ '("LWPOLYLINE" "POLYLINE"))
    (numberp top)
    (numberp elevation)
    (equal elevation top 0.001))
)

(defun DT--light-legacy-ladder-top-cap
  (ent / meta top entity ed typ elevation difference best bestDifference)
  (setq meta (DT--ladder-meta ent)
        top  (if meta (nth 3 meta)))
  (foreach entity (DT--ladder-members ent)
    (setq ed  (if entity (entget entity))
          typ (if ed (cdr (assoc 0 ed))))
    (if (and (member typ '("LWPOLYLINE" "POLYLINE")) (numberp top))
      (progn
        (setq elevation  (DT--ladder-entity-vertex-elevation entity)
              difference (abs (- elevation top)))
        (if (or (null bestDifference) (< difference bestDifference))
          (setq best entity bestDifference difference)))))
  (if (and bestDifference (<= bestDifference 0.001)) best)
)

(defun DT--light-legacy-ladder-placement
  (ent / ed typ meta cap pts count point sumX sumY first second)
  (setq ed   (if ent (entget ent))
        typ  (if ed (cdr (assoc 0 ed)))
        meta (DT--ladder-meta ent))
  (cond
    ((= typ "INSERT")
      (list
        (cdr (assoc 10 ed))
        (if (assoc 50 ed) (cdr (assoc 50 ed)) 0.0)))
    (meta
      (setq cap (DT--light-legacy-ladder-top-cap ent)
            pts (if cap (g365_get_pts cap)))
      (if (and pts (>= (length pts) 2))
        (progn
          (foreach point pts
            (setq sumX (+ (if sumX sumX 0.0) (car point))
                  sumY (+ (if sumY sumY 0.0) (cadr point))))
          (setq count  (float (length pts))
                first  (car pts)
                second (cadr pts))
          (list
            (list (/ sumX count) (/ sumY count) (nth 3 meta))
            (angle first second))))))
)

(defun DT--ladder-top-cap-entity-p (ent)
  (if (DT--light-ladder-control-p ent)
    T
    (DT--light-legacy-ladder-top-cap-entity-p ent))
)

(defun DT--ladder-top-cap (ent / control)
  (cond
    ((DT--light-ladder-control-p ent) ent)
    ((DT--light-ladder-visual-p ent)
      (setq control (DT--light-ladder-controller ent))
      (if control control ent))
    (T (DT--light-legacy-ladder-top-cap ent)))
)

(defun DT--light-ladder-placement
  (control / pts p0 p1 frontMid meta sidePlan u normal base)
  (setq pts (DT--entity-points3d control))
  (if (and pts (>= (length pts) 2))
    (progn
      (setq p0   (nth 0 pts)
            p1   (nth 1 pts)
            frontMid
              (list
                (/ (+ (car p0) (car p1)) 2.0)
                (/ (+ (cadr p0) (cadr p1)) 2.0)
                (/ (+ (caddr p0) (caddr p1)) 2.0))
            meta     (DT--ladder-meta control)
            sidePlan (if meta (DT--plan-side-height (nth 2 meta)) 0.0)
            u        (DT--seg-unit p0 p1)
            normal   (if u (DT--perp u))
            base     (if normal
                       (DT--pt-shift-xy frontMid normal (/ sidePlan 2.0))
                       frontMid))
      (list base (angle p0 p1))))
)

(defun DT--ladder-placement-data (ent / control result)
  (cond
    ((DT--light-ladder-control-p ent)
      (DT--light-ladder-placement ent))
    ((DT--light-ladder-visual-p ent)
      (setq control (DT--light-ladder-controller ent))
      (if control (DT--light-ladder-placement control)))
    (T (DT--light-legacy-ladder-placement ent)))
)

(defun DT--light-ladder-signature (control)
  (if (DT--light-ladder-control-p control)
    (DT--entity-points3d control))
)

(defun DT--light-all-ladder-controls (/ ss i ent out)
  (if (tblsearch "APPID" "DT_LADDER_CONTROL")
    (setq ss
      (ssget "_X"
        '((0 . "LWPOLYLINE,POLYLINE") (-3 ("DT_LADDER_CONTROL"))))))
  (if ss
    (progn
      (setq i 0)
      (while (< i (sslength ss))
        (setq ent (ssname ss i))
        (if (DT--entity-alive-p ent) (setq out (append out (list ent))))
        (setq i (1+ i)))))
  out
)

(defun DT--light-ladder-signature-map (/ control out)
  (foreach control (DT--light-all-ladder-controls)
    (setq out
      (cons
        (cons (DT--ent-handle control)
              (DT--light-ladder-signature control))
        out)))
  out
)

(defun DT--light-rebuild-ladder (control / pts meta p0 p1 p2 p3 base rotation
    scale nominal side top bottom oldVisual newVisual groupId groupName)
  (setq pts  (DT--entity-points3d control)
        meta (DT--ladder-meta control))
  (if (and (= (length pts) 4) meta)
    (progn
      (setq p0       (nth 0 pts)
            p1       (nth 1 pts)
            p2       (nth 2 pts)
            p3       (nth 3 pts)
            base     (list
                       (/ (+ (car p0) (car p1)) 2.0)
                       (/ (+ (cadr p0) (cadr p1)) 2.0)
                       (/ (+ (caddr p0) (caddr p1)) 2.0))
            rotation (angle p0 p1)
            scale    (max 0.000000001 (DEG:PLAN-UNIT-SCALE))
            nominal (/ (distance p0 p1) scale)
            side     (nth 2 meta)
            top      (/ (+ (caddr p0) (caddr p1)) 2.0)
            bottom   (/ (+ (caddr p2) (caddr p3)) 2.0)
            oldVisual (DT--light-ladder-visual control))
      (if (and oldVisual
               (entget oldVisual)
               (eq control (DT--light-ladder-controller oldVisual)))
        (vl-catch-all-apply 'entdel (list oldVisual)))
      (DT--light-clear-app control "DT_LADDER_CONTROL")
      (setq newVisual
        (DT--make-ladder-block-at
          base rotation (car meta) nominal side top bottom))
      (if newVisual
        (progn
          (setq groupId   (DT--ent-handle control)
                groupName (DT--ladder-group-name groupId))
          (DT--delete-group-by-name groupName)
          (DT--set-ladder-meta control (car meta) nominal side top bottom groupId)
          (DT--set-ladder-meta newVisual (car meta) nominal side top bottom groupId)
          (DT--light-set-link control "DT_LADDER_CONTROL" newVisual)
          (DT--light-set-link newVisual "DT_LADDER_VISUAL" control)
          (DT--make-group-object groupName (list control newVisual))
          T))))
)

(defun DT--light-update-label-links (oldMembers newControl / refs ref handle)
  (if (and oldMembers newControl)
    (progn
      (setq refs (DTT--references "e_tava_etiket"))
      (foreach ref refs
        (setq handle (DTT--reference-tray-handle ref))
        (if (and handle (member (strcase handle) oldMembers))
          (DTT--set-reference-tray ref newControl)))))
)

(defun DT--light-migrate-legacy-ladder
  (ent / meta members handles placement newControl)
  (setq meta    (DT--ladder-meta ent)
        members (DT--ladder-members ent))
  (if (and meta
           (not (DT--light-ladder-control-p ent))
           (not (DT--light-ladder-visual-p ent)))
    (progn
      (foreach ent members
        (setq handles (cons (strcase (DT--ent-handle ent)) handles)))
      (setq placement (DT--light-legacy-ladder-placement ent))
      (if placement
        (setq newControl
          (DT--make-ladder-composite-at
            (car placement) (cadr placement)
            (car meta) (nth 1 meta) (nth 2 meta) (nth 3 meta) (nth 4 meta))))
      (if newControl
        (progn
          (DT--light-update-label-links handles newControl)
          (DT--delete-ladder-composite ent)
          newControl))))
)

(defun DT--light-migrate-all-ladders (/ ss i ent meta key seen count)
  (if (tblsearch "APPID" (DT--ladder-meta-app))
    (setq ss
      (ssget "_X"
        (list (list -3 (list (DT--ladder-meta-app)))))))
  (if ss
    (progn
      (setq i 0)
      (while (< i (sslength ss))
        (setq ent  (ssname ss i)
              meta (DT--ladder-meta ent)
              key  (if meta (DT--ladder-selection-key ent)))
        (if (and meta
                 (not (DT--light-ladder-control-p ent))
                 (not (DT--light-ladder-visual-p ent))
                 (not (member key seen)))
          (progn
            (setq seen (cons key seen))
            (if (DT--light-migrate-legacy-ladder ent)
              (setq count (1+ (if count count 0))))))
        (setq i (1+ i)))))
  (if count count 0)
)

(defun DT--light-owned-ladder-visual-p (visual / control)
  (setq control (DT--light-ladder-controller visual))
  (and control (eq visual (DT--light-ladder-visual control)))
)

(defun DT--light-find-copy-ladder-visual
  (control / placement base rotation staleVisual staleEd expectedName
    ss i candidate ed point candidateRotation hit)
  (setq placement    (DT--light-ladder-placement control)
        base         (if placement (car placement))
        rotation     (if placement (cadr placement))
        staleVisual  (DT--light-ladder-visual control)
        staleEd      (if staleVisual (entget staleVisual))
        expectedName (if staleEd (cdr (assoc 2 staleEd))))
  (if (and base expectedName (tblsearch "APPID" "DT_LADDER_VISUAL"))
    (setq ss
      (ssget "_X"
        '((0 . "INSERT") (-3 ("DT_LADDER_VISUAL"))))))
  (if ss
    (progn
      (setq i 0)
      (while (and (< i (sslength ss)) (null hit))
        (setq candidate         (ssname ss i)
              ed                (entget candidate)
              point             (cdr (assoc 10 ed))
              candidateRotation (if (assoc 50 ed) (cdr (assoc 50 ed)) 0.0))
        (if (and (= (strcase (cdr (assoc 2 ed))) (strcase expectedName))
                 (equal point base 0.001)
                 (equal candidateRotation rotation 0.000001)
                 (not (DT--light-owned-ladder-visual-p candidate)))
          (setq hit candidate))
        (setq i (1+ i)))))
  hit
)

(defun DT--light-repair-ladder-copies
  (/ control visual candidate meta groupId groupName)
  ;; A copied two-member group can keep stale XData. The normal command path
  ;; rebuilds any changed controller; unchanged copies are paired by the visual
  ;; INSERT that shares their top-center point.
  (foreach control (DT--light-all-ladder-controls)
    (setq visual (DT--light-ladder-visual control))
    (if (or (null visual)
            (not (eq control (DT--light-ladder-controller visual))))
      (progn
        (setq candidate (DT--light-find-copy-ladder-visual control)
              meta      (DT--ladder-meta control))
        (if (and candidate meta)
          (progn
            (setq groupId   (DT--ent-handle control)
                  groupName (DT--ladder-group-name groupId))
            (DT--set-ladder-meta
              control (car meta) (nth 1 meta) (nth 2 meta)
              (nth 3 meta) (nth 4 meta) groupId)
            (DT--set-ladder-meta
              candidate (car meta) (nth 1 meta) (nth 2 meta)
              (nth 3 meta) (nth 4 meta) groupId)
            (DT--light-set-link control "DT_LADDER_CONTROL" candidate)
            (DT--light-set-link candidate "DT_LADDER_VISUAL" control)
            (DT--light-remove-extra-groups
              (list control candidate) groupName)
            (DT--delete-group-by-name groupName)
            (DT--make-group-object groupName (list control candidate)))
          (DT--light-rebuild-ladder control)))
      (progn
        (setq groupId   (DT--ent-handle control)
              groupName (DT--ladder-group-name groupId))
        (DT--set-ladder-meta
          control
          (car (DT--ladder-meta control))
          (nth 1 (DT--ladder-meta control))
          (nth 2 (DT--ladder-meta control))
          (nth 3 (DT--ladder-meta control))
          (nth 4 (DT--ladder-meta control))
          groupId)
        (DT--set-ladder-meta
          visual
          (car (DT--ladder-meta control))
          (nth 1 (DT--ladder-meta control))
          (nth 2 (DT--ladder-meta control))
          (nth 3 (DT--ladder-meta control))
          (nth 4 (DT--ladder-meta control))
          groupId)
        (DT--delete-group-by-name groupName)
        (DT--make-group-object groupName (list control visual)))))
  T
)

(defun DT--tray-center-seg-from-corners
  (pts / p0 p1 p2 p3 l01 l12)
  (if (and pts (>= (length pts) 4))
    (progn
      (setq p0  (nth 0 pts)
            p1  (nth 1 pts)
            p2  (nth 2 pts)
            p3  (nth 3 pts)
            l01 (distance p0 p1)
            l12 (distance p1 p2))
      (if (>= l01 l12)
        (list (DT--pt-mid p0 p3) (DT--pt-mid p1 p2))
        (list (DT--pt-mid p0 p1) (DT--pt-mid p3 p2))))))

(defun DT--tray-signature-center-seg (signature)
  (if (and (listp signature) (> (length signature) 4))
    (DT--tray-center-seg-from-corners (cdr signature))))

(defun DT--tray-signature-map (/ tray handle signature out)
  ;; Lightweight trays retain their editable boundary as the controller.
  ;; Include that controller in command snapshots so STRETCH/MOVE is visible
  ;; to both the visual rebuild and the hidden network-center synchronizer.
  (foreach tray (DT--light-all-trays)
    (setq handle    (DT--ent-handle tray)
          signature (DT--tray-geometry-signature tray))
    (if (and handle signature)
      (setq out (cons (cons handle signature) out))))
  out
)

(defun DT--replace-route-point-near
  (pts oldPoint newPoint tol / point out changed)
  (foreach point pts
    (if (and (not changed)
             (<= (DT--distance-xy point oldPoint) tol))
      (progn
        (setq out
          (append out
            (list
              (list
                (car newPoint)
                (cadr newPoint)
                (if (caddr point) (caddr point) 0.0)))))
        (setq changed T))
      (setq out (append out (list point)))))
  (list out changed)
)

(defun DT--retarget-center-cuts
  (center oldPoint newPoint tol / cuts cut point gap out changed)
  (setq cuts (DT--plus-cuts center))
  (foreach cut cuts
    (setq point (DT--cut-point cut)
          gap   (if (and (listp cut) (listp (car cut))) (cadr cut) nil))
    (if (<= (DT--distance-xy point oldPoint) tol)
      (progn
        (setq out (append out (list (list newPoint gap))))
        (setq changed T))
      (setq out (append out (list cut)))))
  (if changed (DT--set-plus-cuts center out))
  changed
)

(defun DT--sync-center-from-stretched-tray
  (tray oldSignature / center oldSeg newSeg pts result changed tol)
  (setq center (DT--center-for-tray tray)
        oldSeg (DT--tray-signature-center-seg oldSignature)
        newSeg (DT--tray-center-seg tray)
        tol    0.01)
  (if (and center oldSeg newSeg
           (= (length oldSeg) 2)
           (= (length newSeg) 2))
    (progn
      (setq pts (g365_get_pts center))
      (setq result
        (DT--replace-route-point-near
          pts (car oldSeg) (car newSeg) tol)
        pts     (car result)
        changed (cadr result))
      (setq result
        (DT--replace-route-point-near
          pts (cadr oldSeg) (cadr newSeg) tol)
        pts     (car result)
        changed (or changed (cadr result)))
      (DT--retarget-center-cuts
        center (car oldSeg) (car newSeg) tol)
      (DT--retarget-center-cuts
        center (cadr oldSeg) (cadr newSeg) tol)
      (if changed
        (progn
          (DT--set-center-points center pts)
          center)))))

(defun DT--connection-warning-layer ()
  "e_tava_baglanti_kontrol"
)

(defun DT--connection-warning-block-name ()
  "e_tava_baglanti_kontrol_kure"
)

(defun DT--connection-warning-radius ()
  ;; The configured PLAN scale expresses one physical centimetre.
  (* 50.0 (DEG:PLAN-UNIT-SCALE))
)

(defun DT--ensure-connection-warning-layer (/ lay)
  (setq lay (DT--connection-warning-layer))
  (DT--ensure-layer lay 1 nil)
  lay
)

(defun DT--ensure-connection-warning-block
  (/ name lay oldLayer oldEcho result sphere marker)
  (setq name (DT--connection-warning-block-name)
        lay  (DT--ensure-connection-warning-layer))
  (if (tblsearch "BLOCK" name)
    name
    (progn
      (setq oldLayer (getvar "CLAYER")
            oldEcho  (getvar "CMDECHO"))
      (setvar "CLAYER" lay)
      (setvar "CMDECHO" 0)
      (setq result
        (vl-catch-all-apply
          '(lambda ()
             (vl-cmdf
               "_.SPHERE"
               "_non" '(0.0 0.0 0.0)
               1.0)
             (setq sphere (entlast))
             (vl-cmdf
               "_.-BLOCK"
               name
               "_non" '(0.0 0.0 0.0)
               sphere "")
             (setq marker (entlast))
             (if (and marker
                      (entget marker)
                      (= (cdr (assoc 0 (entget marker))) "INSERT")
                      (=
                        (strcase (cdr (assoc 2 (entget marker))))
                        (strcase name)))
               (DT--safe-delete-ent marker))
             (if (DT--entity-alive-p sphere)
               (DT--safe-delete-ent sphere))
             (tblsearch "BLOCK" name))
          '()))
      (setvar "CLAYER" oldLayer)
      (setvar "CMDECHO" oldEcho)
      (if (or (vl-catch-all-error-p result)
              (not (tblsearch "BLOCK" name)))
        nil
        name)))
)

(defun DT--connection-warning-handles (ent / ed xd rec item out)
  (if (and ent
           (setq ed (entget ent '("DT_CONNECTION_WARNING")))
           (setq xd (assoc -3 ed)))
    (progn
      (setq rec (cadr xd))
      (foreach item (cdr rec)
        (if (= (car item) 1005)
          (setq out (cons (strcase (cdr item)) out))))))
  out
)

(defun DT--connection-warning-elevations
  (point centerA centerB / fallback zA zB result)
  (setq fallback
    (if (and (caddr point) (numberp (caddr point)))
      (caddr point)
      0.0))
  (setq result
    (vl-catch-all-apply
      'DT--center-elevation-at-point
      (list centerA point)))
  (if (not (vl-catch-all-error-p result)) (setq zA result))
  (setq result
    (vl-catch-all-apply
      'DT--center-elevation-at-point
      (list centerB point)))
  (if (not (vl-catch-all-error-p result)) (setq zB result))
  (cond
    ((and (numberp zA) (numberp zB))
      (if (equal zA zB 0.001)
        (list (/ (+ zA zB) 2.0))
        (if (< zA zB) (list zA zB) (list zB zA))))
    ((numberp zA) (list zA))
    ((numberp zB) (list zB))
    (T (list fallback)))
)

(defun DT--connection-warning-same-elevation-p
  (point centerA centerB / zA zB result tolerance)
  (setq result
    (vl-catch-all-apply
      'DT--center-elevation-at-point
      (list centerA point)))
  (if (not (vl-catch-all-error-p result)) (setq zA result))
  (setq result
    (vl-catch-all-apply
      'DT--center-elevation-at-point
      (list centerB point)))
  (if (not (vl-catch-all-error-p result)) (setq zB result))
  ;; 0.01 cm fiziksel tolerans: mm, cm ve metre planlarinda ayni sonucu verir.
  (setq tolerance
    (max 0.000001 (* 0.01 (DEG:PLAN-UNIT-SCALE))))
  (and (numberp zA)
       (numberp zB)
       (equal zA zB tolerance))
)

(defun DT--make-connection-warning-insert
  (point radius centerA centerB / app ent ed payload handle)
  (setq app "DT_CONNECTION_WARNING")
  (if (not (tblsearch "APPID" app)) (regapp app))
  (if (and (numberp radius)
           (> radius 0.0)
           (DT--ensure-connection-warning-block))
    (setq ent
      (entmakex
        (list
          '(0 . "INSERT")
          (cons 2 (DT--connection-warning-block-name))
          (cons 8 (DT--connection-warning-layer))
          (cons 10
            (list
              (car point)
              (cadr point)
              (if (and (caddr point) (numberp (caddr point)))
                (caddr point)
                0.0)))
          (cons 41 radius)
          (cons 42 radius)
          (cons 43 radius)
          '(50 . 0.0)
          '(62 . 256)))))
  (if ent
    (progn
      (setq payload (list app))
      (foreach handle
        (list (DT--ent-handle centerA) (DT--ent-handle centerB))
        (if handle
          (setq payload
            (append payload (list (cons 1005 handle))))))
      (setq ed (entget ent '("*"))
            ed (DT--xdata-set-app ed app payload))
      (entmod ed)
      (entupd ent)))
  ent
)

(defun DT--mark-connection-warning
  (point radius centerA centerB / elevations elevation marker firstMarker)
  (if (DT--connection-warning-same-elevation-p
        point centerA centerB)
    (progn
      (setq elevations
        (DT--connection-warning-elevations point centerA centerB))
      (foreach elevation elevations
        (setq marker
          (DT--make-connection-warning-insert
            (list (car point) (cadr point) elevation)
            radius centerA centerB))
        (if (and marker (null firstMarker))
          (setq firstMarker marker)))))
  firstMarker
)

(defun DT--all-active-centers (/ center out)
  ;; DT oturumu basinda kurulan merkez cache'ini kullan; her yeni tavada
  ;; model space'in tamamini yeniden tarama.
  (foreach center (DT--center-cache-source)
    (if (and (DT--entity-alive-p center)
             (DT--active-center-p center))
      (setq out (cons center out))))
  (reverse out)
)

(defun DT--center-segments (center / pts i out)
  (setq pts (if center (g365_get_pts center) nil)
        i   0)
  (while (and pts (< i (1- (length pts))))
    (if (> (DT--distance-xy (nth i pts) (nth (1+ i) pts)) 0.001)
      (setq out
        (append out
          (list (list (nth i pts) (nth (1+ i) pts))))))
    (setq i (1+ i)))
  out
)

(defun DT--point-on-segment-contact
  (point segment tolerance / rec closest distanceValue)
  (setq rec
    (g365_closest_on_seg point (car segment) (cadr segment)))
  (if rec
    (progn
      (setq closest     (car rec)
            distanceValue (nth 2 rec))
      (if (<= distanceValue tolerance)
        (list
          (DT--pt-mid point closest)
          distanceValue)))))

(defun DT--segments-parallel-p (a b c d / u v)
  (setq u (DT--seg-unit a b)
        v (DT--seg-unit c d))
  (and u v
       (> (abs (g365_dot (car u) (cadr u) (car v) (cadr v)))
          0.999)))

(defun DT--center-pair-contact-points
  (centerA centerB / segsA segsB widthA widthB tolerance
    segA segB ip contact point out)
  (setq segsA     (DT--center-segments centerA)
        segsB     (DT--center-segments centerB)
        widthA    (DT--center-width centerA (DT--plan-width (DT--last-width)))
        widthB    (DT--center-width centerB (DT--plan-width (DT--last-width)))
        tolerance (+ (/ widthA 2.0) (/ widthB 2.0) 0.5))
  (foreach segA segsA
    (foreach segB segsB
      (setq ip (inters (car segA) (cadr segA)
                       (car segB) (cadr segB) T))
      (if ip
        (progn
          (setq point (list (car ip) (cadr ip) 0.0))
          (if (not (DT--point-known-p point out 0.01))
            (setq out (append out (list point)))))
        (foreach point
          (list (car segA) (cadr segA) (car segB) (cadr segB))
          (setq contact
            (cond
              ((or (equal point (car segA) 0.000001)
                   (equal point (cadr segA) 0.000001))
                (DT--point-on-segment-contact point segB tolerance))
              (T
                (DT--point-on-segment-contact point segA tolerance))))
          (if (and contact
                   (not (DT--point-known-p (car contact) out 0.01)))
            (setq out (append out (list (car contact)))))))))
  out
)

(defun DT--connection-warning-fitting-p
  (point fittings fallbackWidth / ent ed insertPoint width tolerance hit)
  (foreach ent fittings
    (if (and (not hit)
             (DT--entity-alive-p ent)
             (DT--fitting-insert-p ent))
      (progn
        (setq ed          (entget ent)
              insertPoint (cdr (assoc 10 ed))
              width       (DT--fitting-insert-width ent fallbackWidth)
              tolerance   (+ (max 1.0 (/ width 2.0)) 1.0))
        (if (and insertPoint
                 (or
                   (DT--point-in-fitting-box-p point ent 0.5)
                   (<=
                     (DT--distance-xy
                       point
                       (list (car insertPoint) (cadr insertPoint) 0.0))
                     tolerance)))
          (setq hit T)))))
  hit
)

(defun DT--connection-warning-fittings (/ ent out)
  (foreach ent (DT--fitting-inserts)
    (if (DT--entity-alive-p ent)
      (setq out (cons ent out))))
  (reverse out)
)

(defun DT--delete-connection-warnings-for-centers
  (centers / handles center ss i ent markerHandles remove handle)
  (foreach center centers
    (setq handle (DT--ent-handle center))
    (if handle (setq handles (cons (strcase handle) handles))))
  (if (tblsearch "APPID" "DT_CONNECTION_WARNING")
    (setq ss
      (ssget "_X"
        '((0 . "CIRCLE,INSERT") (-3 ("DT_CONNECTION_WARNING"))))))
  (if ss
    (progn
      (setq i 0)
      (while (< i (sslength ss))
        (setq ent           (ssname ss i)
              markerHandles (DT--connection-warning-handles ent)
              remove        nil)
        (foreach handle markerHandles
          (if (member handle handles) (setq remove T)))
        (if remove (DT--safe-delete-ent ent))
        (setq i (1+ i)))))
  T
)

(defun DT--upgrade-connection-warning-markers
  (/ ss i marker ed type oldMarker point handles centerA centerB made)
  (if (tblsearch "APPID" "DT_CONNECTION_WARNING")
    (setq ss
      (ssget "_X"
        '((0 . "CIRCLE,INSERT") (-3 ("DT_CONNECTION_WARNING"))))))
  (if ss
    (progn
      (setq i 0)
      (while (< i (sslength ss))
        (setq marker    (ssname ss i)
              ed        (entget marker)
              type      (cdr (assoc 0 ed))
              oldMarker
                (or
                  (= type "CIRCLE")
                  (and (= type "INSERT")
                       (/=
                         (strcase (if (cdr (assoc 2 ed)) (cdr (assoc 2 ed)) ""))
                         (strcase (DT--connection-warning-block-name)))))
              point     (cdr (assoc 10 ed))
              handles   (DT--connection-warning-handles marker)
              centerA (if (car handles) (handent (car handles)) nil)
              centerB (if (cadr handles) (handent (cadr handles)) nil))
        (cond
          ((and point centerA centerB
                (not
                  (DT--connection-warning-same-elevation-p
                    point centerA centerB)))
            (DT--safe-delete-ent marker))
          ((and oldMarker point centerA centerB)
            (if (DT--mark-connection-warning
                  point
                  (DT--connection-warning-radius)
                  centerA centerB)
              (progn
                (DT--safe-delete-ent marker)
                (setq made (1+ (if made made 0)))))))
        (setq i (1+ i)))))
  (if made made 0)
)

(defun DT--connection-warning-needed-p
  (centerA centerB point fittings / layerA layerB ptsA ptsB arms)
  (if (DT--connection-warning-same-elevation-p
        point centerA centerB)
    (progn
      (setq layerA (DT--center-layer centerA "")
            layerB (DT--center-layer centerB ""))
      (if (not (DT--same-tray-layer-p layerA layerB))
        (not
          (DT--connection-warning-fitting-p
            point
            fittings
            (max
              (DT--center-width centerA 1.0)
              (DT--center-width centerB 1.0))))
        (progn
          (setq ptsA (g365_get_pts centerA)
                ptsB (g365_get_pts centerB)
                arms
                  (DT--combine-arms
                    (DT--arms-at-point ptsA point 0.01)
                    (DT--arms-at-point ptsB point 0.01)))
          (if (null arms)
            (setq arms
              (DT--combine-arms
                (list (DT--dir-at-point ptsA point))
                (list (DT--dir-at-point ptsB point)))))
          (setq arms (vl-remove nil arms))
          (and arms
               (not (DT--all-collinear-p arms))
               (not
                 (DT--connection-warning-fitting-p
                   point
                   fittings
                   (max
                     (DT--center-width centerA 1.0)
                     (DT--center-width centerB 1.0)))))))))
)

(defun DT--refresh-connection-warnings-for-centers
  (targets / all fittings target other targetHandle otherHandle pairKey reverseKey
    processed contacts point width radius made nearby targetPts targetWidth)
  (setq targets
    (vl-remove-if-not
      '(lambda (center)
         (and center
              (DT--entity-alive-p center)
              (DT--active-center-p center)))
      targets))
  (if targets
    (progn
      (DT--delete-connection-warnings-for-centers targets)
      (setq all      (DT--all-active-centers)
            fittings (DT--connection-warning-fittings))
      (foreach target targets
        (setq targetHandle (DT--ent-handle target)
              targetPts    (g365_get_pts target)
              targetWidth
                (DT--center-width
                  target
                  (DT--plan-width (DT--last-width)))
              nearby
                (DT--filter-centers-near-route
                  all targetPts targetWidth))
        (foreach other nearby
          (if (and (not (eq target other))
                   (setq otherHandle (DT--ent-handle other)))
            (progn
              (setq pairKey    (strcat targetHandle "|" otherHandle)
                    reverseKey (strcat otherHandle "|" targetHandle))
              (if (and (not (member pairKey processed))
                       (not (member reverseKey processed)))
                (progn
                  (setq processed (cons pairKey processed)
                        contacts
                          (DT--center-pair-contact-points target other))
                  (foreach point contacts
                    (if (DT--connection-warning-needed-p
                          target other point fittings)
                      (progn
                        (setq width
                          (max
                            (DT--center-width target 1.0)
                            (DT--center-width other 1.0))
                          radius (DT--connection-warning-radius))
                        (if (DT--mark-connection-warning
                              point radius target other)
                          (setq made (1+ (if made made 0)))))))))))))))
  (if made made 0)
)

(vl-catch-all-apply 'DT--upgrade-connection-warning-markers '())

(defun DT--connection-warning-marker-p (ent / ed handles)
  (and ent
       (DT--entity-alive-p ent)
       (setq ed (entget ent '("DT_CONNECTION_WARNING")))
       (member (cdr (assoc 0 ed)) '("CIRCLE" "INSERT"))
       (setq handles (DT--connection-warning-handles ent))
       (>= (length handles) 2))
)

(defun DT--selected-connection-warning (ss / i ent marker)
  (if ss
    (progn
      (setq i 0)
      (while (and (< i (sslength ss)) (null marker))
        (setq ent (ssname ss i))
        (if (DT--connection-warning-marker-p ent)
          (setq marker ent))
        (setq i (1+ i)))))
  marker
)

(defun DT--warning-contact-candidates
  (centerA centerB / segsA segsB widthA widthB tolerance
    segA segB ip endpoint rec closest display candidates)
  (setq segsA     (DT--center-segments centerA)
        segsB     (DT--center-segments centerB)
        widthA    (DT--center-width centerA 1.0)
        widthB    (DT--center-width centerB 1.0)
        tolerance (+ (/ widthA 2.0) (/ widthB 2.0) 0.5))
  (foreach segA segsA
    (foreach segB segsB
      (setq ip
        (inters
          (car segA) (cadr segA)
          (car segB) (cadr segB)
          T))
      (if ip
        (progn
          (setq ip (list (car ip) (cadr ip) 0.0))
          (setq candidates
            (cons
              (list ip ip nil nil nil)
              candidates)))
        (progn
          (foreach endpoint (list (car segA) (cadr segA))
            (setq rec
              (g365_closest_on_seg
                endpoint (car segB) (cadr segB)))
            (if (and rec (<= (nth 2 rec) tolerance))
              (progn
                (setq closest (car rec)
                      closest
                        (list (car closest) (cadr closest) 0.0)
                      display (DT--pt-mid endpoint closest))
                (setq candidates
                  (cons
                    (list display closest centerA endpoint closest)
                    candidates)))))
          (foreach endpoint (list (car segB) (cadr segB))
            (setq rec
              (g365_closest_on_seg
                endpoint (car segA) (cadr segA)))
            (if (and rec (<= (nth 2 rec) tolerance))
              (progn
                (setq closest (car rec)
                      closest
                        (list (car closest) (cadr closest) 0.0)
                      display (DT--pt-mid endpoint closest))
                (setq candidates
                  (cons
                    (list display closest centerB endpoint closest)
                    candidates)))))))))
  candidates
)

(defun DT--warning-best-contact
  (markerPoint centerA centerB / candidate score bestScore best)
  (foreach candidate (DT--warning-contact-candidates centerA centerB)
    (setq score
      (DT--distance-xy markerPoint (car candidate)))
    (if (or (null bestScore) (< score bestScore))
      (setq bestScore score
            best candidate)))
  best
)

(defun DT--warning-adjust-center-points
  (center pts moveCenter oldPoint newPoint / result)
  (if (and (eq center moveCenter) oldPoint newPoint)
    (progn
      (setq result
        (DT--replace-route-point-near
          pts oldPoint newPoint 0.05))
      (if (cadr result)
        (list (car result) (list oldPoint newPoint 0.05))
        (list pts nil)))
    (list pts nil))
)

(defun DT--warning-primary-center
  (centerA centerB armsA armsB widthA widthB)
  (cond
    ((> (length armsA) (length armsB)) centerA)
    ((> (length armsB) (length armsA)) centerB)
    ((>= widthA widthB) centerA)
    (T centerB))
)

(defun DT--warning-fitting-fallback
  (point specs fitWidth / ray insert)
  (if (= (length specs) 1)
    (progn
      (setq ray (caar specs))
      (setq specs
        (DT--add-arm-spec
          (list (- (car ray)) (- (cadr ray)))
          fitWidth
          specs))))
  (if (>= (length specs) 2)
    (progn
      (DT--delete-existing-fittings-at
        point (DT--layer-fitting) (+ fitWidth 1.0))
      (setq insert
        (DT--draw-flex-fitting
          point specs (DT--layer-fitting)))
      (if insert 'FLEX)))
)

(defun DT--merge-connection-warning
  (marker
    / handles centerA centerB markerPoint contact point moveCenter oldPoint newPoint
      ptsA ptsB adjusted shiftA shiftB widthA widthB armsA armsB specs arm
      fitWidth primary primaryLayer primaryMeta sideMm kind fittingExists
      oldMode oldLayer oldElevation oldSide oldSideMm
      *DT_REBUILD_POINT_SHIFT*)
  (setq handles (DT--connection-warning-handles marker)
        centerA (if (car handles) (handent (car handles)) nil)
        centerB (if (cadr handles) (handent (cadr handles)) nil)
        markerPoint (if marker (cdr (assoc 10 (entget marker))) nil))
  (if (and markerPoint
           centerA centerB
           (not (eq centerA centerB))
           (DT--active-center-p centerA)
           (DT--active-center-p centerB)
           (DT--connection-warning-same-elevation-p
             markerPoint centerA centerB)
           (setq contact
             (DT--warning-best-contact markerPoint centerA centerB)))
    (progn
      (setq point      (cadr contact)
            moveCenter (nth 2 contact)
            oldPoint   (nth 3 contact)
            newPoint   (nth 4 contact)
            ptsA       (g365_get_pts centerA)
            ptsB       (g365_get_pts centerB)
            adjusted
              (DT--warning-adjust-center-points
                centerA ptsA moveCenter oldPoint newPoint)
            ptsA       (car adjusted)
            shiftA     (cadr adjusted)
            adjusted
              (DT--warning-adjust-center-points
                centerB ptsB moveCenter oldPoint newPoint)
            ptsB       (car adjusted)
            shiftB     (cadr adjusted)
            widthA     (DT--center-width centerA 1.0)
            widthB     (DT--center-width centerB 1.0)
            armsA      (DT--arms-at-point ptsA point 0.01)
            armsB      (DT--arms-at-point ptsB point 0.01))
      (foreach arm armsA
        (setq specs (DT--add-arm-spec arm widthA specs)))
      (foreach arm armsB
        (setq specs (DT--add-arm-spec arm widthB specs)))
      (setq fitWidth
              (DT--specs-max-width specs (max widthA widthB))
            primary
              (DT--warning-primary-center
                centerA centerB armsA armsB widthA widthB)
            primaryLayer
              (DT--center-layer
                primary (DT--mode-layer (DT--last-mode)))
            primaryMeta (DT--tray-meta primary)
            sideMm
              (if (and primaryMeta
                       (numberp (caddr primaryMeta))
                       (> (caddr primaryMeta) 0.0))
                (caddr primaryMeta)
                (DT--active-side-height-mm))
            oldMode      *DT_ACTIVE_MODE*
            oldLayer     *DT_ACTIVE_LAYER*
            oldElevation (DT--active-elevation)
            oldSide      (DT--active-side-height)
            oldSideMm    (DT--active-side-height-mm)
            *DT_ACTIVE_MODE*
              (if primaryMeta
                (DT--normalize-mode (car primaryMeta))
                (DT--mode-from-layer primaryLayer))
            *DT_ACTIVE_LAYER* primaryLayer
            *DT_ACTIVE_ELEVATION*
              (if (and (caddr markerPoint)
                       (numberp (caddr markerPoint)))
                (caddr markerPoint)
                (DT--entity-elevation primary))
            *DT_ACTIVE_SIDE_HEIGHT_MM* sideMm
            *DT_ACTIVE_SIDE_HEIGHT* (DT--plan-side-height sideMm))
      (DT--ensure-layer
        primaryLayer
        (DT--layer-color-for-name primaryLayer)
        nil)
      (setq kind
        (DT--draw-updated-junction-fitting
          point
          (DT--arm-spec-rays specs)
          specs
          fitWidth))
      (if (null kind)
        (setq kind
          (DT--warning-fitting-fallback point specs fitWidth)))
      (setq fittingExists
        (and kind (DT--live-fitting-at-point-p point fitWidth)))
      (if fittingExists
        (progn
          (if shiftA
            (progn
              (DT--retarget-center-cuts
                centerA (car shiftA) (cadr shiftA) (caddr shiftA))
              (DT--set-center-points centerA ptsA)))
          (if shiftB
            (progn
              (DT--retarget-center-cuts
                centerB (car shiftB) (cadr shiftB) (caddr shiftB))
              (DT--set-center-points centerB ptsB)))
          (DT--add-plus-cut centerA point fitWidth)
          (DT--add-plus-cut centerB point fitWidth)
          (setq *DT_REBUILD_POINT_SHIFT* shiftA)
          (DT--rebuild-center-pieces centerA widthA nil)
          (setq *DT_REBUILD_POINT_SHIFT* shiftB)
          (DT--rebuild-center-pieces centerB widthB nil)
          (setq *DT_REBUILD_POINT_SHIFT* nil)
          (DT--safe-delete-ent marker)
          (DT--refresh-connection-warnings-for-centers
            (list centerA centerB))))
      (setq *DT_ACTIVE_MODE* oldMode
            *DT_ACTIVE_LAYER* oldLayer
            *DT_ACTIVE_ELEVATION* oldElevation
            *DT_ACTIVE_SIDE_HEIGHT* oldSide
            *DT_ACTIVE_SIDE_HEIGHT_MM* oldSideMm)
      (if fittingExists
        (list kind centerA centerB point)))))

(defun C:DT_PALETTE_MERGE
  (/ rec path state requestId ss marker undoToken result status)
  (vl-load-com)
  (setq rec (DT--palette-open-state))
  (if rec
    (setq path      (car rec)
          state     (cadr rec)
          requestId (DT--palette-state-get "REQUEST_ID" state)))
  (setq ss     (DT--pickfirst-selection)
        marker (DT--selected-connection-warning ss))
  (cond
    ((null marker)
      (setq status
        "Birlestirmek icin once kirmizi cakisma kuresini secin."))
    (T
      (setq undoToken (DEG:UNDO-GROUP-BEGIN)
            result
              (vl-catch-all-apply
                'DT--merge-connection-warning
                (list marker)))
      (DEG:UNDO-GROUP-END undoToken)
      (cond
        ((vl-catch-all-error-p result)
          (setq status
            (strcat
              "Birlestirme hatasi: "
              (vl-catch-all-error-message result))))
        (result
          (setq status
            "Iki tava baglanti blogu ile birlestirildi."))
        (T
          (setq status
            "Kuredeki iki tava birlestirilemedi; tava merkezleri bulunamadi.")))))
  (sssetfirst nil nil)
  (if path
    (progn
      (setq state (DT--palette-state-read path)
            state (DT--palette-state-put "REQUEST" "" state)
            state
              (DT--palette-state-put
                "REQUEST_DONE" (if requestId requestId "") state)
            state (DT--palette-state-put "STATUS" status state))
      (DT--palette-state-write path state)))
  (princ (strcat "\nDT palet: " status))
  (DT--palette-publish-current-selection)
  (princ)
)

(defun DT--sidewall-sync-watched-command-p (cmd)
  (member cmd
    '("STRETCH" "GRIP_STRETCH"
      "MOVE" "GRIP_MOVE"
      "ROTATE" "GRIP_ROTATE"
      "SCALE" "GRIP_SCALE"
      "MIRROR" "ALIGN"
      "COPY" "GRIP_COPY"
      "PASTECLIP" "PASTEORIG" "PASTEBLOCK"))
)

(defun DT--composite-erase-map (/ tray trayHandle entities ent handle handles out)
  (foreach tray (DT--light-all-trays)
    (setq trayHandle (DT--ent-handle tray)
          entities   (cdr (DT--tray-group-entities tray))
          handles    nil)
    (foreach ent entities
      (setq handle (DT--ent-handle ent))
      (if handle (setq handles (cons handle handles))))
    (if (and trayHandle handles)
      (setq out (cons (cons trayHandle handles) out))))
  out
)

(defun DT--sidewall-sync-command-start (reactor info / cmd)
  (if (not *DT_SIDEWALL_SYNC_BUSY*)
    (progn
      (setq cmd (DT--sidewall-sync-command-name info))
      (DT--composite-stretch-selection-begin cmd)
      (cond
        ((= cmd "ERASE")
          (setq *DT_COMPOSITE_ERASE_BEFORE* (DT--composite-erase-map)))
        ((DT--sidewall-sync-watched-command-p cmd)
          (setq *DT_SIDEWALL_SYNC_COMMAND* cmd
                *DT_SIDEWALL_SYNC_BEFORE* (DT--tray-signature-map)
                *DT_LIGHT_LADDER_BEFORE* (DT--light-ladder-signature-map))))))
  (princ)
)

(defun DT--sidewall-sync-command-finish
  (reactor info / cmd before now rec old tray center changedCenters ladderNow control)
  (setq cmd (DT--sidewall-sync-command-name info))
  (if (= cmd "ERASE") (DT--composite-erase-finish))
  (if (DT--composite-undo-command-p cmd)
    (progn
      (setq *DT_DELETED_HANDLES* nil)
      (vl-catch-all-apply 'DT--light-repair-tray-copies '())
      (vl-catch-all-apply 'DT--light-repair-ladder-copies '())))
  (if (and (not *DT_SIDEWALL_SYNC_BUSY*)
           *DT_SIDEWALL_SYNC_COMMAND*
           (= cmd *DT_SIDEWALL_SYNC_COMMAND*))
    (progn
      (setq *DT_SIDEWALL_SYNC_BUSY* T
            before *DT_SIDEWALL_SYNC_BEFORE*
            now    (DT--tray-signature-map))
      (foreach rec now
        (setq old (assoc (car rec) before))
        (if (and old (not (equal (cdr old) (cdr rec) 0.000001)))
          (progn
            (setq tray (handent (car rec)))
            (if tray
              (progn
                (setq center
                  (DT--sync-center-from-stretched-tray tray (cdr old)))
                (if (and center
                         (not (DT--entity-in-list-p center changedCenters)))
                  (setq changedCenters
                    (append changedCenters (list center))))
                (vl-catch-all-apply
                  'DT--rebuild-tray-sidewall-geometry
                  (list tray)))))))
      (setq ladderNow (DT--light-ladder-signature-map))
      (foreach rec ladderNow
        (setq old (assoc (car rec) *DT_LIGHT_LADDER_BEFORE*))
        (if (and old (not (equal (cdr old) (cdr rec) 0.000001)))
          (progn
            (setq control (handent (car rec)))
            (if control
              (vl-catch-all-apply 'DT--light-rebuild-ladder (list control))))))
      (if (member cmd '("COPY" "GRIP_COPY" "PASTECLIP" "PASTEORIG" "PASTEBLOCK"))
        (progn
          (vl-catch-all-apply 'DT--light-repair-tray-copies '())
          (vl-catch-all-apply 'DT--light-repair-ladder-copies '())
          (vl-catch-all-apply 'DT--light-clean-orphan-tray-visuals '())))
      (if changedCenters
        (vl-catch-all-apply
          'DT--refresh-connection-warnings-for-centers
          (list changedCenters)))
      (setq *DT_SIDEWALL_SYNC_BEFORE* nil
            *DT_LIGHT_LADDER_BEFORE* nil
            *DT_SIDEWALL_SYNC_COMMAND* nil
            *DT_SIDEWALL_SYNC_BUSY* nil)))
  (DT--composite-stretch-selection-end)
  (princ)
)

(defun DT--sidewall-sync-command-cancel (reactor info)
  (DT--composite-stretch-selection-end)
  (setq *DT_SIDEWALL_SYNC_BEFORE* nil
        *DT_LIGHT_LADDER_BEFORE* nil
        *DT_SIDEWALL_SYNC_COMMAND* nil
        *DT_COMPOSITE_ERASE_BEFORE* nil
        *DT_SIDEWALL_SYNC_BUSY* nil)
  (princ)
)

(defun DTT--selection-handles
  (ss / i raw en h out ladderMeta ladderKey representative ladderSeen attached)
  (setq i 0 out nil)
  (if ss
    (while (< i (sslength ss))
      (setq raw         (ssname ss i)
            en
              (if (DT--light-ladder-visual-p raw)
                (DT--light-ladder-controller raw)
                raw)
            ladderMeta  (DT--ladder-meta en)
            attached
              (if ladderMeta
                (or
                  (DT--light-ladder-control-p en)
                  (DT--ladder-attached-group-p en))))
      (cond
        ((DT--light-tray-visual-p raw) nil)
        (ladderMeta
          (if (or attached (DT--ladder-top-cap-entity-p en))
            (progn
              (setq ladderKey (DTT--ladder-key en))
              (if (not (member ladderKey ladderSeen))
                (progn
                  (setq ladderSeen (cons ladderKey ladderSeen)
                        representative
                          (if attached (DT--ladder-top-cap en) en)
                        h (if representative
                            (cdr (assoc 5 (entget representative)))))
                  (if h (setq out (cons h out))))))))
        (T
          (setq h (cdr (assoc 5 (entget en))))
          (if h (setq out (cons h out)))))
      (setq i (1+ i))))
  (reverse out)
)

(defun DT--selected-center-map
  (/ ss i center tray handle out)
  ;; Build the center-to-tray index once per selection. The old palette path
  ;; scanned every center entity again for every selected tray.
  (setq ss
    (ssget "_X"
      (list
        (cons 0 "LWPOLYLINE,POLYLINE")
        (cons 8 (DT--layer-center)))))
  (if ss
    (progn
      (setq i 0)
      (while (< i (sslength ss))
        (setq center (ssname ss i))
        (if (and (DT--entity-alive-p center) (DT--active-center-p center))
          (foreach tray (DT--linked-trays center)
            (setq handle (if tray (DT--ent-handle tray)))
            (if (and handle (null (assoc handle out)))
              (setq out (cons (cons handle center) out)))))
        (setq i (1+ i)))))
  out
)

(defun DT--light-repair-tray-meta-from-centers
  (/ centerMap centerRec tray centerMeta trayMeta centerSide traySide count)
  (setq centerMap (DT--selected-center-map))
  (foreach centerRec centerMap
    (setq tray       (handent (car centerRec))
          centerMeta (DT--tray-meta (cdr centerRec))
          trayMeta   (DT--tray-meta tray)
          centerSide (if (and centerMeta (numberp (caddr centerMeta)))
                       (caddr centerMeta))
          traySide   (if (and trayMeta (numberp (caddr trayMeta)))
                       (caddr trayMeta)))
    (if (and centerMeta
             (not (DT--tray-piece-override-p tray))
             (> centerSide 0.0)
             (or (null traySide) (not (equal centerSide traySide 0.000001))))
      (progn
        (DT--set-tray-meta-one
          tray
          (car centerMeta)
          (cadr centerMeta)
          centerSide
          (nth 3 centerMeta))
        (if (DT--rebuild-tray-sidewall-geometry tray)
          (setq count (1+ (if count count 0)))))))
  (if count count 0)
)

(defun DT--selected-info
  (ss /
    i raw ent ed typ handle centerMap centerRec filteredTrays
    centers fittings looseTrays ladders
    centerSeen fittingSeen traySeen ladderSeen
    ladderMeta ladderKey)
  (if (and ss (= (type ss) 'PICKSET))
    (progn
      (setq i 0)
      (while (< i (sslength ss))
        (setq raw (ssname ss i)
              ent
                (cond
                  ((DT--light-tray-visual-p raw)
                    (DT--light-tray-visual-owner raw))
                  ((DT--light-ladder-visual-p raw)
                    (DT--light-ladder-controller raw))
                  (T raw))
              ed         (if ent (entget ent '("DT_FITTING")) nil)
              typ        (if ed (cdr (assoc 0 ed)) nil)
              handle     (if ent (DT--ent-handle ent))
              ladderMeta (if ent (DT--ladder-meta ent)))
        (cond
          (ladderMeta
            (setq ladderKey
              (if (DT--light-ladder-control-p ent)
                handle
                (DT--ladder-selection-key ent)))
            (if (and ladderKey (not (member ladderKey ladderSeen)))
              (setq ladderSeen (cons ladderKey ladderSeen)
                    ladders    (cons ent ladders))))
          ((DT--center-layer-p ent)
            (if (and handle (not (member handle centerSeen)))
              (setq centerSeen (cons handle centerSeen)
                    centers    (cons ent centers))))
          ((DT--visible-tray-p ent)
            (if (and handle (not (member handle traySeen)))
              (setq traySeen   (cons handle traySeen)
                    looseTrays (cons ent looseTrays))))
          ((and (= typ "INSERT") (DT--fitting-insert-p ent))
            (if (and handle (not (member handle fittingSeen)))
              (setq fittingSeen (cons handle fittingSeen)
                    fittings   (cons ent fittings)))))
        (setq i (1+ i)))))
  ;; A window selection can contain both the hidden center route and its tray
  ;; pieces. In that case the explicit center selection owns the operation;
  ;; otherwise a picked tray remains an individual palette edit.
  (if (and centers looseTrays)
    (progn
      (setq centerMap (DT--selected-center-map))
      (foreach ent looseTrays
        (setq centerRec (assoc (DT--ent-handle ent) centerMap))
        (if (not
              (and centerRec
                   (member
                     (DT--ent-handle (cdr centerRec))
                     centerSeen)))
          (setq filteredTrays (cons ent filteredTrays))))
      (setq looseTrays (reverse filteredTrays))))
  (list
    (reverse centers)
    (reverse fittings)
    (reverse looseTrays)
    (reverse ladders))
)

(defun C:DTHAFIF (/ trayCount ladderCount)
  (vl-load-com)
  (princ "\nDTHAFIF: Cizimdeki eski DT tava ve merdivenleri hafif yapiya donusturuyor...")
  (setq *DT_SIDEWALL_SYNC_BUSY* T)
  (setq trayCount   (DT--light-migrate-all-trays)
        ladderCount (DT--light-migrate-all-ladders))
  (DT--light-repair-tray-copies)
  (DT--light-repair-ladder-copies)
  (DT--light-clean-orphan-tray-visuals)
  (DT--light-repair-tray-meta-from-centers)
  (setq *DT_SIDEWALL_SYNC_BUSY* nil)
  (DT--ensure-composite-pickstyle)
  (vl-catch-all-apply 'setvar (list "GRIPOBJLIMIT" 100))
  (princ
    (strcat
      "\nDTHAFIF tamam: "
      (itoa trayCount) " tava, "
      (itoa ladderCount) " merdiven donusturuldu."))
  (princ)
)

(setq *DT_LIGHTWEIGHT_INSTALLED* T)

(vl-load-com)
(setq *DT_PALETTE_SELECTION_BUSY* nil)
(DT--reset-sidewall-sync-reactor)
(DT--reset-palette-selection-reactor)
(vl-catch-all-apply 'DT--ensure-composite-pickstyle '())
(vl-catch-all-apply 'setvar (list "GRIPOBJLIMIT" 100))
(DEG:CMD-APPLY-ALIASES)
(princ)
